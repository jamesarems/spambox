ASSP-MIB DEFINITIONS ::= BEGIN

--
-- Top-level infrastructure of the ASSP project enterprise MIB tree
--

IMPORTS
    MODULE-IDENTITY, enterprises, OBJECT-TYPE FROM SNMPv2-SMI
    Float FROM NET-SNMP-TC
    TruthValue FROM SNMPv2-TC;

thockar MODULE-IDENTITY
    LAST-UPDATED "201412170000Z"
    ORGANIZATION "www.thockar.com"
    CONTACT-INFO
	 "postal:       Thomas Eckardt

      email:    thockar@lists.sourceforge.net"
    DESCRIPTION
	"Top-level infrastructure of thockar projects enterprise MIB tree"
    REVISION     "201412170000Z"
    DESCRIPTION
	"First draft"
    ::= { enterprises 37058}

asspSNMP MODULE-IDENTITY
    LAST-UPDATED "201412170000Z"
    ORGANIZATION "www.thockar.com"
    CONTACT-INFO
	 "postal:       Thomas Eckardt

      email:    thockar@lists.sourceforge.net"
    DESCRIPTION
	"Top-level infrastructure of the thockar ASSP project enterprise MIB tree"
    REVISION     "201412160000Z"
    DESCRIPTION
	"First draft"
    ::= { thockar 2}

--
--  ASSP enterprise-specific management objects
--

asspRunTimeInfo              OBJECT IDENTIFIER ::= {asspSNMP 1}
asspConfig                   OBJECT IDENTIFIER ::= {asspSNMP 2}
asspPerlModuleInfo           OBJECT IDENTIFIER ::= {asspSNMP 3}
asspStats                    OBJECT IDENTIFIER ::= {asspSNMP 4}
asspAPI                      OBJECT IDENTIFIER ::= {asspSNMP 5}

currentStats                 OBJECT IDENTIFIER ::= {asspStats 1}
cumulativeStat               OBJECT IDENTIFIER ::= {asspStats 2}
currentTotalStat             OBJECT IDENTIFIER ::= {asspStats 3}
cumulativeTotalStat          OBJECT IDENTIFIER ::= {asspStats 4}
currentScoreStat             OBJECT IDENTIFIER ::= {asspStats 5}
cumulativeScoreStat          OBJECT IDENTIFIER ::= {asspStats 6}


asspHealtyBool    OBJECT-TYPE
    SYNTAX      OCTET STRING
    MAX-ACCESS  read-only
    STATUS      current
    DESCRIPTION
"
assp healthy Status
"
     ::= {asspRunTimeInfo 0}
asspHealtyText    OBJECT-TYPE
    SYNTAX      OCTET STRING
    MAX-ACCESS  read-only
    STATUS      current
    DESCRIPTION
"
assp healthy Status
"
     ::= {asspRunTimeInfo 1}
asspRunningBool    OBJECT-TYPE
    SYNTAX      OCTET STRING
    MAX-ACCESS  read-only
    STATUS      current
    DESCRIPTION
"
is running or shutting down
"
     ::= {asspRunTimeInfo 2}
asspRunningText    OBJECT-TYPE
    SYNTAX      OCTET STRING
    MAX-ACCESS  read-only
    STATUS      current
    DESCRIPTION
"
is running or shutting down
"
     ::= {asspRunTimeInfo 3}
asspVersionString    OBJECT-TYPE
    SYNTAX      OCTET STRING
    MAX-ACCESS  read-only
    STATUS      current
    DESCRIPTION
"
assp version
"
     ::= {asspRunTimeInfo 4}
asspScriptName    OBJECT-TYPE
    SYNTAX      OCTET STRING
    MAX-ACCESS  read-only
    STATUS      current
    DESCRIPTION
"
assp script name
"
     ::= {asspRunTimeInfo 5}
perlVersionString    OBJECT-TYPE
    SYNTAX      OCTET STRING
    MAX-ACCESS  read-only
    STATUS      current
    DESCRIPTION
"
perl version
"
     ::= {asspRunTimeInfo 6}
perlExecutableName    OBJECT-TYPE
    SYNTAX      OCTET STRING
    MAX-ACCESS  read-only
    STATUS      current
    DESCRIPTION
"
perl executable
"
     ::= {asspRunTimeInfo 7}
operatingSystemName    OBJECT-TYPE
    SYNTAX      OCTET STRING
    MAX-ACCESS  read-only
    STATUS      current
    DESCRIPTION
"
operating system name
"
     ::= {asspRunTimeInfo 8}
hostName    OBJECT-TYPE
    SYNTAX      OCTET STRING
    MAX-ACCESS  read-only
    STATUS      current
    DESCRIPTION
"
host name
"
     ::= {asspRunTimeInfo 9}
hostIP     OBJECT-TYPE
    SYNTAX      OCTET STRING
    MAX-ACCESS  read-only
    STATUS      current
    DESCRIPTION
"
host IP
"
     ::= {asspRunTimeInfo 10}
myNameRTI     OBJECT-TYPE
    SYNTAX      OCTET STRING
    MAX-ACCESS  read-only
    STATUS      current
    DESCRIPTION
"
myName from config
"
     ::= {asspRunTimeInfo 11}
asspVersionURL     OBJECT-TYPE
    SYNTAX      OCTET STRING
    MAX-ACCESS  read-only
    STATUS      current
    DESCRIPTION
"
URL to update assp
"
     ::= {asspRunTimeInfo 12}
runningTasks     OBJECT-TYPE
    SYNTAX      OCTET STRING
    MAX-ACCESS  read-only
    STATUS      current
    DESCRIPTION
"
currently running tasks
"
     ::= {asspRunTimeInfo 13}
memoryUsage     OBJECT-TYPE
    SYNTAX      OCTET STRING
    MAX-ACCESS  read-only
    STATUS      current
    DESCRIPTION
"
memory usage
"
     ::= {asspRunTimeInfo 14}

scheduleInformation     OBJECT IDENTIFIER ::= {asspRunTimeInfo 20}

nextBerkeleyDBSync     OBJECT-TYPE
    SYNTAX      OCTET STRING
    MAX-ACCESS  read-only
    STATUS      current
    DESCRIPTION
"
next BerkeleyDB database synchronisation to disk
"
     ::= {scheduleInformation 1}
nextConfigReload     OBJECT-TYPE
    SYNTAX      OCTET STRING
    MAX-ACCESS  read-only
    STATUS      current
    DESCRIPTION
"
next scheduled Config reload
"
     ::= {scheduleInformation 2}
nextBATVTagCacheCleaning      OBJECT-TYPE
    SYNTAX      OCTET STRING
    MAX-ACCESS  read-only
    STATUS      current
    DESCRIPTION
"
next BATVTag Cache Cleaning
"
     ::= {scheduleInformation 3}
nextgeneralCacheCleaning     OBJECT-TYPE
    SYNTAX      OCTET STRING
    MAX-ACCESS  read-only
    STATUS      current
    DESCRIPTION
"
next general Cache Cleaning
"
     ::= {scheduleInformation 4}
nextIPperDomainCacheCleaning    OBJECT-TYPE
    SYNTAX      OCTET STRING
    MAX-ACCESS  read-only
    STATUS      current
    DESCRIPTION
"
next IPperDomain Cache Cleaning
"
     ::= {scheduleInformation 5}
nextDelayDBCacheCleaning    OBJECT-TYPE
    SYNTAX      OCTET STRING
    MAX-ACCESS  read-only
    STATUS      current
    DESCRIPTION
"
next DelayDB Cache Cleaning
"
     ::= {scheduleInformation 6}
nextPenaltyboxCacheCleaning     OBJECT-TYPE
    SYNTAX      OCTET STRING
    MAX-ACCESS  read-only
    STATUS      current
    DESCRIPTION
"
next Penaltybox Cache Cleaning
"
     ::= {scheduleInformation 7}
nextDatabaseBackup     OBJECT-TYPE
    SYNTAX      OCTET STRING
    MAX-ACCESS  read-only
    STATUS      current
    DESCRIPTION
"
next Database Backup
"
     ::= {scheduleInformation 8}
nextDatabaseConnectionCheck     OBJECT-TYPE
    SYNTAX      OCTET STRING
    MAX-ACCESS  read-only
    STATUS      current
    DESCRIPTION
"
next Database Connection Check
"
     ::= {scheduleInformation 9}
nextDNSConnectionCheck    OBJECT-TYPE
    SYNTAX      OCTET STRING
    MAX-ACCESS  read-only
    STATUS      current
    DESCRIPTION
"
next DNS-Connection Check
"
     ::= {scheduleInformation 10}
nextHourlyJobAt     OBJECT-TYPE
    SYNTAX      OCTET STRING
    MAX-ACCESS  read-only
    STATUS      current
    DESCRIPTION
"
next Hourly Job will run at
"
     ::= {scheduleInformation 11}
nextDatabaseExport     OBJECT-TYPE
    SYNTAX      OCTET STRING
    MAX-ACCESS  read-only
    STATUS      current
    DESCRIPTION
"
next Database Export
"
     ::= {scheduleInformation 12}
nextUploadGlobalBlack     OBJECT-TYPE
    SYNTAX      OCTET STRING
    MAX-ACCESS  read-only
    STATUS      current
    DESCRIPTION
"
next Upload Global-Black
"
     ::= {scheduleInformation 13}
nextUploadGlobalWhite     OBJECT-TYPE
    SYNTAX      OCTET STRING
    MAX-ACCESS  read-only
    STATUS      current
    DESCRIPTION
"
next Upload Global-White
"
     ::= {scheduleInformation 14}
nextHashFileCheck     OBJECT-TYPE
    SYNTAX      OCTET STRING
    MAX-ACCESS  read-only
    STATUS      current
    DESCRIPTION
"
next Check for Optionfiles
"
     ::= {scheduleInformation 15}
nextLDAPcrossCheck     OBJECT-TYPE
    SYNTAX      OCTET STRING
    MAX-ACCESS  read-only
    STATUS      current
    DESCRIPTION
"
next LDAP-cross-Check
"
     ::= {scheduleInformation 16}
nextRebuildSpamDB     OBJECT-TYPE
    SYNTAX      OCTET STRING
    MAX-ACCESS  read-only
    STATUS      current
    DESCRIPTION
"
next RebuildSpamDB (not scheduled)
"
     ::= {scheduleInformation 17}
nextResendMail      OBJECT-TYPE
    SYNTAX      OCTET STRING
    MAX-ACCESS  read-only
    STATUS      current
    DESCRIPTION
"
next ResendMail
"
     ::= {scheduleInformation 18}
nextasspFileDownload     OBJECT-TYPE
    SYNTAX      OCTET STRING
    MAX-ACCESS  read-only
    STATUS      current
    DESCRIPTION
"
next Download of assp.gz for autoupdate
"
     ::= {scheduleInformation 19}
nextVersionFileDownload     OBJECT-TYPE
    SYNTAX      OCTET STRING
    MAX-ACCESS  read-only
    STATUS      current
    DESCRIPTION
"
next Download of version.txt for check of ne available assp version
"
     ::= {scheduleInformation 20}
nextBackDNSFileDownload    OBJECT-TYPE
    SYNTAX      OCTET STRING
    MAX-ACCESS  read-only
    STATUS      current
    DESCRIPTION
"
next BackDNSFile Download
"
     ::= {scheduleInformation 21}
nextCodeChangeCheck      OBJECT-TYPE
    SYNTAX      OCTET STRING
    MAX-ACCESS  read-only
    STATUS      current
    DESCRIPTION
"
next Check for changed Code
"
     ::= {scheduleInformation 22}
nextDroplistDownload     OBJECT-TYPE
    SYNTAX      OCTET STRING
    MAX-ACCESS  read-only
    STATUS      current
    DESCRIPTION
"
next Droplist Download
"
     ::= {scheduleInformation 23}
nextGriplistDownload     OBJECT-TYPE
    SYNTAX      OCTET STRING
    MAX-ACCESS  read-only
    STATUS      current
    DESCRIPTION
"
next Griplist Download
"
     ::= {scheduleInformation 24}
nextPOP3Collect     OBJECT-TYPE
    SYNTAX      OCTET STRING
    MAX-ACCESS  read-only
    STATUS      current
    DESCRIPTION
"
next POP3Collect will start at
"
     ::= {scheduleInformation 25}
nextSaveStats     OBJECT-TYPE
    SYNTAX      OCTET STRING
    MAX-ACCESS  read-only
    STATUS      current
    DESCRIPTION
"
next SaveStats
"
     ::= {scheduleInformation 26}
nextTLDlistDownload     OBJECT-TYPE
    SYNTAX      OCTET STRING
    MAX-ACCESS  read-only
    STATUS      current
    DESCRIPTION
"
next TLDlist Download
"
     ::= {scheduleInformation 27}
nextSyncConfig     OBJECT-TYPE
    SYNTAX      OCTET STRING
    MAX-ACCESS  read-only
    STATUS      current
    DESCRIPTION
"
next synchronization check for the config values
"
     ::= {scheduleInformation 28}
nextGroupsReload     OBJECT-TYPE
    SYNTAX      OCTET STRING
    MAX-ACCESS  read-only
    STATUS      current
    DESCRIPTION
"
next Groups File reload
"
     ::= {scheduleInformation 29}
nextBlockReportSchedule     OBJECT-TYPE
    SYNTAX      OCTET STRING
    MAX-ACCESS  read-only
    STATUS      current
    DESCRIPTION
"
next BlockReport Schedule
"
     ::= {scheduleInformation 30}
nextFileAgeSchedule     OBJECT-TYPE
    SYNTAX      OCTET STRING
    MAX-ACCESS  read-only
    STATUS      current
    DESCRIPTION
"
next File Age Schedule
"
     ::= {scheduleInformation 31}
nextQueueSchedule     OBJECT-TYPE
    SYNTAX      OCTET STRING
    MAX-ACCESS  read-only
    STATUS      current
    DESCRIPTION
"
next BlockReport Queue Schedule
"
     ::= {scheduleInformation 32}

workerStatus              OBJECT IDENTIFIER ::= {asspRunTimeInfo 30}
databaseStatus              OBJECT IDENTIFIER ::= {asspRunTimeInfo 31}

workerHealthy1  OBJECT-TYPE
    SYNTAX      TruthValue
    MAX-ACCESS  read-only
    STATUS      current
    DESCRIPTION
"
healthy Status of Worker-1
"
    ::= {workerStatus 1}

workerLastLoop1  OBJECT-TYPE
    SYNTAX      OCTET STRING
    MAX-ACCESS  read-only
    STATUS      current
    DESCRIPTION
"
time since last loop in Worker-1
"
    ::= {workerStatus 1 1}

workerLastAction1  OBJECT-TYPE
    SYNTAX      OCTET STRING
    MAX-ACCESS  read-only
    STATUS      current
    DESCRIPTION
"
last registered action of Worker-1
"
    ::= {workerStatus 1 2}

workerHealthy2  OBJECT-TYPE
    SYNTAX      TruthValue
    MAX-ACCESS  read-only
    STATUS      current
    DESCRIPTION
"
healthy Status of Worker-2
"
    ::= {workerStatus 2}

workerLastLoop2  OBJECT-TYPE
    SYNTAX      OCTET STRING
    MAX-ACCESS  read-only
    STATUS      current
    DESCRIPTION
"
time since last loop in Worker-2
"
    ::= {workerStatus 2 1}

workerLastAction2  OBJECT-TYPE
    SYNTAX      OCTET STRING
    MAX-ACCESS  read-only
    STATUS      current
    DESCRIPTION
"
last registered action of Worker-2
"
    ::= {workerStatus 2 2}

workerHealthy3  OBJECT-TYPE
    SYNTAX      TruthValue
    MAX-ACCESS  read-only
    STATUS      current
    DESCRIPTION
"
healthy Status of Worker-3
"
    ::= {workerStatus 3}

workerLastLoop3  OBJECT-TYPE
    SYNTAX      OCTET STRING
    MAX-ACCESS  read-only
    STATUS      current
    DESCRIPTION
"
time since last loop in Worker-3
"
    ::= {workerStatus 3 1}

workerLastAction3  OBJECT-TYPE
    SYNTAX      OCTET STRING
    MAX-ACCESS  read-only
    STATUS      current
    DESCRIPTION
"
last registered action of Worker-3
"
    ::= {workerStatus 3 2}

workerHealthy4  OBJECT-TYPE
    SYNTAX      TruthValue
    MAX-ACCESS  read-only
    STATUS      current
    DESCRIPTION
"
healthy Status of Worker-4
"
    ::= {workerStatus 4}

workerLastLoop4  OBJECT-TYPE
    SYNTAX      OCTET STRING
    MAX-ACCESS  read-only
    STATUS      current
    DESCRIPTION
"
time since last loop in Worker-4
"
    ::= {workerStatus 4 1}

workerLastAction4  OBJECT-TYPE
    SYNTAX      OCTET STRING
    MAX-ACCESS  read-only
    STATUS      current
    DESCRIPTION
"
last registered action of Worker-4
"
    ::= {workerStatus 4 2}

workerHealthy5  OBJECT-TYPE
    SYNTAX      TruthValue
    MAX-ACCESS  read-only
    STATUS      current
    DESCRIPTION
"
healthy Status of Worker-5
"
    ::= {workerStatus 5}

workerLastLoop5  OBJECT-TYPE
    SYNTAX      OCTET STRING
    MAX-ACCESS  read-only
    STATUS      current
    DESCRIPTION
"
time since last loop in Worker-5
"
    ::= {workerStatus 5 1}

workerLastAction5  OBJECT-TYPE
    SYNTAX      OCTET STRING
    MAX-ACCESS  read-only
    STATUS      current
    DESCRIPTION
"
last registered action of Worker-5
"
    ::= {workerStatus 5 2}

workerHealthy6  OBJECT-TYPE
    SYNTAX      TruthValue
    MAX-ACCESS  read-only
    STATUS      current
    DESCRIPTION
"
healthy Status of Worker-6
"
    ::= {workerStatus 6}

workerLastLoop6  OBJECT-TYPE
    SYNTAX      OCTET STRING
    MAX-ACCESS  read-only
    STATUS      current
    DESCRIPTION
"
time since last loop in Worker-6
"
    ::= {workerStatus 6 1}

workerLastAction6  OBJECT-TYPE
    SYNTAX      OCTET STRING
    MAX-ACCESS  read-only
    STATUS      current
    DESCRIPTION
"
last registered action of Worker-6
"
    ::= {workerStatus 6 2}

workerHealthy7  OBJECT-TYPE
    SYNTAX      TruthValue
    MAX-ACCESS  read-only
    STATUS      current
    DESCRIPTION
"
healthy Status of Worker-7
"
    ::= {workerStatus 7}

workerLastLoop7  OBJECT-TYPE
    SYNTAX      OCTET STRING
    MAX-ACCESS  read-only
    STATUS      current
    DESCRIPTION
"
time since last loop in Worker-7
"
    ::= {workerStatus 7 1}

workerLastAction7  OBJECT-TYPE
    SYNTAX      OCTET STRING
    MAX-ACCESS  read-only
    STATUS      current
    DESCRIPTION
"
last registered action of Worker-7
"
    ::= {workerStatus 7 2}

workerHealthy8  OBJECT-TYPE
    SYNTAX      TruthValue
    MAX-ACCESS  read-only
    STATUS      current
    DESCRIPTION
"
healthy Status of Worker-8
"
    ::= {workerStatus 8}

workerLastLoop8  OBJECT-TYPE
    SYNTAX      OCTET STRING
    MAX-ACCESS  read-only
    STATUS      current
    DESCRIPTION
"
time since last loop in Worker-8
"
    ::= {workerStatus 8 1}

workerLastAction8  OBJECT-TYPE
    SYNTAX      OCTET STRING
    MAX-ACCESS  read-only
    STATUS      current
    DESCRIPTION
"
last registered action of Worker-8
"
    ::= {workerStatus 8 2}

workerHealthy9  OBJECT-TYPE
    SYNTAX      TruthValue
    MAX-ACCESS  read-only
    STATUS      current
    DESCRIPTION
"
healthy Status of Worker-9
"
    ::= {workerStatus 9}

workerLastLoop9  OBJECT-TYPE
    SYNTAX      OCTET STRING
    MAX-ACCESS  read-only
    STATUS      current
    DESCRIPTION
"
time since last loop in Worker-9
"
    ::= {workerStatus 9 1}

workerLastAction9  OBJECT-TYPE
    SYNTAX      OCTET STRING
    MAX-ACCESS  read-only
    STATUS      current
    DESCRIPTION
"
last registered action of Worker-9
"
    ::= {workerStatus 9 2}

workerHealthy10  OBJECT-TYPE
    SYNTAX      TruthValue
    MAX-ACCESS  read-only
    STATUS      current
    DESCRIPTION
"
healthy Status of Worker-10
"
    ::= {workerStatus 10}

workerLastLoop10  OBJECT-TYPE
    SYNTAX      OCTET STRING
    MAX-ACCESS  read-only
    STATUS      current
    DESCRIPTION
"
time since last loop in Worker-10
"
    ::= {workerStatus 10 1}

workerLastAction10  OBJECT-TYPE
    SYNTAX      OCTET STRING
    MAX-ACCESS  read-only
    STATUS      current
    DESCRIPTION
"
last registered action of Worker-10
"
    ::= {workerStatus 10 2}

workerHealthy11  OBJECT-TYPE
    SYNTAX      TruthValue
    MAX-ACCESS  read-only
    STATUS      current
    DESCRIPTION
"
healthy Status of Worker-11
"
    ::= {workerStatus 11}

workerLastLoop11  OBJECT-TYPE
    SYNTAX      OCTET STRING
    MAX-ACCESS  read-only
    STATUS      current
    DESCRIPTION
"
time since last loop in Worker-11
"
    ::= {workerStatus 11 1}

workerLastAction11  OBJECT-TYPE
    SYNTAX      OCTET STRING
    MAX-ACCESS  read-only
    STATUS      current
    DESCRIPTION
"
last registered action of Worker-11
"
    ::= {workerStatus 11 2}

workerHealthy12  OBJECT-TYPE
    SYNTAX      TruthValue
    MAX-ACCESS  read-only
    STATUS      current
    DESCRIPTION
"
healthy Status of Worker-12
"
    ::= {workerStatus 12}

workerLastLoop12  OBJECT-TYPE
    SYNTAX      OCTET STRING
    MAX-ACCESS  read-only
    STATUS      current
    DESCRIPTION
"
time since last loop in Worker-12
"
    ::= {workerStatus 12 1}

workerLastAction12  OBJECT-TYPE
    SYNTAX      OCTET STRING
    MAX-ACCESS  read-only
    STATUS      current
    DESCRIPTION
"
last registered action of Worker-12
"
    ::= {workerStatus 12 2}

workerHealthy13  OBJECT-TYPE
    SYNTAX      TruthValue
    MAX-ACCESS  read-only
    STATUS      current
    DESCRIPTION
"
healthy Status of Worker-13
"
    ::= {workerStatus 13}

workerLastLoop13  OBJECT-TYPE
    SYNTAX      OCTET STRING
    MAX-ACCESS  read-only
    STATUS      current
    DESCRIPTION
"
time since last loop in Worker-13
"
    ::= {workerStatus 13 1}

workerLastAction13  OBJECT-TYPE
    SYNTAX      OCTET STRING
    MAX-ACCESS  read-only
    STATUS      current
    DESCRIPTION
"
last registered action of Worker-13
"
    ::= {workerStatus 13 2}

workerHealthy14  OBJECT-TYPE
    SYNTAX      TruthValue
    MAX-ACCESS  read-only
    STATUS      current
    DESCRIPTION
"
healthy Status of Worker-14
"
    ::= {workerStatus 14}

workerLastLoop14  OBJECT-TYPE
    SYNTAX      OCTET STRING
    MAX-ACCESS  read-only
    STATUS      current
    DESCRIPTION
"
time since last loop in Worker-14
"
    ::= {workerStatus 14 1}

workerLastAction14  OBJECT-TYPE
    SYNTAX      OCTET STRING
    MAX-ACCESS  read-only
    STATUS      current
    DESCRIPTION
"
last registered action of Worker-14
"
    ::= {workerStatus 14 2}

workerHealthy15  OBJECT-TYPE
    SYNTAX      TruthValue
    MAX-ACCESS  read-only
    STATUS      current
    DESCRIPTION
"
healthy Status of Worker-15
"
    ::= {workerStatus 15}

workerLastLoop15  OBJECT-TYPE
    SYNTAX      OCTET STRING
    MAX-ACCESS  read-only
    STATUS      current
    DESCRIPTION
"
time since last loop in Worker-15
"
    ::= {workerStatus 15 1}

workerLastAction15  OBJECT-TYPE
    SYNTAX      OCTET STRING
    MAX-ACCESS  read-only
    STATUS      current
    DESCRIPTION
"
last registered action of Worker-15
"
    ::= {workerStatus 15 2}

workerHealthy16  OBJECT-TYPE
    SYNTAX      TruthValue
    MAX-ACCESS  read-only
    STATUS      current
    DESCRIPTION
"
healthy Status of Worker-16
"
    ::= {workerStatus 16}

workerLastLoop16  OBJECT-TYPE
    SYNTAX      OCTET STRING
    MAX-ACCESS  read-only
    STATUS      current
    DESCRIPTION
"
time since last loop in Worker-16
"
    ::= {workerStatus 16 1}

workerLastAction16  OBJECT-TYPE
    SYNTAX      OCTET STRING
    MAX-ACCESS  read-only
    STATUS      current
    DESCRIPTION
"
last registered action of Worker-16
"
    ::= {workerStatus 16 2}

workerHealthy17  OBJECT-TYPE
    SYNTAX      TruthValue
    MAX-ACCESS  read-only
    STATUS      current
    DESCRIPTION
"
healthy Status of Worker-17
"
    ::= {workerStatus 17}

workerLastLoop17  OBJECT-TYPE
    SYNTAX      OCTET STRING
    MAX-ACCESS  read-only
    STATUS      current
    DESCRIPTION
"
time since last loop in Worker-17
"
    ::= {workerStatus 17 1}

workerLastAction17  OBJECT-TYPE
    SYNTAX      OCTET STRING
    MAX-ACCESS  read-only
    STATUS      current
    DESCRIPTION
"
last registered action of Worker-17
"
    ::= {workerStatus 17 2}

workerHealthy18  OBJECT-TYPE
    SYNTAX      TruthValue
    MAX-ACCESS  read-only
    STATUS      current
    DESCRIPTION
"
healthy Status of Worker-18
"
    ::= {workerStatus 18}

workerLastLoop18  OBJECT-TYPE
    SYNTAX      OCTET STRING
    MAX-ACCESS  read-only
    STATUS      current
    DESCRIPTION
"
time since last loop in Worker-18
"
    ::= {workerStatus 18 1}

workerLastAction18  OBJECT-TYPE
    SYNTAX      OCTET STRING
    MAX-ACCESS  read-only
    STATUS      current
    DESCRIPTION
"
last registered action of Worker-18
"
    ::= {workerStatus 18 2}

workerHealthy19  OBJECT-TYPE
    SYNTAX      TruthValue
    MAX-ACCESS  read-only
    STATUS      current
    DESCRIPTION
"
healthy Status of Worker-19
"
    ::= {workerStatus 19}

workerLastLoop19  OBJECT-TYPE
    SYNTAX      OCTET STRING
    MAX-ACCESS  read-only
    STATUS      current
    DESCRIPTION
"
time since last loop in Worker-19
"
    ::= {workerStatus 19 1}

workerLastAction19  OBJECT-TYPE
    SYNTAX      OCTET STRING
    MAX-ACCESS  read-only
    STATUS      current
    DESCRIPTION
"
last registered action of Worker-19
"
    ::= {workerStatus 19 2}

workerHealthy20  OBJECT-TYPE
    SYNTAX      TruthValue
    MAX-ACCESS  read-only
    STATUS      current
    DESCRIPTION
"
healthy Status of Worker-20
"
    ::= {workerStatus 20}

workerLastLoop20  OBJECT-TYPE
    SYNTAX      OCTET STRING
    MAX-ACCESS  read-only
    STATUS      current
    DESCRIPTION
"
time since last loop in Worker-20
"
    ::= {workerStatus 20 1}

workerLastAction20  OBJECT-TYPE
    SYNTAX      OCTET STRING
    MAX-ACCESS  read-only
    STATUS      current
    DESCRIPTION
"
last registered action of Worker-20
"
    ::= {workerStatus 20 2}

workerHealthy21  OBJECT-TYPE
    SYNTAX      TruthValue
    MAX-ACCESS  read-only
    STATUS      current
    DESCRIPTION
"
healthy Status of Worker-21
"
    ::= {workerStatus 21}

workerLastLoop21  OBJECT-TYPE
    SYNTAX      OCTET STRING
    MAX-ACCESS  read-only
    STATUS      current
    DESCRIPTION
"
time since last loop in Worker-21
"
    ::= {workerStatus 21 1}

workerLastAction21  OBJECT-TYPE
    SYNTAX      OCTET STRING
    MAX-ACCESS  read-only
    STATUS      current
    DESCRIPTION
"
last registered action of Worker-21
"
    ::= {workerStatus 21 2}

workerHealthy22  OBJECT-TYPE
    SYNTAX      TruthValue
    MAX-ACCESS  read-only
    STATUS      current
    DESCRIPTION
"
healthy Status of Worker-22
"
    ::= {workerStatus 22}

workerLastLoop22  OBJECT-TYPE
    SYNTAX      OCTET STRING
    MAX-ACCESS  read-only
    STATUS      current
    DESCRIPTION
"
time since last loop in Worker-22
"
    ::= {workerStatus 22 1}

workerLastAction22  OBJECT-TYPE
    SYNTAX      OCTET STRING
    MAX-ACCESS  read-only
    STATUS      current
    DESCRIPTION
"
last registered action of Worker-22
"
    ::= {workerStatus 22 2}

workerHealthy23  OBJECT-TYPE
    SYNTAX      TruthValue
    MAX-ACCESS  read-only
    STATUS      current
    DESCRIPTION
"
healthy Status of Worker-23
"
    ::= {workerStatus 23}

workerLastLoop23  OBJECT-TYPE
    SYNTAX      OCTET STRING
    MAX-ACCESS  read-only
    STATUS      current
    DESCRIPTION
"
time since last loop in Worker-23
"
    ::= {workerStatus 23 1}

workerLastAction23  OBJECT-TYPE
    SYNTAX      OCTET STRING
    MAX-ACCESS  read-only
    STATUS      current
    DESCRIPTION
"
last registered action of Worker-23
"
    ::= {workerStatus 23 2}

workerHealthy24  OBJECT-TYPE
    SYNTAX      TruthValue
    MAX-ACCESS  read-only
    STATUS      current
    DESCRIPTION
"
healthy Status of Worker-24
"
    ::= {workerStatus 24}

workerLastLoop24  OBJECT-TYPE
    SYNTAX      OCTET STRING
    MAX-ACCESS  read-only
    STATUS      current
    DESCRIPTION
"
time since last loop in Worker-24
"
    ::= {workerStatus 24 1}

workerLastAction24  OBJECT-TYPE
    SYNTAX      OCTET STRING
    MAX-ACCESS  read-only
    STATUS      current
    DESCRIPTION
"
last registered action of Worker-24
"
    ::= {workerStatus 24 2}

workerHealthy25  OBJECT-TYPE
    SYNTAX      TruthValue
    MAX-ACCESS  read-only
    STATUS      current
    DESCRIPTION
"
healthy Status of Worker-25
"
    ::= {workerStatus 25}

workerLastLoop25  OBJECT-TYPE
    SYNTAX      OCTET STRING
    MAX-ACCESS  read-only
    STATUS      current
    DESCRIPTION
"
time since last loop in Worker-25
"
    ::= {workerStatus 25 1}

workerLastAction25  OBJECT-TYPE
    SYNTAX      OCTET STRING
    MAX-ACCESS  read-only
    STATUS      current
    DESCRIPTION
"
last registered action of Worker-25
"
    ::= {workerStatus 25 2}

workerHealthy26  OBJECT-TYPE
    SYNTAX      TruthValue
    MAX-ACCESS  read-only
    STATUS      current
    DESCRIPTION
"
healthy Status of Worker-26
"
    ::= {workerStatus 26}

workerLastLoop26  OBJECT-TYPE
    SYNTAX      OCTET STRING
    MAX-ACCESS  read-only
    STATUS      current
    DESCRIPTION
"
time since last loop in Worker-26
"
    ::= {workerStatus 26 1}

workerLastAction26  OBJECT-TYPE
    SYNTAX      OCTET STRING
    MAX-ACCESS  read-only
    STATUS      current
    DESCRIPTION
"
last registered action of Worker-26
"
    ::= {workerStatus 26 2}

workerHealthy27  OBJECT-TYPE
    SYNTAX      TruthValue
    MAX-ACCESS  read-only
    STATUS      current
    DESCRIPTION
"
healthy Status of Worker-27
"
    ::= {workerStatus 27}

workerLastLoop27  OBJECT-TYPE
    SYNTAX      OCTET STRING
    MAX-ACCESS  read-only
    STATUS      current
    DESCRIPTION
"
time since last loop in Worker-27
"
    ::= {workerStatus 27 1}

workerLastAction27  OBJECT-TYPE
    SYNTAX      OCTET STRING
    MAX-ACCESS  read-only
    STATUS      current
    DESCRIPTION
"
last registered action of Worker-27
"
    ::= {workerStatus 27 2}

workerHealthy28  OBJECT-TYPE
    SYNTAX      TruthValue
    MAX-ACCESS  read-only
    STATUS      current
    DESCRIPTION
"
healthy Status of Worker-28
"
    ::= {workerStatus 28}

workerLastLoop28  OBJECT-TYPE
    SYNTAX      OCTET STRING
    MAX-ACCESS  read-only
    STATUS      current
    DESCRIPTION
"
time since last loop in Worker-28
"
    ::= {workerStatus 28 1}

workerLastAction28  OBJECT-TYPE
    SYNTAX      OCTET STRING
    MAX-ACCESS  read-only
    STATUS      current
    DESCRIPTION
"
last registered action of Worker-28
"
    ::= {workerStatus 28 2}

workerHealthy29  OBJECT-TYPE
    SYNTAX      TruthValue
    MAX-ACCESS  read-only
    STATUS      current
    DESCRIPTION
"
healthy Status of Worker-29
"
    ::= {workerStatus 29}

workerLastLoop29  OBJECT-TYPE
    SYNTAX      OCTET STRING
    MAX-ACCESS  read-only
    STATUS      current
    DESCRIPTION
"
time since last loop in Worker-29
"
    ::= {workerStatus 29 1}

workerLastAction29  OBJECT-TYPE
    SYNTAX      OCTET STRING
    MAX-ACCESS  read-only
    STATUS      current
    DESCRIPTION
"
last registered action of Worker-29
"
    ::= {workerStatus 29 2}

workerHealthy30  OBJECT-TYPE
    SYNTAX      TruthValue
    MAX-ACCESS  read-only
    STATUS      current
    DESCRIPTION
"
healthy Status of Worker-30
"
    ::= {workerStatus 30}

workerLastLoop30  OBJECT-TYPE
    SYNTAX      OCTET STRING
    MAX-ACCESS  read-only
    STATUS      current
    DESCRIPTION
"
time since last loop in Worker-30
"
    ::= {workerStatus 30 1}

workerLastAction30  OBJECT-TYPE
    SYNTAX      OCTET STRING
    MAX-ACCESS  read-only
    STATUS      current
    DESCRIPTION
"
last registered action of Worker-30
"
    ::= {workerStatus 30 2}

workerHealthy31  OBJECT-TYPE
    SYNTAX      TruthValue
    MAX-ACCESS  read-only
    STATUS      current
    DESCRIPTION
"
healthy Status of Worker-31
"
    ::= {workerStatus 31}

workerLastLoop31  OBJECT-TYPE
    SYNTAX      OCTET STRING
    MAX-ACCESS  read-only
    STATUS      current
    DESCRIPTION
"
time since last loop in Worker-31
"
    ::= {workerStatus 31 1}

workerLastAction31  OBJECT-TYPE
    SYNTAX      OCTET STRING
    MAX-ACCESS  read-only
    STATUS      current
    DESCRIPTION
"
last registered action of Worker-31
"
    ::= {workerStatus 31 2}

workerHealthy32  OBJECT-TYPE
    SYNTAX      TruthValue
    MAX-ACCESS  read-only
    STATUS      current
    DESCRIPTION
"
healthy Status of Worker-32
"
    ::= {workerStatus 32}

workerLastLoop32  OBJECT-TYPE
    SYNTAX      OCTET STRING
    MAX-ACCESS  read-only
    STATUS      current
    DESCRIPTION
"
time since last loop in Worker-32
"
    ::= {workerStatus 32 1}

workerLastAction32  OBJECT-TYPE
    SYNTAX      OCTET STRING
    MAX-ACCESS  read-only
    STATUS      current
    DESCRIPTION
"
last registered action of Worker-32
"
    ::= {workerStatus 32 2}

workerHealthy33  OBJECT-TYPE
    SYNTAX      TruthValue
    MAX-ACCESS  read-only
    STATUS      current
    DESCRIPTION
"
healthy Status of Worker-33
"
    ::= {workerStatus 33}

workerLastLoop33  OBJECT-TYPE
    SYNTAX      OCTET STRING
    MAX-ACCESS  read-only
    STATUS      current
    DESCRIPTION
"
time since last loop in Worker-33
"
    ::= {workerStatus 33 1}

workerLastAction33  OBJECT-TYPE
    SYNTAX      OCTET STRING
    MAX-ACCESS  read-only
    STATUS      current
    DESCRIPTION
"
last registered action of Worker-33
"
    ::= {workerStatus 33 2}

workerHealthy10000  OBJECT-TYPE
    SYNTAX      TruthValue
    MAX-ACCESS  read-only
    STATUS      current
    DESCRIPTION
"
healthy Status of Worker-10000
"
    ::= {workerStatus 10000}

workerLastLoop10000  OBJECT-TYPE
    SYNTAX      OCTET STRING
    MAX-ACCESS  read-only
    STATUS      current
    DESCRIPTION
"
time since last loop in Worker-10000
"
    ::= {workerStatus 10000 1}

workerLastAction10000  OBJECT-TYPE
    SYNTAX      OCTET STRING
    MAX-ACCESS  read-only
    STATUS      current
    DESCRIPTION
"
last registered action of Worker-10000
"
    ::= {workerStatus 10000 2}

workerHealthy10001  OBJECT-TYPE
    SYNTAX      TruthValue
    MAX-ACCESS  read-only
    STATUS      current
    DESCRIPTION
"
healthy Status of Worker-10001
"
    ::= {workerStatus 10001}

workerLastLoop10001  OBJECT-TYPE
    SYNTAX      OCTET STRING
    MAX-ACCESS  read-only
    STATUS      current
    DESCRIPTION
"
time since last loop in Worker-10001
"
    ::= {workerStatus 10001 1}

workerLastAction10001  OBJECT-TYPE
    SYNTAX      OCTET STRING
    MAX-ACCESS  read-only
    STATUS      current
    DESCRIPTION
"
last registered action of Worker-10001
"
    ::= {workerStatus 10001 2}

generalDatabaseStatus  OBJECT-TYPE
    SYNTAX      TruthValue
    MAX-ACCESS  read-only
    STATUS      current
    DESCRIPTION
"
general database status
"
    ::= {databaseStatus 0}

generalDatabaseStatusText  OBJECT-TYPE
    SYNTAX      OCTET STRING
    MAX-ACCESS  read-only
    STATUS      current
    DESCRIPTION
"
general database status as text
"
    ::= {databaseStatus 0 1}

dbStatusRBLCache  OBJECT-TYPE
    SYNTAX      TruthValue
    MAX-ACCESS  read-only
    STATUS      current
    DESCRIPTION
"
database status of table RBLCache
"
    ::= {databaseStatus 1}

databaseTableNameRBLCache  OBJECT-TYPE
    SYNTAX      OCTET STRING
    MAX-ACCESS  read-only
    STATUS      current
    DESCRIPTION
"
database RBLCache table name
"
    ::= {databaseStatus 1 1}

dbStatusPBWhite  OBJECT-TYPE
    SYNTAX      TruthValue
    MAX-ACCESS  read-only
    STATUS      current
    DESCRIPTION
"
database status of table PBWhite
"
    ::= {databaseStatus 2}

databaseTableNamePBWhite  OBJECT-TYPE
    SYNTAX      OCTET STRING
    MAX-ACCESS  read-only
    STATUS      current
    DESCRIPTION
"
database PBWhite table name
"
    ::= {databaseStatus 2 1}

dbStatusPBTrap  OBJECT-TYPE
    SYNTAX      TruthValue
    MAX-ACCESS  read-only
    STATUS      current
    DESCRIPTION
"
database status of table PBTrap
"
    ::= {databaseStatus 3}

databaseTableNamePBTrap  OBJECT-TYPE
    SYNTAX      OCTET STRING
    MAX-ACCESS  read-only
    STATUS      current
    DESCRIPTION
"
database PBTrap table name
"
    ::= {databaseStatus 3 1}

dbStatusURIBLCache  OBJECT-TYPE
    SYNTAX      TruthValue
    MAX-ACCESS  read-only
    STATUS      current
    DESCRIPTION
"
database status of table URIBLCache
"
    ::= {databaseStatus 4}

databaseTableNameURIBLCache  OBJECT-TYPE
    SYNTAX      OCTET STRING
    MAX-ACCESS  read-only
    STATUS      current
    DESCRIPTION
"
database URIBLCache table name
"
    ::= {databaseStatus 4 1}

dbStatusMXACache  OBJECT-TYPE
    SYNTAX      TruthValue
    MAX-ACCESS  read-only
    STATUS      current
    DESCRIPTION
"
database status of table MXACache
"
    ::= {databaseStatus 5}

databaseTableNameMXACache  OBJECT-TYPE
    SYNTAX      OCTET STRING
    MAX-ACCESS  read-only
    STATUS      current
    DESCRIPTION
"
database MXACache table name
"
    ::= {databaseStatus 5 1}

dbStatusLDAPlist  OBJECT-TYPE
    SYNTAX      TruthValue
    MAX-ACCESS  read-only
    STATUS      current
    DESCRIPTION
"
database status of table LDAPlist
"
    ::= {databaseStatus 6}

databaseTableNameLDAPlist  OBJECT-TYPE
    SYNTAX      OCTET STRING
    MAX-ACCESS  read-only
    STATUS      current
    DESCRIPTION
"
database LDAPlist table name
"
    ::= {databaseStatus 6 1}

dbStatusRWLCache  OBJECT-TYPE
    SYNTAX      TruthValue
    MAX-ACCESS  read-only
    STATUS      current
    DESCRIPTION
"
database status of table RWLCache
"
    ::= {databaseStatus 7}

databaseTableNameRWLCache  OBJECT-TYPE
    SYNTAX      OCTET STRING
    MAX-ACCESS  read-only
    STATUS      current
    DESCRIPTION
"
database RWLCache table name
"
    ::= {databaseStatus 7 1}

dbStatusBackDNS  OBJECT-TYPE
    SYNTAX      TruthValue
    MAX-ACCESS  read-only
    STATUS      current
    DESCRIPTION
"
database status of table BackDNS
"
    ::= {databaseStatus 8}

databaseTableNameBackDNS  OBJECT-TYPE
    SYNTAX      OCTET STRING
    MAX-ACCESS  read-only
    STATUS      current
    DESCRIPTION
"
database BackDNS table name
"
    ::= {databaseStatus 8 1}

dbStatusPTRCache  OBJECT-TYPE
    SYNTAX      TruthValue
    MAX-ACCESS  read-only
    STATUS      current
    DESCRIPTION
"
database status of table PTRCache
"
    ::= {databaseStatus 9}

databaseTableNamePTRCache  OBJECT-TYPE
    SYNTAX      OCTET STRING
    MAX-ACCESS  read-only
    STATUS      current
    DESCRIPTION
"
database PTRCache table name
"
    ::= {databaseStatus 9 1}

dbStatusAdminUsersRight  OBJECT-TYPE
    SYNTAX      TruthValue
    MAX-ACCESS  read-only
    STATUS      current
    DESCRIPTION
"
database status of table AdminUsersRight
"
    ::= {databaseStatus 10}

databaseTableNameAdminUsersRight  OBJECT-TYPE
    SYNTAX      OCTET STRING
    MAX-ACCESS  read-only
    STATUS      current
    DESCRIPTION
"
database AdminUsersRight table name
"
    ::= {databaseStatus 10 1}

dbStatusHMMdb  OBJECT-TYPE
    SYNTAX      TruthValue
    MAX-ACCESS  read-only
    STATUS      current
    DESCRIPTION
"
database status of table HMMdb
"
    ::= {databaseStatus 11}

databaseTableNameHMMdb  OBJECT-TYPE
    SYNTAX      OCTET STRING
    MAX-ACCESS  read-only
    STATUS      current
    DESCRIPTION
"
database HMMdb table name
"
    ::= {databaseStatus 11 1}

dbStatusPersBlack  OBJECT-TYPE
    SYNTAX      TruthValue
    MAX-ACCESS  read-only
    STATUS      current
    DESCRIPTION
"
database status of table PersBlack
"
    ::= {databaseStatus 12}

databaseTableNamePersBlack  OBJECT-TYPE
    SYNTAX      OCTET STRING
    MAX-ACCESS  read-only
    STATUS      current
    DESCRIPTION
"
database PersBlack table name
"
    ::= {databaseStatus 12 1}

dbStatusDKIMCache  OBJECT-TYPE
    SYNTAX      TruthValue
    MAX-ACCESS  read-only
    STATUS      current
    DESCRIPTION
"
database status of table DKIMCache
"
    ::= {databaseStatus 13}

databaseTableNameDKIMCache  OBJECT-TYPE
    SYNTAX      OCTET STRING
    MAX-ACCESS  read-only
    STATUS      current
    DESCRIPTION
"
database DKIMCache table name
"
    ::= {databaseStatus 13 1}

dbStatusBATVTag  OBJECT-TYPE
    SYNTAX      TruthValue
    MAX-ACCESS  read-only
    STATUS      current
    DESCRIPTION
"
database status of table BATVTag
"
    ::= {databaseStatus 14}

databaseTableNameBATVTag  OBJECT-TYPE
    SYNTAX      OCTET STRING
    MAX-ACCESS  read-only
    STATUS      current
    DESCRIPTION
"
database BATVTag table name
"
    ::= {databaseStatus 14 1}

dbStatusDelayWhite  OBJECT-TYPE
    SYNTAX      TruthValue
    MAX-ACCESS  read-only
    STATUS      current
    DESCRIPTION
"
database status of table DelayWhite
"
    ::= {databaseStatus 15}

databaseTableNameDelayWhite  OBJECT-TYPE
    SYNTAX      OCTET STRING
    MAX-ACCESS  read-only
    STATUS      current
    DESCRIPTION
"
database DelayWhite table name
"
    ::= {databaseStatus 15 1}

dbStatusSpamdb  OBJECT-TYPE
    SYNTAX      TruthValue
    MAX-ACCESS  read-only
    STATUS      current
    DESCRIPTION
"
database status of table Spamdb
"
    ::= {databaseStatus 16}

databaseTableNameSpamdb  OBJECT-TYPE
    SYNTAX      OCTET STRING
    MAX-ACCESS  read-only
    STATUS      current
    DESCRIPTION
"
database Spamdb table name
"
    ::= {databaseStatus 16 1}

dbStatusDelay  OBJECT-TYPE
    SYNTAX      TruthValue
    MAX-ACCESS  read-only
    STATUS      current
    DESCRIPTION
"
database status of table Delay
"
    ::= {databaseStatus 17}

databaseTableNameDelay  OBJECT-TYPE
    SYNTAX      OCTET STRING
    MAX-ACCESS  read-only
    STATUS      current
    DESCRIPTION
"
database Delay table name
"
    ::= {databaseStatus 17 1}

dbStatusRedlist  OBJECT-TYPE
    SYNTAX      TruthValue
    MAX-ACCESS  read-only
    STATUS      current
    DESCRIPTION
"
database status of table Redlist
"
    ::= {databaseStatus 18}

databaseTableNameRedlist  OBJECT-TYPE
    SYNTAX      OCTET STRING
    MAX-ACCESS  read-only
    STATUS      current
    DESCRIPTION
"
database Redlist table name
"
    ::= {databaseStatus 18 1}

dbStatusAdminUsers  OBJECT-TYPE
    SYNTAX      TruthValue
    MAX-ACCESS  read-only
    STATUS      current
    DESCRIPTION
"
database status of table AdminUsers
"
    ::= {databaseStatus 19}

databaseTableNameAdminUsers  OBJECT-TYPE
    SYNTAX      OCTET STRING
    MAX-ACCESS  read-only
    STATUS      current
    DESCRIPTION
"
database AdminUsers table name
"
    ::= {databaseStatus 19 1}

dbStatusPBBlack  OBJECT-TYPE
    SYNTAX      TruthValue
    MAX-ACCESS  read-only
    STATUS      current
    DESCRIPTION
"
database status of table PBBlack
"
    ::= {databaseStatus 20}

databaseTableNamePBBlack  OBJECT-TYPE
    SYNTAX      OCTET STRING
    MAX-ACCESS  read-only
    STATUS      current
    DESCRIPTION
"
database PBBlack table name
"
    ::= {databaseStatus 20 1}

dbStatusSPFCache  OBJECT-TYPE
    SYNTAX      TruthValue
    MAX-ACCESS  read-only
    STATUS      current
    DESCRIPTION
"
database status of table SPFCache
"
    ::= {databaseStatus 21}

databaseTableNameSPFCache  OBJECT-TYPE
    SYNTAX      OCTET STRING
    MAX-ACCESS  read-only
    STATUS      current
    DESCRIPTION
"
database SPFCache table name
"
    ::= {databaseStatus 21 1}

dbStatusWhitelist  OBJECT-TYPE
    SYNTAX      TruthValue
    MAX-ACCESS  read-only
    STATUS      current
    DESCRIPTION
"
database status of table Whitelist
"
    ::= {databaseStatus 22}

databaseTableNameWhitelist  OBJECT-TYPE
    SYNTAX      OCTET STRING
    MAX-ACCESS  read-only
    STATUS      current
    DESCRIPTION
"
database Whitelist table name
"
    ::= {databaseStatus 22 1}

dbStatusHeloBlack  OBJECT-TYPE
    SYNTAX      TruthValue
    MAX-ACCESS  read-only
    STATUS      current
    DESCRIPTION
"
database status of table HeloBlack
"
    ::= {databaseStatus 23}

databaseTableNameHeloBlack  OBJECT-TYPE
    SYNTAX      OCTET STRING
    MAX-ACCESS  read-only
    STATUS      current
    DESCRIPTION
"
database HeloBlack table name
"
    ::= {databaseStatus 23 1}

ConfigurationSynchronizationandSharing  OBJECT IDENTIFIER ::= {asspConfig 0}
enableCFGShare  OBJECT-TYPE
    SYNTAX      OCTET STRING
    MAX-ACCESS  read-write
    STATUS      current
    DESCRIPTION
"
Read all positions in this section carefully (multiple times is recommended!!!)!&nbsp;A wrong configuration sequence or wrong configuration values can lead in to a destroyed ASSP configuration!
  If set, the configuration value and option files synchronization will be enabled. This synchronization belong to the configuration values, to the file that is possibly defined in a value and to the include files that are possibly defined in the configured file. If you don't want a specific configuration file or include file to be synchronized (send and receive), write
  # assp-no-sync
  as a comment anywhere in the file. An possible reason could be for example 'localDomains' - if ASSP1 is hosting DOMAIN1 and DOMAIN2 but ASSP2 is hosting only DOMAIN2 - so the entry for DOMAIN2 could be put in a not synchronized include file on ASSP1 and the synchronized main config file contains the entry for DOMAIN1.
  If the configuration of all values in this section is valid, the synchronization status will be shown in the GUI for each config value that is, or could be shared. There are several configuration values, that could not be shared. The list of all shareable values could be found in the distributed file assp_sync.cfg
  For an initial synchronization setup set the following config values in this order: setup syncServer, syncConfigFile, syncTestMode and as last syncCFGPass (leave isShareSlave and isShareMaster off). Use the default (distributed syncConfigFile assp_sync.cfg) file and configure all values to your needs - do this on all peers by removing lines or setting the general sync flag to 0 or 1 (see the description of syncConfigFile ).
  If you have finished this initial setup, enable isShareMaster or isShareSlave - now assp will setup all entries in the configuration file for all sync peers to the configured default values (to 1 if isShareMaster or to 3 if isShareSlave is selected). Do this on all peers. Now you can configure the synchronization behavior for each single configuration value for each peer, if it should differ from the default setup.
  For the initial synchronization, configure only one ASSP installation as master (all others as slave). If the initial synchronization has finished, which will take up to one hour, you can configure all or some assp as master and slave. On the initial master simply switch on isShareSlave. On the inital slaves, switch on isShareMaster and change all values in the sync config file that should be bidirectional shared from 3 to 1. As last action enable enableCFGShare on the SyncSlaves first and then on the SyncMaster.
  After such an initial setup, any changes of the peers (syncServer) will have no effect to the configuration file (syncConfigFile)! To add or remove a sync peer after an initial setup, you have to configure syncServer and you have to edit the sync config file manualy.
  This option can only be enabled, if isShareMaster and/or isShareSlave and syncServer and syncConfigFile and syncCFGPass are configured!
  Because the synchronization is done using a special SMTP protocol (without 'mail from' and 'rcpt to'), this option requires an installed  module in PERL. If you want the sync feature to use a secured connection (using STARTTLS) , DoTLS has to be set to 'do TLS'. This special SMTP protocol is not usable to for any MTA for security reasons, so the 'sync mails' could not be forwarded via any MTA.
  For this reason all sync peers must have a direct or routed TCP connection to each other peer.
  If you build a sync topology with more than two ASSP, please notice, that it is not allowed to build any ring-synchronization. Only a chain-, tree- or star- topology is supported. It is also not allowed to build a sync ring inside any of the three allowed topologies!
  
"
    REFERENCE "Enable Configuration Sharing"
    DEFVAL { "" }
    ::= {ConfigurationSynchronizationandSharing 917}

isShareMaster  OBJECT-TYPE
    SYNTAX      OCTET STRING
    MAX-ACCESS  read-write
    STATUS      current
    DESCRIPTION
"
If selected, ASSP will send configured configuration changes to sync peers.
"
    REFERENCE "This is a Share Master"
    DEFVAL { "" }
    ::= {ConfigurationSynchronizationandSharing 918}

isShareSlave  OBJECT-TYPE
    SYNTAX      OCTET STRING
    MAX-ACCESS  read-write
    STATUS      current
    DESCRIPTION
"
If selected, ASSP will receive configured configuration changes from sync peers. To accept a sync request, every sending peer has to be defined in syncServer - even if there are manualy made entries in the sync config file for a peer.
"
    REFERENCE "This is a Share Slave"
    DEFVAL { "" }
    ::= {ConfigurationSynchronizationandSharing 919}

syncServer  OBJECT-TYPE
    SYNTAX      OCTET STRING
    MAX-ACCESS  read-write
    STATUS      current
    DESCRIPTION
"
Define all configuration sync peers here (to send changes to or to receive changes from). Separate multiple values by '|'. Any value must be a pair of hostname or ip-address and :port, like 10.10.10.10:25 or mypeerhost:125 or mypeerhost.mydomain.com:225. The :port must be defined!
  The target port can be the listenPort , listenPort2 , relayPort or if syncUsesSSL is enabled, it has to be the listenPortSSL of the peer.
"
    REFERENCE "Default Sync Peers"
    DEFVAL { "" }
    ::= {ConfigurationSynchronizationandSharing 920}

syncTestMode  OBJECT-TYPE
    SYNTAX      OCTET STRING
    MAX-ACCESS  read-write
    STATUS      current
    DESCRIPTION
"
If selected, a master (isShareMaster) will process all steps to send configuration changes, but will not realy send the request to the peers. A slave (isShareSlave) will receive all sync requests, but it will not change the configuration values and possibly sent configuration files will be stored at the original location and will get an extension of '.synctest'.
"
    REFERENCE "Test Mode for Config Sync"
    DEFVAL { "" }
    ::= {ConfigurationSynchronizationandSharing 921}

syncConfigFile  OBJECT-TYPE
    SYNTAX      OCTET STRING
    MAX-ACCESS  read-write
    STATUS      current
    DESCRIPTION
"
Define the synchronization configuration file here (default is file:assp_sync.cfg).
 This file holds the configuration and the current status of all synchronized assp configuration values.
 The format of an initial value is:  'varname:=syncflag' - where syncflag could be 0 -not shared and 1 -is shared - for example: HeaderMaxLength:=1 . The syncflag is a general sign, which means, a value of 0 disables the synchronization of the config value for all peers. A value of 1, enables the peer configuration that possibly follows.
 The format after an initial setup is: 'varname:=syncflag,syncServer1=status,syncServer2=status,......'. The 'status' could be one of the following:
 0 - no sync - changes of this value will not be sent to this syncServer - I will ignore all change requests for this value from there
 1 - I am a SyncMaster, the value is still out of sync to this peer and should be synchronized as soon as possible
 2 - I am a SyncMaster, the value is still in sync to this peer - I am also a SyncSlave to this peer (bidirectional sync) if isShareSlave is enabled
 3 - I am not a SyncMaster but a SyncSlave - only this SyncMaster (peer) knows the current sync status to me
 4 - I am a SyncMaster and a SyncSlave (bidirectional sync) - a change of this value was still received from this syncServer (peer) and should not be sent back to this syncServer - this flag will be automaticaly set back to 2 at the next synchronization check
 
"
    REFERENCE "Configuration File for Config Sync*"
    DEFVAL { "file:assp_sync.cfg" }
    ::= {ConfigurationSynchronizationandSharing 922}

syncCFGPass  OBJECT-TYPE
    SYNTAX      OCTET STRING
    MAX-ACCESS  read-write
    STATUS      current
    DESCRIPTION
"
The password that is used and required (additionally to the sending IP address) to identify a valid sync request. This password has to be set equal in all ASSP installations, from where and/or to where the configuration should be synchronized.
  The password must be at least six characters long.
  If you want or need to change this password, first disable enableCFGShare here and on all peers, change the password on all peers, enable enableCFGShare on SyncSlaves then enable enableCFGShare on SyncMasters.
"
    REFERENCE "Config Sync Password"
    DEFVAL { "" }
    ::= {ConfigurationSynchronizationandSharing 923}

syncShowGUIDetails  OBJECT-TYPE
    SYNTAX      OCTET STRING
    MAX-ACCESS  read-write
    STATUS      current
    DESCRIPTION
"
If selected, the detail synchronization status is shown at the top of each configuration parameter like:
  nothing shown - there is no entry defined for this parameter in the syncConfigFile or it is an unsharable parameter
  '(shareable)' - the parameter is shareable but the general sync sign in the syncConfigFile is zero
  '(shared: ...)' - the detail sync status for each sync peer
  If not selected, only different colored bulls are shown at the top of each configuration parameter like:
  nothing shown - no entry in the syncConfigFile or it is an unsharable parameter
  'black bull &bull;</font>' - the parameter is shareable but the general sync sign in the syncConfigFile is zero
  'green bull <font color='green'>&bull;</font>' - the parameter is shared and in sync to each peer
  'red bull <font color='red'>&bull;</font>' - the parameter is shared but it is currently out of sync to at least one peer
  If you move the mouse over the bull, a hint box will show the detail synchronization status. An click on the bull or link will open a sync config dialog box for the single configuration parameter.
  
  
"
    REFERENCE "Show Detail Sync Information in GUI"
    DEFVAL { "" }
    ::= {ConfigurationSynchronizationandSharing 925}

syncUsesSSL  OBJECT-TYPE
    SYNTAX      OCTET STRING
    MAX-ACCESS  read-write
    STATUS      current
    DESCRIPTION
"
If selected, SSL will be used for the transport of the sychronisation requests. In this case the target ip:port of all peers must be its listenPortSSL ! The Perl modules Net::SMTP::SSL and IO::Socket::SSL must be installed and enabled if this option is selected, otherwise all synchronisation requests will fail!
"
    REFERENCE "SSL is used for the Sync SMTP Transport"
    DEFVAL { "" }
    ::= {ConfigurationSynchronizationandSharing 1014}

NetworkSetup  OBJECT IDENTIFIER ::= {asspConfig 1}
DisableSMTPNetworking  OBJECT-TYPE
    SYNTAX      OCTET STRING
    MAX-ACCESS  read-write
    STATUS      current
    DESCRIPTION
"
If selected, ASSP will not answer to new SMTP and Proxy connections on 'listenPort , listenPort2 , listenPortSSL , relayPort and ProxyConf'. Currently existing SMTP and Proxy connections are not affected! Web and Stat connection are also not affected.
"
    REFERENCE "Disable all new SMTP and Proxy Network Connections"
    DEFVAL { "0" }
    ::= {NetworkSetup 1}

listenPort  OBJECT-TYPE
    SYNTAX      OCTET STRING
    MAX-ACCESS  read-write
    STATUS      current
    DESCRIPTION
"
The port number on which ASSP will listen for incoming SMTP connections (normally 25). You can specify both an IP address and port number to limit connections to a specific interface. Separate multiple entries by '|'.Examples: 25, 127.0.0.1:25, 127.0.0.1:25|127.0.0.2:25 
"
    REFERENCE "SMTP Listen Port"
    DEFVAL { "25" }
    ::= {NetworkSetup 2}

syncStatlistenPort  OBJECT-TYPE
    SYNTAX      OCTET STRING
    MAX-ACCESS  read-only
    STATUS      current
    DESCRIPTION
"
synchronization status for listenPort
-1 - listenPort could not be synchronized
 0 - synchronization not configured
 1 - out of sync - running master mode
 2 - in sync - running  mastermode
 3 - in sync - running slave mode
 4 - in sync - running master mode (wait to reach state 2)
"
    ::= {listenPort 5}

syncStatStrlistenPort  OBJECT-TYPE
    SYNTAX      OCTET STRING
    MAX-ACCESS  read-only
    STATUS      current
    DESCRIPTION
"
synchronization status line from file assp_sync.cfg for listenPort
 0 - synchronization not configured
 1 - out of sync - running master mode
 2 - in sync - running  mastermode
 3 - in sync - running slave mode
 4 - in sync - running master mode (wait to reach state 2)
"
    ::= {listenPort 6}

smtpDestination  OBJECT-TYPE
    SYNTAX      OCTET STRING
    MAX-ACCESS  read-write
    STATUS      current
    DESCRIPTION
"
The IP number! and port number of your primary SMTP  (MTA). If multiple servers are listed and the first listed MTA does not respond, each additional MTA will be tried. If only a port number is entered, or the dynamic keyword INBOUND is used with a port number, then the connection will be established to the local IP address on which the connection was received. This is useful when you have several IP addresses with different domains or profiles in your MTA. If INBOUND:PORT is used, ReportingReplies (Analyze,Help,etc and CopyMail will go to 127.0.0.1:PORT or [::1]:PORT. If your needs are different, use smtpReportServer (SMTP Reporting Destination) and sendAllDestination (Copy Spam SMTP Destination). Separate multiple entries by '|'.
  If you need to connect to the SMTP destination host using native SSL, write 'SSL:' in front of the IP/host definition. In this case the Perl module  must be installed and enabled ( useIOSocketSSL ).
  Examples: 125,  127.0.0.1:125, 127.0.0.1:125|127.0.0.5:125|SSL:127.0.0.1:465, INBOUND:125
"
    REFERENCE "SMTP Destination"
    DEFVAL { "125" }
    ::= {NetworkSetup 3}

syncStatsmtpDestination  OBJECT-TYPE
    SYNTAX      OCTET STRING
    MAX-ACCESS  read-only
    STATUS      current
    DESCRIPTION
"
synchronization status for smtpDestination
-1 - smtpDestination could not be synchronized
 0 - synchronization not configured
 1 - out of sync - running master mode
 2 - in sync - running  mastermode
 3 - in sync - running slave mode
 4 - in sync - running master mode (wait to reach state 2)
"
    ::= {smtpDestination 5}

syncStatStrsmtpDestination  OBJECT-TYPE
    SYNTAX      OCTET STRING
    MAX-ACCESS  read-only
    STATUS      current
    DESCRIPTION
"
synchronization status line from file assp_sync.cfg for smtpDestination
 0 - synchronization not configured
 1 - out of sync - running master mode
 2 - in sync - running  mastermode
 3 - in sync - running slave mode
 4 - in sync - running master mode (wait to reach state 2)
"
    ::= {smtpDestination 6}

smtpDestinationRT  OBJECT-TYPE
    SYNTAX      OCTET STRING
    MAX-ACCESS  read-write
    STATUS      current
    DESCRIPTION
"
If INBOUND is used in the SMTP Destination field, the rules specified here are used to route the inbound IP address to a different outbound IP address. You must specify a port number with the outbound IP address. Example:141.120.110.1=>141.120.110.129:25|141.120.110.2=>141.120.110.130:125|141.120.110.3=>SSL:141.120.110.130:125
"
    REFERENCE "SMTP Destination Routing Table*"
    DEFVAL { "" }
    ::= {NetworkSetup 4}

syncStatsmtpDestinationRT  OBJECT-TYPE
    SYNTAX      OCTET STRING
    MAX-ACCESS  read-only
    STATUS      current
    DESCRIPTION
"
synchronization status for smtpDestinationRT
-1 - smtpDestinationRT could not be synchronized
 0 - synchronization not configured
 1 - out of sync - running master mode
 2 - in sync - running  mastermode
 3 - in sync - running slave mode
 4 - in sync - running master mode (wait to reach state 2)
"
    ::= {smtpDestinationRT 5}

syncStatStrsmtpDestinationRT  OBJECT-TYPE
    SYNTAX      OCTET STRING
    MAX-ACCESS  read-only
    STATUS      current
    DESCRIPTION
"
synchronization status line from file assp_sync.cfg for smtpDestinationRT
 0 - synchronization not configured
 1 - out of sync - running master mode
 2 - in sync - running  mastermode
 3 - in sync - running slave mode
 4 - in sync - running master mode (wait to reach state 2)
"
    ::= {smtpDestinationRT 6}

listenPortSSL  OBJECT-TYPE
    SYNTAX      OCTET STRING
    MAX-ACCESS  read-write
    STATUS      current
    DESCRIPTION
"
The port number on which ASSP will listen for incoming secure SMTP connections (normally 465). You can specify both an IP address and port number to limit connections to a specific interface. Separate multiple entries by '|'.Examples: 465, 127.0.0.1:465, 127.0.0.1:465|127.0.0.2:465 . More configuration options are smtpSSLRequireClientCert, SSLSMTPCertVerifyCB and SSLSMTPConfigure .
"
    REFERENCE "SMTP Secure Listen Port"
    DEFVAL { "" }
    ::= {NetworkSetup 5}

syncStatlistenPortSSL  OBJECT-TYPE
    SYNTAX      OCTET STRING
    MAX-ACCESS  read-only
    STATUS      current
    DESCRIPTION
"
synchronization status for listenPortSSL
-1 - listenPortSSL could not be synchronized
 0 - synchronization not configured
 1 - out of sync - running master mode
 2 - in sync - running  mastermode
 3 - in sync - running slave mode
 4 - in sync - running master mode (wait to reach state 2)
"
    ::= {listenPortSSL 5}

syncStatStrlistenPortSSL  OBJECT-TYPE
    SYNTAX      OCTET STRING
    MAX-ACCESS  read-only
    STATUS      current
    DESCRIPTION
"
synchronization status line from file assp_sync.cfg for listenPortSSL
 0 - synchronization not configured
 1 - out of sync - running master mode
 2 - in sync - running  mastermode
 3 - in sync - running slave mode
 4 - in sync - running master mode (wait to reach state 2)
"
    ::= {listenPortSSL 6}

smtpDestinationSSL  OBJECT-TYPE
    SYNTAX      OCTET STRING
    MAX-ACCESS  read-write
    STATUS      current
    DESCRIPTION
"
The IP address! and port number to connect to when mail is received on the SSL listen port. If the field is blank, the primary SMTP destination will be used.
  If you need to connect to the SSL destination host using native SSL, write 'SSL:' in front of the IP/host definition. In this case the Perl module  must be installed and enabled ( useIOSocketSSL ).
  Examples:127.0.0.1:565, 565
"
    REFERENCE "SSL Destination"
    DEFVAL { "" }
    ::= {NetworkSetup 6}

syncStatsmtpDestinationSSL  OBJECT-TYPE
    SYNTAX      OCTET STRING
    MAX-ACCESS  read-only
    STATUS      current
    DESCRIPTION
"
synchronization status for smtpDestinationSSL
-1 - smtpDestinationSSL could not be synchronized
 0 - synchronization not configured
 1 - out of sync - running master mode
 2 - in sync - running  mastermode
 3 - in sync - running slave mode
 4 - in sync - running master mode (wait to reach state 2)
"
    ::= {smtpDestinationSSL 5}

syncStatStrsmtpDestinationSSL  OBJECT-TYPE
    SYNTAX      OCTET STRING
    MAX-ACCESS  read-only
    STATUS      current
    DESCRIPTION
"
synchronization status line from file assp_sync.cfg for smtpDestinationSSL
 0 - synchronization not configured
 1 - out of sync - running master mode
 2 - in sync - running  mastermode
 3 - in sync - running slave mode
 4 - in sync - running master mode (wait to reach state 2)
"
    ::= {smtpDestinationSSL 6}

listenPort2  OBJECT-TYPE
    SYNTAX      OCTET STRING
    MAX-ACCESS  read-write
    STATUS      current
    DESCRIPTION
"
A secondary port number on which ASSP can accept SMTP connections. This is useful as a dedicated port for VPN clients or for those who cannot directly send mail to a mail server outside of their ISP's network because the ISP is blocking port 25. You may also specify an IP address to limit connections to a specific interface. Separate multiple entries by '|'.Examples: 2525, 127.0.0.1:2525, 192.168.0.100:25000
"
    REFERENCE "Second SMTP Listen Port"
    DEFVAL { "" }
    ::= {NetworkSetup 7}

syncStatlistenPort2  OBJECT-TYPE
    SYNTAX      OCTET STRING
    MAX-ACCESS  read-only
    STATUS      current
    DESCRIPTION
"
synchronization status for listenPort2
-1 - listenPort2 could not be synchronized
 0 - synchronization not configured
 1 - out of sync - running master mode
 2 - in sync - running  mastermode
 3 - in sync - running slave mode
 4 - in sync - running master mode (wait to reach state 2)
"
    ::= {listenPort2 5}

syncStatStrlistenPort2  OBJECT-TYPE
    SYNTAX      OCTET STRING
    MAX-ACCESS  read-only
    STATUS      current
    DESCRIPTION
"
synchronization status line from file assp_sync.cfg for listenPort2
 0 - synchronization not configured
 1 - out of sync - running master mode
 2 - in sync - running  mastermode
 3 - in sync - running slave mode
 4 - in sync - running master mode (wait to reach state 2)
"
    ::= {listenPort2 6}

smtpAuthServer  OBJECT-TYPE
    SYNTAX      OCTET STRING
    MAX-ACCESS  read-write
    STATUS      current
    DESCRIPTION
"
The IP address and port number to connect to when mail is received on the second SMTP listen port. If the field is blank, the primary SMTP destination will be used. The purpose of this setting is to allow remote users to make authenticated connections and transmit their email without encountering SPF failures.
  If you need to connect to the second SMTP destination host using native SSL, write 'SSL:' in front of the IP/host definition. In this case the Perl module  must be installed and enabled ( useIOSocketSSL ).
  Examples: 587, 127.0.0.1:587, SSL:127.0.0.1:465
"
    REFERENCE "Second SMTP Destination"
    DEFVAL { "" }
    ::= {NetworkSetup 8}

syncStatsmtpAuthServer  OBJECT-TYPE
    SYNTAX      OCTET STRING
    MAX-ACCESS  read-only
    STATUS      current
    DESCRIPTION
"
synchronization status for smtpAuthServer
-1 - smtpAuthServer could not be synchronized
 0 - synchronization not configured
 1 - out of sync - running master mode
 2 - in sync - running  mastermode
 3 - in sync - running slave mode
 4 - in sync - running master mode (wait to reach state 2)
"
    ::= {smtpAuthServer 5}

syncStatStrsmtpAuthServer  OBJECT-TYPE
    SYNTAX      OCTET STRING
    MAX-ACCESS  read-only
    STATUS      current
    DESCRIPTION
"
synchronization status line from file assp_sync.cfg for smtpAuthServer
 0 - synchronization not configured
 1 - out of sync - running master mode
 2 - in sync - running  mastermode
 3 - in sync - running slave mode
 4 - in sync - running master mode (wait to reach state 2)
"
    ::= {smtpAuthServer 6}

EnforceAuth  OBJECT-TYPE
    SYNTAX      OCTET STRING
    MAX-ACCESS  read-write
    STATUS      current
    DESCRIPTION
"
Force clients connecting to the second listen port to authenticate before transferring mail. To use this setting, both listenPort2 (Second SMTP Listen Port) and smtpAuthServer (Second SMTP Destination) must be configured.
"
    REFERENCE "Force SMTP AUTH on Second SMTP Listen Port"
    DEFVAL { "0" }
    ::= {NetworkSetup 9}

syncStatEnforceAuth  OBJECT-TYPE
    SYNTAX      OCTET STRING
    MAX-ACCESS  read-only
    STATUS      current
    DESCRIPTION
"
synchronization status for EnforceAuth
-1 - EnforceAuth could not be synchronized
 0 - synchronization not configured
 1 - out of sync - running master mode
 2 - in sync - running  mastermode
 3 - in sync - running slave mode
 4 - in sync - running master mode (wait to reach state 2)
"
    ::= {EnforceAuth 5}

syncStatStrEnforceAuth  OBJECT-TYPE
    SYNTAX      OCTET STRING
    MAX-ACCESS  read-only
    STATUS      current
    DESCRIPTION
"
synchronization status line from file assp_sync.cfg for EnforceAuth
 0 - synchronization not configured
 1 - out of sync - running master mode
 2 - in sync - running  mastermode
 3 - in sync - running slave mode
 4 - in sync - running master mode (wait to reach state 2)
"
    ::= {EnforceAuth 6}

NoAUTHlistenPorts  OBJECT-TYPE
    SYNTAX      OCTET STRING
    MAX-ACCESS  read-write
    STATUS      current
    DESCRIPTION
"
This disables the SMTP AUTH command on the defined listenPorts independed from any other setting. This option works for listenPort , listenPort2 and listenPortSSL . The listener definition here has to be the same like in the port definitions. Separate multiple entries by '|'.Examples: 25, 127.0.0.1:25, 127.0.0.1:25|127.0.0.2:25 
"
    REFERENCE "Disable AUTH support on listenPorts"
    DEFVAL { "" }
    ::= {NetworkSetup 806}

syncStatNoAUTHlistenPorts  OBJECT-TYPE
    SYNTAX      OCTET STRING
    MAX-ACCESS  read-only
    STATUS      current
    DESCRIPTION
"
synchronization status for NoAUTHlistenPorts
-1 - NoAUTHlistenPorts could not be synchronized
 0 - synchronization not configured
 1 - out of sync - running master mode
 2 - in sync - running  mastermode
 3 - in sync - running slave mode
 4 - in sync - running master mode (wait to reach state 2)
"
    ::= {NoAUTHlistenPorts 5}

syncStatStrNoAUTHlistenPorts  OBJECT-TYPE
    SYNTAX      OCTET STRING
    MAX-ACCESS  read-only
    STATUS      current
    DESCRIPTION
"
synchronization status line from file assp_sync.cfg for NoAUTHlistenPorts
 0 - synchronization not configured
 1 - out of sync - running master mode
 2 - in sync - running  mastermode
 3 - in sync - running slave mode
 4 - in sync - running master mode (wait to reach state 2)
"
    ::= {NoAUTHlistenPorts 6}

enableINET6  OBJECT-TYPE
    SYNTAX      OCTET STRING
    MAX-ACCESS  read-write
    STATUS      current
    DESCRIPTION
"
For IPv6 network support to be enabled, check this box. Default is disabled. IO::Socket::INET6 is able to handle both IPv4 and IPv6. NOTE: This option requires an installed  module in PERL and your system should support IPv6 sockets to give enableing this option a sense!
  It is recommended to leave this option OFF as long as you don't want to use IPv6 addresses for a listener or a destination (SMTP,DNS-server,LDAP-server etc.).
  Before you enable or disable IPv6, please check every IP listener and destination definition in assp and correct the settings. After changing this option a restart of assp is recommended. IPv4 addresses are defined for example 192.168.0.1 or 192.168.0.1:25 - IPv6 addresses are defined like [FE80:1:0:0:0:0:0:1]:25 or [FE80:1::1]:25 ! If an IPv4 address is defined for a listener, assp will listen only on the IPv4 socket. If an IPv6 address is defined for a listener, assp will listen only on the IPv6 socket. If only a port is defined for a listener, assp will listen on both IPv4 and IPv6 sockets.
  For the definition of destination IP's applies the same. You are free to define hostnames instead of IP addresses like myhost.mydomain.com:25 - how ever, because of the needed IP address resolving, this will possibly slow down assp.
"
    REFERENCE "Enable IPv6 support"
    DEFVAL { "" }
    ::= {NetworkSetup 948}

syncStatenableINET6  OBJECT-TYPE
    SYNTAX      OCTET STRING
    MAX-ACCESS  read-only
    STATUS      current
    DESCRIPTION
"
synchronization status for enableINET6
-1 - enableINET6 could not be synchronized
 0 - synchronization not configured
 1 - out of sync - running master mode
 2 - in sync - running  mastermode
 3 - in sync - running slave mode
 4 - in sync - running master mode (wait to reach state 2)
"
    ::= {enableINET6 5}

syncStatStrenableINET6  OBJECT-TYPE
    SYNTAX      OCTET STRING
    MAX-ACCESS  read-only
    STATUS      current
    DESCRIPTION
"
synchronization status line from file assp_sync.cfg for enableINET6
 0 - synchronization not configured
 1 - out of sync - running master mode
 2 - in sync - running  mastermode
 3 - in sync - running slave mode
 4 - in sync - running master mode (wait to reach state 2)
"
    ::= {enableINET6 6}

DisableExtAUTH  OBJECT-TYPE
    SYNTAX      OCTET STRING
    MAX-ACCESS  read-write
    STATUS      current
    DESCRIPTION
"
If you do not want external clients (IP not in acceptAllMail or relayPort is not used) to use SMTP AUTH - for example to prevent address and password harvesting - check this option.
  The 'AUTH' offer in the EHLO and HELP reply will be stripped out, if set to on.
  Notice: setting this option to ON could prevent roaming users (dynamic IP) from being able to authenticate!
"
    REFERENCE "Disable SMTP AUTH for External Clients"
    DEFVAL { "" }
    ::= {NetworkSetup 1025}

syncStatDisableExtAUTH  OBJECT-TYPE
    SYNTAX      OCTET STRING
    MAX-ACCESS  read-only
    STATUS      current
    DESCRIPTION
"
synchronization status for DisableExtAUTH
-1 - DisableExtAUTH could not be synchronized
 0 - synchronization not configured
 1 - out of sync - running master mode
 2 - in sync - running  mastermode
 3 - in sync - running slave mode
 4 - in sync - running master mode (wait to reach state 2)
"
    ::= {DisableExtAUTH 5}

syncStatStrDisableExtAUTH  OBJECT-TYPE
    SYNTAX      OCTET STRING
    MAX-ACCESS  read-only
    STATUS      current
    DESCRIPTION
"
synchronization status line from file assp_sync.cfg for DisableExtAUTH
 0 - synchronization not configured
 1 - out of sync - running master mode
 2 - in sync - running  mastermode
 3 - in sync - running slave mode
 4 - in sync - running master mode (wait to reach state 2)
"
    ::= {DisableExtAUTH 6}

SMTPSessionLimits  OBJECT IDENTIFIER ::= {asspConfig 2}
MaxErrors  OBJECT-TYPE
    SYNTAX      OCTET STRING
    MAX-ACCESS  read-write
    STATUS      current
    DESCRIPTION
"
The maximum number of SMTP session errors encountered before the connection is dropped. An value of zero disables this feature. PB: meValencePB
"
    REFERENCE "Maximum Errors Per Session"
    DEFVAL { "5" }
    ::= {SMTPSessionLimits 10}

syncStatMaxErrors  OBJECT-TYPE
    SYNTAX      OCTET STRING
    MAX-ACCESS  read-only
    STATUS      current
    DESCRIPTION
"
synchronization status for MaxErrors
-1 - MaxErrors could not be synchronized
 0 - synchronization not configured
 1 - out of sync - running master mode
 2 - in sync - running  mastermode
 3 - in sync - running slave mode
 4 - in sync - running master mode (wait to reach state 2)
"
    ::= {MaxErrors 5}

syncStatStrMaxErrors  OBJECT-TYPE
    SYNTAX      OCTET STRING
    MAX-ACCESS  read-only
    STATUS      current
    DESCRIPTION
"
synchronization status line from file assp_sync.cfg for MaxErrors
 0 - synchronization not configured
 1 - out of sync - running master mode
 2 - in sync - running  mastermode
 3 - in sync - running slave mode
 4 - in sync - running master mode (wait to reach state 2)
"
    ::= {MaxErrors 6}

maxSMTPSessions  OBJECT-TYPE
    SYNTAX      OCTET STRING
    MAX-ACCESS  read-write
    STATUS      current
    DESCRIPTION
"
The maximum number of simultaneous SMTP sessions. This can prevent server overloading and DoS attacks. 64 simultaneous sessions are typically enough. Zero means no limit. Connections on relayPort will be counted, but connections on relayPort will never be limited because of this value. If the value is reached, assp will wait until the number of simultaneous SMTP sessions is lower than (value - 20) or (value * 0.75).
"
    REFERENCE "Maximum Sessions"
    DEFVAL { "64" }
    ::= {SMTPSessionLimits 11}

syncStatmaxSMTPSessions  OBJECT-TYPE
    SYNTAX      OCTET STRING
    MAX-ACCESS  read-only
    STATUS      current
    DESCRIPTION
"
synchronization status for maxSMTPSessions
-1 - maxSMTPSessions could not be synchronized
 0 - synchronization not configured
 1 - out of sync - running master mode
 2 - in sync - running  mastermode
 3 - in sync - running slave mode
 4 - in sync - running master mode (wait to reach state 2)
"
    ::= {maxSMTPSessions 5}

syncStatStrmaxSMTPSessions  OBJECT-TYPE
    SYNTAX      OCTET STRING
    MAX-ACCESS  read-only
    STATUS      current
    DESCRIPTION
"
synchronization status line from file assp_sync.cfg for maxSMTPSessions
 0 - synchronization not configured
 1 - out of sync - running master mode
 2 - in sync - running  mastermode
 3 - in sync - running slave mode
 4 - in sync - running master mode (wait to reach state 2)
"
    ::= {maxSMTPSessions 6}

maxSMTPipSessions  OBJECT-TYPE
    SYNTAX      OCTET STRING
    MAX-ACCESS  read-write
    STATUS      current
    DESCRIPTION
"
The maximum number of SMTP sessions allowed per IP address. Use this setting to prevent server overloading and DoS attacks. 5 sessions are typically enough. If set to 0 there is no limit imposed by ASSP. ispip (ISP/Secondary MX Servers) and acceptAllMail (Accept All Mail) matches are excluded from SMTP session limiting. PB: iplValencePB
"
    REFERENCE "Maximum Sessions Per IP Address"
    DEFVAL { "5" }
    ::= {SMTPSessionLimits 12}

syncStatmaxSMTPipSessions  OBJECT-TYPE
    SYNTAX      OCTET STRING
    MAX-ACCESS  read-only
    STATUS      current
    DESCRIPTION
"
synchronization status for maxSMTPipSessions
-1 - maxSMTPipSessions could not be synchronized
 0 - synchronization not configured
 1 - out of sync - running master mode
 2 - in sync - running  mastermode
 3 - in sync - running slave mode
 4 - in sync - running master mode (wait to reach state 2)
"
    ::= {maxSMTPipSessions 5}

syncStatStrmaxSMTPipSessions  OBJECT-TYPE
    SYNTAX      OCTET STRING
    MAX-ACCESS  read-only
    STATUS      current
    DESCRIPTION
"
synchronization status line from file assp_sync.cfg for maxSMTPipSessions
 0 - synchronization not configured
 1 - out of sync - running master mode
 2 - in sync - running  mastermode
 3 - in sync - running slave mode
 4 - in sync - running master mode (wait to reach state 2)
"
    ::= {maxSMTPipSessions 6}

HeaderMaxLength  OBJECT-TYPE
    SYNTAX      OCTET STRING
    MAX-ACCESS  read-write
    STATUS      current
    DESCRIPTION
"
The maximum allowed header length, in bytes. At each mail hop header information is added by the mail server. A large mail header can indicate a mail loop. If the value is blank or 0 the header size will not be checked.
"
    REFERENCE "Maximum Header Size"
    DEFVAL { "50000" }
    ::= {SMTPSessionLimits 13}

syncStatHeaderMaxLength  OBJECT-TYPE
    SYNTAX      OCTET STRING
    MAX-ACCESS  read-only
    STATUS      current
    DESCRIPTION
"
synchronization status for HeaderMaxLength
-1 - HeaderMaxLength could not be synchronized
 0 - synchronization not configured
 1 - out of sync - running master mode
 2 - in sync - running  mastermode
 3 - in sync - running slave mode
 4 - in sync - running master mode (wait to reach state 2)
"
    ::= {HeaderMaxLength 5}

syncStatStrHeaderMaxLength  OBJECT-TYPE
    SYNTAX      OCTET STRING
    MAX-ACCESS  read-only
    STATUS      current
    DESCRIPTION
"
synchronization status line from file assp_sync.cfg for HeaderMaxLength
 0 - synchronization not configured
 1 - out of sync - running master mode
 2 - in sync - running  mastermode
 3 - in sync - running slave mode
 4 - in sync - running master mode (wait to reach state 2)
"
    ::= {HeaderMaxLength 6}

maxRealSize  OBJECT-TYPE
    SYNTAX      OCTET STRING
    MAX-ACCESS  read-write
    STATUS      current
    DESCRIPTION
"
If the value of (number of [rcpt to] * [message size]) exceeds maxRealSize in bytes the transmission of the local message will be canceled. No limit is imposed by ASSP if the field is left blank or set to 0. This option allows admins to limit useless bandwidth wasting based on the total transmit size.
"
    REFERENCE "Max Real Size of Local Message"
    DEFVAL { "" }
    ::= {SMTPSessionLimits 14}

syncStatmaxRealSize  OBJECT-TYPE
    SYNTAX      OCTET STRING
    MAX-ACCESS  read-only
    STATUS      current
    DESCRIPTION
"
synchronization status for maxRealSize
-1 - maxRealSize could not be synchronized
 0 - synchronization not configured
 1 - out of sync - running master mode
 2 - in sync - running  mastermode
 3 - in sync - running slave mode
 4 - in sync - running master mode (wait to reach state 2)
"
    ::= {maxRealSize 5}

syncStatStrmaxRealSize  OBJECT-TYPE
    SYNTAX      OCTET STRING
    MAX-ACCESS  read-only
    STATUS      current
    DESCRIPTION
"
synchronization status line from file assp_sync.cfg for maxRealSize
 0 - synchronization not configured
 1 - out of sync - running master mode
 2 - in sync - running  mastermode
 3 - in sync - running slave mode
 4 - in sync - running master mode (wait to reach state 2)
"
    ::= {maxRealSize 6}

maxRealSizeExternal  OBJECT-TYPE
    SYNTAX      OCTET STRING
    MAX-ACCESS  read-write
    STATUS      current
    DESCRIPTION
"
If the value of (number of [rcpt to] * [message size]) exceeds maxRealSizeExternal in bytes the transmission of the external message will be canceled. No limit is imposed by ASSP if the field is left blank or set to 0. This option allows admins to limit useless bandwidth wasting based on the total transmit size.
"
    REFERENCE "Max Real Size of External Message"
    DEFVAL { "" }
    ::= {SMTPSessionLimits 15}

syncStatmaxRealSizeExternal  OBJECT-TYPE
    SYNTAX      OCTET STRING
    MAX-ACCESS  read-only
    STATUS      current
    DESCRIPTION
"
synchronization status for maxRealSizeExternal
-1 - maxRealSizeExternal could not be synchronized
 0 - synchronization not configured
 1 - out of sync - running master mode
 2 - in sync - running  mastermode
 3 - in sync - running slave mode
 4 - in sync - running master mode (wait to reach state 2)
"
    ::= {maxRealSizeExternal 5}

syncStatStrmaxRealSizeExternal  OBJECT-TYPE
    SYNTAX      OCTET STRING
    MAX-ACCESS  read-only
    STATUS      current
    DESCRIPTION
"
synchronization status line from file assp_sync.cfg for maxRealSizeExternal
 0 - synchronization not configured
 1 - out of sync - running master mode
 2 - in sync - running  mastermode
 3 - in sync - running slave mode
 4 - in sync - running master mode (wait to reach state 2)
"
    ::= {maxRealSizeExternal 6}

maxRealSizeError  OBJECT-TYPE
    SYNTAX      OCTET STRING
    MAX-ACCESS  read-write
    STATUS      current
    DESCRIPTION
"
SMTP error message to reject maxRealSize / maxRealSizeExternal exceeding mails. For example:552 message exceeds MAXREALSIZE byte (size * rcpt)! MAXREALSIZE will be replaced by the value of maxRealSize / maxRealSizeExternal.
"
    REFERENCE "max real message size Error"
    DEFVAL { "552 message exceeds MAXREALSIZE byte (size * rcpt)" }
    ::= {SMTPSessionLimits 16}

syncStatmaxRealSizeError  OBJECT-TYPE
    SYNTAX      OCTET STRING
    MAX-ACCESS  read-only
    STATUS      current
    DESCRIPTION
"
synchronization status for maxRealSizeError
-1 - maxRealSizeError could not be synchronized
 0 - synchronization not configured
 1 - out of sync - running master mode
 2 - in sync - running  mastermode
 3 - in sync - running slave mode
 4 - in sync - running master mode (wait to reach state 2)
"
    ::= {maxRealSizeError 5}

syncStatStrmaxRealSizeError  OBJECT-TYPE
    SYNTAX      OCTET STRING
    MAX-ACCESS  read-only
    STATUS      current
    DESCRIPTION
"
synchronization status line from file assp_sync.cfg for maxRealSizeError
 0 - synchronization not configured
 1 - out of sync - running master mode
 2 - in sync - running  mastermode
 3 - in sync - running slave mode
 4 - in sync - running master mode (wait to reach state 2)
"
    ::= {maxRealSizeError 6}

smtpIdleTimeout  OBJECT-TYPE
    SYNTAX      OCTET STRING
    MAX-ACCESS  read-write
    STATUS      current
    DESCRIPTION
"
The number of seconds a session is allowed to be idle before being forcibly disconnected. The default is 180 seconds. No limit is imposed by ASSP if the field is left blank or set to 0. If you have not defined an IdleTimeout on your MTA, this value should not be set to 0, because then a connection will never be timed out!
"
    REFERENCE "SMTP Idle Timeout"
    DEFVAL { "180" }
    ::= {SMTPSessionLimits 17}

syncStatsmtpIdleTimeout  OBJECT-TYPE
    SYNTAX      OCTET STRING
    MAX-ACCESS  read-only
    STATUS      current
    DESCRIPTION
"
synchronization status for smtpIdleTimeout
-1 - smtpIdleTimeout could not be synchronized
 0 - synchronization not configured
 1 - out of sync - running master mode
 2 - in sync - running  mastermode
 3 - in sync - running slave mode
 4 - in sync - running master mode (wait to reach state 2)
"
    ::= {smtpIdleTimeout 5}

syncStatStrsmtpIdleTimeout  OBJECT-TYPE
    SYNTAX      OCTET STRING
    MAX-ACCESS  read-only
    STATUS      current
    DESCRIPTION
"
synchronization status line from file assp_sync.cfg for smtpIdleTimeout
 0 - synchronization not configured
 1 - out of sync - running master mode
 2 - in sync - running  mastermode
 3 - in sync - running slave mode
 4 - in sync - running master mode (wait to reach state 2)
"
    ::= {smtpIdleTimeout 6}

smtpNOOPIdleTimeout  OBJECT-TYPE
    SYNTAX      OCTET STRING
    MAX-ACCESS  read-write
    STATUS      current
    DESCRIPTION
"
The number of seconds a session is allowed to be idle after a 'NOOP' command is received, before being forcibly disconnected. The default is 0 seconds. No limit is imposed by ASSP if the field is left blank or set to 0.
  This should prevent hackers to hold and block connections by sending 'NOOP' commands short before the 'smtpIdleTimeout' is reached.
"
    REFERENCE "SMTP Idle Timeout after NOOP"
    DEFVAL { "0" }
    ::= {SMTPSessionLimits 18}

syncStatsmtpNOOPIdleTimeout  OBJECT-TYPE
    SYNTAX      OCTET STRING
    MAX-ACCESS  read-only
    STATUS      current
    DESCRIPTION
"
synchronization status for smtpNOOPIdleTimeout
-1 - smtpNOOPIdleTimeout could not be synchronized
 0 - synchronization not configured
 1 - out of sync - running master mode
 2 - in sync - running  mastermode
 3 - in sync - running slave mode
 4 - in sync - running master mode (wait to reach state 2)
"
    ::= {smtpNOOPIdleTimeout 5}

syncStatStrsmtpNOOPIdleTimeout  OBJECT-TYPE
    SYNTAX      OCTET STRING
    MAX-ACCESS  read-only
    STATUS      current
    DESCRIPTION
"
synchronization status line from file assp_sync.cfg for smtpNOOPIdleTimeout
 0 - synchronization not configured
 1 - out of sync - running master mode
 2 - in sync - running  mastermode
 3 - in sync - running slave mode
 4 - in sync - running master mode (wait to reach state 2)
"
    ::= {smtpNOOPIdleTimeout 6}

smtpNOOPIdleTimeoutCount  OBJECT-TYPE
    SYNTAX      OCTET STRING
    MAX-ACCESS  read-write
    STATUS      current
    DESCRIPTION
"
The number of counts a session is allowed send 'NOOP' commands following on each other, before being forcibly disconnected. The default is 0. No limit is imposed by ASSP if the field is left blank or set to 0.
  This in cooperation with 'smtpNOOPIdleTimeout' should prevent hackers to hold and block connections by sending repeatedly 'NOOP' commands short before the 'smtpNOOPIdleTimeout' is reached. If 'smtpNOOPIdleTimeout' is not defined or 0, this value will be ignored!
"
    REFERENCE "SMTP Idle Timeout after NOOP Count"
    DEFVAL { "0" }
    ::= {SMTPSessionLimits 19}

syncStatsmtpNOOPIdleTimeoutCount  OBJECT-TYPE
    SYNTAX      OCTET STRING
    MAX-ACCESS  read-only
    STATUS      current
    DESCRIPTION
"
synchronization status for smtpNOOPIdleTimeoutCount
-1 - smtpNOOPIdleTimeoutCount could not be synchronized
 0 - synchronization not configured
 1 - out of sync - running master mode
 2 - in sync - running  mastermode
 3 - in sync - running slave mode
 4 - in sync - running master mode (wait to reach state 2)
"
    ::= {smtpNOOPIdleTimeoutCount 5}

syncStatStrsmtpNOOPIdleTimeoutCount  OBJECT-TYPE
    SYNTAX      OCTET STRING
    MAX-ACCESS  read-only
    STATUS      current
    DESCRIPTION
"
synchronization status line from file assp_sync.cfg for smtpNOOPIdleTimeoutCount
 0 - synchronization not configured
 1 - out of sync - running master mode
 2 - in sync - running  mastermode
 3 - in sync - running slave mode
 4 - in sync - running master mode (wait to reach state 2)
"
    ::= {smtpNOOPIdleTimeoutCount 6}

maxSize  OBJECT-TYPE
    SYNTAX      OCTET STRING
    MAX-ACCESS  read-write
    STATUS      current
    DESCRIPTION
"
If the value of ([message size]) exceeds maxSize in bytes the transmission of the local message will be canceled. No limit is imposed by ASSP if the field is left blank or set to 0. This option allows admins to limit useless bandwidth wasting based on the transmit size.
"
    REFERENCE "Max Size of Local Message"
    DEFVAL { "" }
    ::= {SMTPSessionLimits 862}

syncStatmaxSize  OBJECT-TYPE
    SYNTAX      OCTET STRING
    MAX-ACCESS  read-only
    STATUS      current
    DESCRIPTION
"
synchronization status for maxSize
-1 - maxSize could not be synchronized
 0 - synchronization not configured
 1 - out of sync - running master mode
 2 - in sync - running  mastermode
 3 - in sync - running slave mode
 4 - in sync - running master mode (wait to reach state 2)
"
    ::= {maxSize 5}

syncStatStrmaxSize  OBJECT-TYPE
    SYNTAX      OCTET STRING
    MAX-ACCESS  read-only
    STATUS      current
    DESCRIPTION
"
synchronization status line from file assp_sync.cfg for maxSize
 0 - synchronization not configured
 1 - out of sync - running master mode
 2 - in sync - running  mastermode
 3 - in sync - running slave mode
 4 - in sync - running master mode (wait to reach state 2)
"
    ::= {maxSize 6}

maxSizeExternal  OBJECT-TYPE
    SYNTAX      OCTET STRING
    MAX-ACCESS  read-write
    STATUS      current
    DESCRIPTION
"
If the value of ([message size]) exceeds maxSizeExternal in bytes the transmission of the external message will be canceled. No limit is imposed by ASSP if the field is left blank or set to 0. This option allows admins to limit useless bandwidth wasting based on the transmit size.
"
    REFERENCE "Max Size of External Message"
    DEFVAL { "" }
    ::= {SMTPSessionLimits 863}

syncStatmaxSizeExternal  OBJECT-TYPE
    SYNTAX      OCTET STRING
    MAX-ACCESS  read-only
    STATUS      current
    DESCRIPTION
"
synchronization status for maxSizeExternal
-1 - maxSizeExternal could not be synchronized
 0 - synchronization not configured
 1 - out of sync - running master mode
 2 - in sync - running  mastermode
 3 - in sync - running slave mode
 4 - in sync - running master mode (wait to reach state 2)
"
    ::= {maxSizeExternal 5}

syncStatStrmaxSizeExternal  OBJECT-TYPE
    SYNTAX      OCTET STRING
    MAX-ACCESS  read-only
    STATUS      current
    DESCRIPTION
"
synchronization status line from file assp_sync.cfg for maxSizeExternal
 0 - synchronization not configured
 1 - out of sync - running master mode
 2 - in sync - running  mastermode
 3 - in sync - running slave mode
 4 - in sync - running master mode (wait to reach state 2)
"
    ::= {maxSizeExternal 6}

maxSizeError  OBJECT-TYPE
    SYNTAX      OCTET STRING
    MAX-ACCESS  read-write
    STATUS      current
    DESCRIPTION
"
SMTP error message to reject maxSize / maxSizeExternal exceeding mails. For example:552 message exceeds MAXSIZE byte (size)! MAXSIZE will be replaced by the value of maxSize / maxSizeExternal.
"
    REFERENCE "max message size Error"
    DEFVAL { "552 message exceeds MAXSIZE byte (size)" }
    ::= {SMTPSessionLimits 864}

syncStatmaxSizeError  OBJECT-TYPE
    SYNTAX      OCTET STRING
    MAX-ACCESS  read-only
    STATUS      current
    DESCRIPTION
"
synchronization status for maxSizeError
-1 - maxSizeError could not be synchronized
 0 - synchronization not configured
 1 - out of sync - running master mode
 2 - in sync - running  mastermode
 3 - in sync - running slave mode
 4 - in sync - running master mode (wait to reach state 2)
"
    ::= {maxSizeError 5}

syncStatStrmaxSizeError  OBJECT-TYPE
    SYNTAX      OCTET STRING
    MAX-ACCESS  read-only
    STATUS      current
    DESCRIPTION
"
synchronization status line from file assp_sync.cfg for maxSizeError
 0 - synchronization not configured
 1 - out of sync - running master mode
 2 - in sync - running  mastermode
 3 - in sync - running slave mode
 4 - in sync - running master mode (wait to reach state 2)
"
    ::= {maxSizeError 6}

detectMailLoop  OBJECT-TYPE
    SYNTAX      OCTET STRING
    MAX-ACCESS  read-write
    STATUS      current
    DESCRIPTION
"
If set to a value higher than 0, ASSP count it's own Received-header in the header of the mail. If this count exceeds the defined value, the transmission of the message will be canceled.
"
    REFERENCE "Detect Possible Mailloop"
    DEFVAL { "3" }
    ::= {SMTPSessionLimits 886}

syncStatdetectMailLoop  OBJECT-TYPE
    SYNTAX      OCTET STRING
    MAX-ACCESS  read-only
    STATUS      current
    DESCRIPTION
"
synchronization status for detectMailLoop
-1 - detectMailLoop could not be synchronized
 0 - synchronization not configured
 1 - out of sync - running master mode
 2 - in sync - running  mastermode
 3 - in sync - running slave mode
 4 - in sync - running master mode (wait to reach state 2)
"
    ::= {detectMailLoop 5}

syncStatStrdetectMailLoop  OBJECT-TYPE
    SYNTAX      OCTET STRING
    MAX-ACCESS  read-only
    STATUS      current
    DESCRIPTION
"
synchronization status line from file assp_sync.cfg for detectMailLoop
 0 - synchronization not configured
 1 - out of sync - running master mode
 2 - in sync - running  mastermode
 3 - in sync - running slave mode
 4 - in sync - running master mode (wait to reach state 2)
"
    ::= {detectMailLoop 6}

MaxEqualXHeader  OBJECT-TYPE
    SYNTAX      OCTET STRING
    MAX-ACCESS  read-write
    STATUS      current
    DESCRIPTION
"
The maximum allowed equal X-header lines - eg. 'X-SubscriberID'. If the value is set to empty the header will not be checked for equal X-header lines. This check will be skipped for noprocessing, whitelisted and outgoing mails.
  The default is '*=&gt;20', which means any X-header can occur 20 time maximum. You can define different values for different X-headers - wildcards like '*' and '?' are allowed to be used.
  For example:
  *=&gt;20|X-Notes-Item=&gt;100|X-Subscriber*=&gt;10|X-AnyTag=&gt;0
  An value of zero disables the check for the defined X-header. The check is also skipped if no default like '*=&gt;20' is defined and the X-header defintion is not found.
"
    REFERENCE "Maximum Equal X-Header Lines*"
    DEFVAL { "*=>20" }
    ::= {SMTPSessionLimits 906}

syncStatMaxEqualXHeader  OBJECT-TYPE
    SYNTAX      OCTET STRING
    MAX-ACCESS  read-only
    STATUS      current
    DESCRIPTION
"
synchronization status for MaxEqualXHeader
-1 - MaxEqualXHeader could not be synchronized
 0 - synchronization not configured
 1 - out of sync - running master mode
 2 - in sync - running  mastermode
 3 - in sync - running slave mode
 4 - in sync - running master mode (wait to reach state 2)
"
    ::= {MaxEqualXHeader 5}

syncStatStrMaxEqualXHeader  OBJECT-TYPE
    SYNTAX      OCTET STRING
    MAX-ACCESS  read-only
    STATUS      current
    DESCRIPTION
"
synchronization status line from file assp_sync.cfg for MaxEqualXHeader
 0 - synchronization not configured
 1 - out of sync - running master mode
 2 - in sync - running  mastermode
 3 - in sync - running slave mode
 4 - in sync - running master mode (wait to reach state 2)
"
    ::= {MaxEqualXHeader 6}

noMaxSMTPSessions  OBJECT-TYPE
    SYNTAX      OCTET STRING
    MAX-ACCESS  read-write
    STATUS      current
    DESCRIPTION
"
Mail from any of these IP numbers will pass through without checking maximum number of simultaneous SMTP sessions. For example: 145.145.145.145
"
    REFERENCE "No Maximum Sessions IP numbers*"
    DEFVAL { "" }
    ::= {SMTPSessionLimits 916}

syncStatnoMaxSMTPSessions  OBJECT-TYPE
    SYNTAX      OCTET STRING
    MAX-ACCESS  read-only
    STATUS      current
    DESCRIPTION
"
synchronization status for noMaxSMTPSessions
-1 - noMaxSMTPSessions could not be synchronized
 0 - synchronization not configured
 1 - out of sync - running master mode
 2 - in sync - running  mastermode
 3 - in sync - running slave mode
 4 - in sync - running master mode (wait to reach state 2)
"
    ::= {noMaxSMTPSessions 5}

syncStatStrnoMaxSMTPSessions  OBJECT-TYPE
    SYNTAX      OCTET STRING
    MAX-ACCESS  read-only
    STATUS      current
    DESCRIPTION
"
synchronization status line from file assp_sync.cfg for noMaxSMTPSessions
 0 - synchronization not configured
 1 - out of sync - running master mode
 2 - in sync - running  mastermode
 3 - in sync - running slave mode
 4 - in sync - running master mode (wait to reach state 2)
"
    ::= {noMaxSMTPSessions 6}

MaxAUTHErrors  OBJECT-TYPE
    SYNTAX      OCTET STRING
    MAX-ACCESS  read-write
    STATUS      current
    DESCRIPTION
"
If an IP (/24 network is used) exceeds this number of authentication errors (535 or 530) the transmission of the current message will be canceled and any new connection from that IP will be blocked for 5-10 minutes.
  Every 5 Minutes the 'AUTHError' -counter of the IP will be decreased by one. autValencePB is used for the penalty box.
  No limit is imposed by ASSP if the field is left blank or set to 0. This option allows admins to prevent external bruteforce or dictionary attacks via AUTH command. Whitelisted, noBlockingIPs and NoProcessing IP's are ignored like any relayed connection.
"
    REFERENCE "Max Number of AUTHentication Errors"
    DEFVAL { "" }
    ::= {SMTPSessionLimits 931}

syncStatMaxAUTHErrors  OBJECT-TYPE
    SYNTAX      OCTET STRING
    MAX-ACCESS  read-only
    STATUS      current
    DESCRIPTION
"
synchronization status for MaxAUTHErrors
-1 - MaxAUTHErrors could not be synchronized
 0 - synchronization not configured
 1 - out of sync - running master mode
 2 - in sync - running  mastermode
 3 - in sync - running slave mode
 4 - in sync - running master mode (wait to reach state 2)
"
    ::= {MaxAUTHErrors 5}

syncStatStrMaxAUTHErrors  OBJECT-TYPE
    SYNTAX      OCTET STRING
    MAX-ACCESS  read-only
    STATUS      current
    DESCRIPTION
"
synchronization status line from file assp_sync.cfg for MaxAUTHErrors
 0 - synchronization not configured
 1 - out of sync - running master mode
 2 - in sync - running  mastermode
 3 - in sync - running slave mode
 4 - in sync - running master mode (wait to reach state 2)
"
    ::= {MaxAUTHErrors 6}

MaxRealSizeAdr  OBJECT-TYPE
    SYNTAX      OCTET STRING
    MAX-ACCESS  read-write
    STATUS      current
    DESCRIPTION
"
Use this parameter to set individual maxRealSize values for email addresses, domains, user names and IP addresses. A file must be specified if used.
Accepts specific addresses (user@domain.com), user parts (user), entire domains (@domain.com) and IP addresses (CIDR notation like 123.1.101/32 is here not supported!) - group definitions could be used. Use one entry per line. Wildcards are supported (fribo*@domain.co?). A second parameter separated by '=>' specifies the size limit. 
For example:
fribo*@thisdomain.co?=&gt;1000000
jhanna=&gt;0
@sillyguys.org=&gt;500000
101.1.2.*=&gt;0
[admins]=&gt;0 
If multiple matches (values) are found in a mail for any IP address in the transport mail chain, any envelope recipient and the envelope sender, the highest value or 0 (no limit) will be used! If no match (value) is found in a mail, the definition in maxRealSize will take place.
"
    REFERENCE "Max Real Size of Local Message Addresses*"
    DEFVAL { "file:files/MaxRealSize.txt" }
    ::= {SMTPSessionLimits 949}

syncStatMaxRealSizeAdr  OBJECT-TYPE
    SYNTAX      OCTET STRING
    MAX-ACCESS  read-only
    STATUS      current
    DESCRIPTION
"
synchronization status for MaxRealSizeAdr
-1 - MaxRealSizeAdr could not be synchronized
 0 - synchronization not configured
 1 - out of sync - running master mode
 2 - in sync - running  mastermode
 3 - in sync - running slave mode
 4 - in sync - running master mode (wait to reach state 2)
"
    ::= {MaxRealSizeAdr 5}

syncStatStrMaxRealSizeAdr  OBJECT-TYPE
    SYNTAX      OCTET STRING
    MAX-ACCESS  read-only
    STATUS      current
    DESCRIPTION
"
synchronization status line from file assp_sync.cfg for MaxRealSizeAdr
 0 - synchronization not configured
 1 - out of sync - running master mode
 2 - in sync - running  mastermode
 3 - in sync - running slave mode
 4 - in sync - running master mode (wait to reach state 2)
"
    ::= {MaxRealSizeAdr 6}

MaxRealSizeExternalAdr  OBJECT-TYPE
    SYNTAX      OCTET STRING
    MAX-ACCESS  read-write
    STATUS      current
    DESCRIPTION
"
Use this parameter to set individual maxRealSizeExternal values for email addresses, domains, user names and IP addresses. A file must be specified if used.
Accepts specific addresses (user@domain.com), user parts (user), entire domains (@domain.com) and IP addresses (CIDR notation like 123.1.101/32 is here not supported!) - group definitions could be used. Use one entry per line. Wildcards are supported (fribo*@domain.co?). A second parameter separated by '=>' specifies the size limit. 
For example:
fribo*@thisdomain.co?=&gt;1000000
jhanna=&gt;0
@sillyguys.org=&gt;500000
101.1.2.*=&gt;0
[admins]=&gt;0 
If multiple matches (values) are found in a mail for any IP address in the transport mail chain, any envelope recipient and the envelope sender, the highest value or 0 (no limit) will be used! If no match (value) is found in a mail, the definition in maxRealSizeExternal will take place.
"
    REFERENCE "Max Real Size of External Message Addresses*"
    DEFVAL { "file:files/MaxRealSizeExt.txt" }
    ::= {SMTPSessionLimits 950}

syncStatMaxRealSizeExternalAdr  OBJECT-TYPE
    SYNTAX      OCTET STRING
    MAX-ACCESS  read-only
    STATUS      current
    DESCRIPTION
"
synchronization status for MaxRealSizeExternalAdr
-1 - MaxRealSizeExternalAdr could not be synchronized
 0 - synchronization not configured
 1 - out of sync - running master mode
 2 - in sync - running  mastermode
 3 - in sync - running slave mode
 4 - in sync - running master mode (wait to reach state 2)
"
    ::= {MaxRealSizeExternalAdr 5}

syncStatStrMaxRealSizeExternalAdr  OBJECT-TYPE
    SYNTAX      OCTET STRING
    MAX-ACCESS  read-only
    STATUS      current
    DESCRIPTION
"
synchronization status line from file assp_sync.cfg for MaxRealSizeExternalAdr
 0 - synchronization not configured
 1 - out of sync - running master mode
 2 - in sync - running  mastermode
 3 - in sync - running slave mode
 4 - in sync - running master mode (wait to reach state 2)
"
    ::= {MaxRealSizeExternalAdr 6}

MaxSizeAdr  OBJECT-TYPE
    SYNTAX      OCTET STRING
    MAX-ACCESS  read-write
    STATUS      current
    DESCRIPTION
"
Use this parameter to set individual maxSize values for email addresses, domains, user names and IP addresses. A file must be specified if used.
Accepts specific addresses (user@domain.com), user parts (user), entire domains (@domain.com) and IP addresses (CIDR notation like 123.1.101/32 is here not supported!) - group definitions could be used. Use one entry per line. Wildcards are supported (fribo*@domain.co?). A second parameter separated by '=>' specifies the size limit. 
For example:
fribo*@thisdomain.co?=&gt;1000000
jhanna=&gt;0
@sillyguys.org=&gt;500000
101.1.2.*=&gt;0
[admins]=&gt;0 
If multiple matches (values) are found in a mail for any IP address in the transport mail chain, any envelope recipient and the envelope sender, the highest value or 0 (no limit) will be used! If no match (value) is found in a mail, the definition in maxSize will take place.
"
    REFERENCE "Max Size of Local Message Addresses*"
    DEFVAL { "file:files/MaxSize.txt" }
    ::= {SMTPSessionLimits 951}

syncStatMaxSizeAdr  OBJECT-TYPE
    SYNTAX      OCTET STRING
    MAX-ACCESS  read-only
    STATUS      current
    DESCRIPTION
"
synchronization status for MaxSizeAdr
-1 - MaxSizeAdr could not be synchronized
 0 - synchronization not configured
 1 - out of sync - running master mode
 2 - in sync - running  mastermode
 3 - in sync - running slave mode
 4 - in sync - running master mode (wait to reach state 2)
"
    ::= {MaxSizeAdr 5}

syncStatStrMaxSizeAdr  OBJECT-TYPE
    SYNTAX      OCTET STRING
    MAX-ACCESS  read-only
    STATUS      current
    DESCRIPTION
"
synchronization status line from file assp_sync.cfg for MaxSizeAdr
 0 - synchronization not configured
 1 - out of sync - running master mode
 2 - in sync - running  mastermode
 3 - in sync - running slave mode
 4 - in sync - running master mode (wait to reach state 2)
"
    ::= {MaxSizeAdr 6}

MaxSizeExternalAdr  OBJECT-TYPE
    SYNTAX      OCTET STRING
    MAX-ACCESS  read-write
    STATUS      current
    DESCRIPTION
"
Use this parameter to set individual maxSizeExternal values for email addresses, domains, user names and IP addresses. A file must be specified if used.
Accepts specific addresses (user@domain.com), user parts (user), entire domains (@domain.com) and IP addresses (CIDR notation like 123.1.101/32 is here not supported!) - group definitions could be used. Use one entry per line. Wildcards are supported (fribo*@domain.co?). A second parameter separated by '=>' specifies the size limit. 
For example:
fribo*@thisdomain.co?=&gt;1000000
jhanna=&gt;0
@sillyguys.org=&gt;500000
101.1.2.*=&gt;0
[admins]=&gt;0 
If multiple matches (values) are found in a mail for any IP address in the transport mail chain, any envelope recipient and the envelope sender, the highest value or 0 (no limit) will be used! If no match (value) is found in a mail, the definition in maxSizeExternal will take place.
"
    REFERENCE "Max Size of External Message Addresses*"
    DEFVAL { "file:files/MaxSizeExt.txt" }
    ::= {SMTPSessionLimits 952}

syncStatMaxSizeExternalAdr  OBJECT-TYPE
    SYNTAX      OCTET STRING
    MAX-ACCESS  read-only
    STATUS      current
    DESCRIPTION
"
synchronization status for MaxSizeExternalAdr
-1 - MaxSizeExternalAdr could not be synchronized
 0 - synchronization not configured
 1 - out of sync - running master mode
 2 - in sync - running  mastermode
 3 - in sync - running slave mode
 4 - in sync - running master mode (wait to reach state 2)
"
    ::= {MaxSizeExternalAdr 5}

syncStatStrMaxSizeExternalAdr  OBJECT-TYPE
    SYNTAX      OCTET STRING
    MAX-ACCESS  read-only
    STATUS      current
    DESCRIPTION
"
synchronization status line from file assp_sync.cfg for MaxSizeExternalAdr
 0 - synchronization not configured
 1 - out of sync - running master mode
 2 - in sync - running  mastermode
 3 - in sync - running slave mode
 4 - in sync - running master mode (wait to reach state 2)
"
    ::= {MaxSizeExternalAdr 6}

noMaxAUTHErrorIPs  OBJECT-TYPE
    SYNTAX      OCTET STRING
    MAX-ACCESS  read-write
    STATUS      current
    DESCRIPTION
"
List of IP's which should not be checked for MaxAUTHErrors .  For example: 145.145.145.145|145.146.
"
    REFERENCE "Do not check MaxAUTHErrors for these IP's*"
    DEFVAL { "" }
    ::= {SMTPSessionLimits 958}

syncStatnoMaxAUTHErrorIPs  OBJECT-TYPE
    SYNTAX      OCTET STRING
    MAX-ACCESS  read-only
    STATUS      current
    DESCRIPTION
"
synchronization status for noMaxAUTHErrorIPs
-1 - noMaxAUTHErrorIPs could not be synchronized
 0 - synchronization not configured
 1 - out of sync - running master mode
 2 - in sync - running  mastermode
 3 - in sync - running slave mode
 4 - in sync - running master mode (wait to reach state 2)
"
    ::= {noMaxAUTHErrorIPs 5}

syncStatStrnoMaxAUTHErrorIPs  OBJECT-TYPE
    SYNTAX      OCTET STRING
    MAX-ACCESS  read-only
    STATUS      current
    DESCRIPTION
"
synchronization status line from file assp_sync.cfg for noMaxAUTHErrorIPs
 0 - synchronization not configured
 1 - out of sync - running master mode
 2 - in sync - running  mastermode
 3 - in sync - running slave mode
 4 - in sync - running master mode (wait to reach state 2)
"
    ::= {noMaxAUTHErrorIPs 6}

NpWlTimeOut  OBJECT-TYPE
    SYNTAX      OCTET STRING
    MAX-ACCESS  read-write
    STATUS      current
    DESCRIPTION
"
The number of seconds a whitelisted or noprocessing session is allowed to be idle before being forcibly disconnected. The default is 1200 seconds. No limit is imposed by ASSP if the field is left blank or set to 0. If you have not defined an IdleTimeout on your MTA, this value should not be set to 0, because then a connection will never be timed out!
"
    REFERENCE "SMTP Idle Timeout for Whitelisted an Noprocessing"
    DEFVAL { "1200" }
    ::= {SMTPSessionLimits 986}

syncStatNpWlTimeOut  OBJECT-TYPE
    SYNTAX      OCTET STRING
    MAX-ACCESS  read-only
    STATUS      current
    DESCRIPTION
"
synchronization status for NpWlTimeOut
-1 - NpWlTimeOut could not be synchronized
 0 - synchronization not configured
 1 - out of sync - running master mode
 2 - in sync - running  mastermode
 3 - in sync - running slave mode
 4 - in sync - running master mode (wait to reach state 2)
"
    ::= {NpWlTimeOut 5}

syncStatStrNpWlTimeOut  OBJECT-TYPE
    SYNTAX      OCTET STRING
    MAX-ACCESS  read-only
    STATUS      current
    DESCRIPTION
"
synchronization status line from file assp_sync.cfg for NpWlTimeOut
 0 - synchronization not configured
 1 - out of sync - running master mode
 2 - in sync - running  mastermode
 3 - in sync - running slave mode
 4 - in sync - running master mode (wait to reach state 2)
"
    ::= {NpWlTimeOut 6}

DoSameSubject  OBJECT-TYPE
    SYNTAX      OCTET STRING
    MAX-ACCESS  read-write
    STATUS      current
    DESCRIPTION
"
If activated, assp will check the mail subjects for equality using the config parameters below. Scoring is done with 'isValencePB'.
"
    REFERENCE "Check Same Subjects"
    DEFVAL { "0" }
    ::= {SMTPSessionLimits 1004}

syncStatDoSameSubject  OBJECT-TYPE
    SYNTAX      OCTET STRING
    MAX-ACCESS  read-only
    STATUS      current
    DESCRIPTION
"
synchronization status for DoSameSubject
-1 - DoSameSubject could not be synchronized
 0 - synchronization not configured
 1 - out of sync - running master mode
 2 - in sync - running  mastermode
 3 - in sync - running slave mode
 4 - in sync - running master mode (wait to reach state 2)
"
    ::= {DoSameSubject 5}

syncStatStrDoSameSubject  OBJECT-TYPE
    SYNTAX      OCTET STRING
    MAX-ACCESS  read-only
    STATUS      current
    DESCRIPTION
"
synchronization status line from file assp_sync.cfg for DoSameSubject
 0 - synchronization not configured
 1 - out of sync - running master mode
 2 - in sync - running  mastermode
 3 - in sync - running slave mode
 4 - in sync - running master mode (wait to reach state 2)
"
    ::= {DoSameSubject 6}

subjectFrequencyInt  OBJECT-TYPE
    SYNTAX      OCTET STRING
    MAX-ACCESS  read-write
    STATUS      current
    DESCRIPTION
"
The time interval in seconds in which the number of equal subjects has not to exceed a specific number ( subjectFrequencyNumSubj ).
  Use this in combination with subjectFrequencyNumSubj to limit the number of equal subjects in a given interval. A value of 0 (default) will disable this feature and clean the cache within five minutes.
  
"
    REFERENCE "Subject Frequency Interval"
    DEFVAL { "300" }
    ::= {SMTPSessionLimits 1005}

syncStatsubjectFrequencyInt  OBJECT-TYPE
    SYNTAX      OCTET STRING
    MAX-ACCESS  read-only
    STATUS      current
    DESCRIPTION
"
synchronization status for subjectFrequencyInt
-1 - subjectFrequencyInt could not be synchronized
 0 - synchronization not configured
 1 - out of sync - running master mode
 2 - in sync - running  mastermode
 3 - in sync - running slave mode
 4 - in sync - running master mode (wait to reach state 2)
"
    ::= {subjectFrequencyInt 5}

syncStatStrsubjectFrequencyInt  OBJECT-TYPE
    SYNTAX      OCTET STRING
    MAX-ACCESS  read-only
    STATUS      current
    DESCRIPTION
"
synchronization status line from file assp_sync.cfg for subjectFrequencyInt
 0 - synchronization not configured
 1 - out of sync - running master mode
 2 - in sync - running  mastermode
 3 - in sync - running slave mode
 4 - in sync - running master mode (wait to reach state 2)
"
    ::= {subjectFrequencyInt 6}

subjectFrequencyNumSubj  OBJECT-TYPE
    SYNTAX      OCTET STRING
    MAX-ACCESS  read-write
    STATUS      current
    DESCRIPTION
"
The number of equal sbujects that has not to exceed in a specific time interval ( subjectFrequencyInt ).
  Use this in combination with subjectFrequencyInt to limit the number of equal subjects in a given interval. A value of 0 (default) will disable this feature and clean the cache within five minutes.
  
"
    REFERENCE "Subject Frequency Number of Subjects"
    DEFVAL { "5" }
    ::= {SMTPSessionLimits 1006}

syncStatsubjectFrequencyNumSubj  OBJECT-TYPE
    SYNTAX      OCTET STRING
    MAX-ACCESS  read-only
    STATUS      current
    DESCRIPTION
"
synchronization status for subjectFrequencyNumSubj
-1 - subjectFrequencyNumSubj could not be synchronized
 0 - synchronization not configured
 1 - out of sync - running master mode
 2 - in sync - running  mastermode
 3 - in sync - running slave mode
 4 - in sync - running master mode (wait to reach state 2)
"
    ::= {subjectFrequencyNumSubj 5}

syncStatStrsubjectFrequencyNumSubj  OBJECT-TYPE
    SYNTAX      OCTET STRING
    MAX-ACCESS  read-only
    STATUS      current
    DESCRIPTION
"
synchronization status line from file assp_sync.cfg for subjectFrequencyNumSubj
 0 - synchronization not configured
 1 - out of sync - running master mode
 2 - in sync - running  mastermode
 3 - in sync - running slave mode
 4 - in sync - running master mode (wait to reach state 2)
"
    ::= {subjectFrequencyNumSubj 6}

subjectFrequencyOnly  OBJECT-TYPE
    SYNTAX      OCTET STRING
    MAX-ACCESS  read-write
    STATUS      current
    DESCRIPTION
"
A list of local addresses, for which the 'subject frequency check' should be done. Leave this field blank (default), to do the check for every address.
  Accepts specific addresses (user@domain.com), user parts (user) or entire domains (@domain.com).  Wildcards are supported (fribo*@domain.com).
  For example: fribo*@thisdomain.com|jhanna|@sillyguys.org 
"
    REFERENCE "Check Equal Subject Frequency for this Users only*"
    DEFVAL { "" }
    ::= {SMTPSessionLimits 1007}

syncStatsubjectFrequencyOnly  OBJECT-TYPE
    SYNTAX      OCTET STRING
    MAX-ACCESS  read-only
    STATUS      current
    DESCRIPTION
"
synchronization status for subjectFrequencyOnly
-1 - subjectFrequencyOnly could not be synchronized
 0 - synchronization not configured
 1 - out of sync - running master mode
 2 - in sync - running  mastermode
 3 - in sync - running slave mode
 4 - in sync - running master mode (wait to reach state 2)
"
    ::= {subjectFrequencyOnly 5}

syncStatStrsubjectFrequencyOnly  OBJECT-TYPE
    SYNTAX      OCTET STRING
    MAX-ACCESS  read-only
    STATUS      current
    DESCRIPTION
"
synchronization status line from file assp_sync.cfg for subjectFrequencyOnly
 0 - synchronization not configured
 1 - out of sync - running master mode
 2 - in sync - running  mastermode
 3 - in sync - running slave mode
 4 - in sync - running master mode (wait to reach state 2)
"
    ::= {subjectFrequencyOnly 6}

NoSubjectFrequency  OBJECT-TYPE
    SYNTAX      OCTET STRING
    MAX-ACCESS  read-write
    STATUS      current
    DESCRIPTION
"
A list of local addresses, for which the 'subject frequency check' should not be done.
  Accepts specific addresses (user@domain.com), user parts (user) or entire domains (@domain.com).  Wildcards are supported (fribo*@domain.com).
  For example: fribo*@thisdomain.com|jhanna|@sillyguys.org 
"
    REFERENCE "Check Equal Subject Frequency NOT for this Users*"
    DEFVAL { "" }
    ::= {SMTPSessionLimits 1008}

syncStatNoSubjectFrequency  OBJECT-TYPE
    SYNTAX      OCTET STRING
    MAX-ACCESS  read-only
    STATUS      current
    DESCRIPTION
"
synchronization status for NoSubjectFrequency
-1 - NoSubjectFrequency could not be synchronized
 0 - synchronization not configured
 1 - out of sync - running master mode
 2 - in sync - running  mastermode
 3 - in sync - running slave mode
 4 - in sync - running master mode (wait to reach state 2)
"
    ::= {NoSubjectFrequency 5}

syncStatStrNoSubjectFrequency  OBJECT-TYPE
    SYNTAX      OCTET STRING
    MAX-ACCESS  read-only
    STATUS      current
    DESCRIPTION
"
synchronization status line from file assp_sync.cfg for NoSubjectFrequency
 0 - synchronization not configured
 1 - out of sync - running master mode
 2 - in sync - running  mastermode
 3 - in sync - running slave mode
 4 - in sync - running master mode (wait to reach state 2)
"
    ::= {NoSubjectFrequency 6}

NoSubjectFrequencyIP  OBJECT-TYPE
    SYNTAX      OCTET STRING
    MAX-ACCESS  read-write
    STATUS      current
    DESCRIPTION
"
Mail from any of these IP numbers will pass through without checking the equality of subjects. For example: 145.145.145.145
"
    REFERENCE "Check Equal Subject Frequency NOT for this IP's*"
    DEFVAL { "" }
    ::= {SMTPSessionLimits 1009}

syncStatNoSubjectFrequencyIP  OBJECT-TYPE
    SYNTAX      OCTET STRING
    MAX-ACCESS  read-only
    STATUS      current
    DESCRIPTION
"
synchronization status for NoSubjectFrequencyIP
-1 - NoSubjectFrequencyIP could not be synchronized
 0 - synchronization not configured
 1 - out of sync - running master mode
 2 - in sync - running  mastermode
 3 - in sync - running slave mode
 4 - in sync - running master mode (wait to reach state 2)
"
    ::= {NoSubjectFrequencyIP 5}

syncStatStrNoSubjectFrequencyIP  OBJECT-TYPE
    SYNTAX      OCTET STRING
    MAX-ACCESS  read-only
    STATUS      current
    DESCRIPTION
"
synchronization status line from file assp_sync.cfg for NoSubjectFrequencyIP
 0 - synchronization not configured
 1 - out of sync - running master mode
 2 - in sync - running  mastermode
 3 - in sync - running slave mode
 4 - in sync - running master mode (wait to reach state 2)
"
    ::= {NoSubjectFrequencyIP 6}

Groupdefinition  OBJECT IDENTIFIER ::= {asspConfig 3}
GroupsReloadEvery  OBJECT-TYPE
    SYNTAX      OCTET STRING
    MAX-ACCESS  read-write
    STATUS      current
    DESCRIPTION
"
ASSP will reload the Groups definiton every this minutes, if the exec: or ldap: option is used in Groups. 
 An value of zero disables the scheduled reload. Defaults to 60 minutes.
 
"
    REFERENCE "Reload the Groups definitions every this minutes <sup>s</sup>"
    DEFVAL { "60" }
    ::= {Groupdefinition 791}

syncStatGroupsReloadEvery  OBJECT-TYPE
    SYNTAX      OCTET STRING
    MAX-ACCESS  read-only
    STATUS      current
    DESCRIPTION
"
synchronization status for GroupsReloadEvery
-1 - GroupsReloadEvery could not be synchronized
 0 - synchronization not configured
 1 - out of sync - running master mode
 2 - in sync - running  mastermode
 3 - in sync - running slave mode
 4 - in sync - running master mode (wait to reach state 2)
"
    ::= {GroupsReloadEvery 5}

syncStatStrGroupsReloadEvery  OBJECT-TYPE
    SYNTAX      OCTET STRING
    MAX-ACCESS  read-only
    STATUS      current
    DESCRIPTION
"
synchronization status line from file assp_sync.cfg for GroupsReloadEvery
 0 - synchronization not configured
 1 - out of sync - running master mode
 2 - in sync - running  mastermode
 3 - in sync - running slave mode
 4 - in sync - running master mode (wait to reach state 2)
"
    ::= {GroupsReloadEvery 6}

Groups  OBJECT-TYPE
    SYNTAX      OCTET STRING
    MAX-ACCESS  read-write
    STATUS      current
    DESCRIPTION
"

 If you don't want to use group definitions, leave this field blank otherwise a file definition like 'file:files/groups.txt' is required.
 Group definitions could be used in any other configuration value where multiple user names, email addresses or domain names or IP addresses could be defined.
 Groups are defined and used using the same syntax [group-name] (including the brackets) in a single line. In the configuration parameters, the line [group-name] will be replaced by the content of the group definition, that is done here.
 All group definitions are case sensitive. Group names can only contain the following characters: A-Z, a-z, 0-9, - , _ and @ !
 The structure of this file has to be as follows:
 
 [super_spamlovers]
 myBoss
 ldap:{host=&gt;my_LDAP_server:389,base=&gt;(sep)DC=domain,DC=tld(sep),user=&gt;(sep)CN=admin,DC=domain(sep),password=&gt;(sep)pass(sep),timeout=&gt;2,scheme=&gt;ldap,STARTTLS=&gt;1,version=&gt;3},{(CN=management)}{member},{(CN=%USERID%)}{mailaddress}
 entry
 exec:/usr/bin/list_postfix_users --domain mydomain --group postoffice
 entry
 ...
 
 [admins]
 ldap:{host=&gt;domino1.mydomain.com:389,base=&gt;(sep)DC=domain,DC=tld(sep),user=&gt;(sep)Administrator(sep),password=&gt;(sep)pass(sep),timeout=&gt;2,scheme=&gt;ldap,STARTTLS=&gt;1,version=&gt;3},{(CN=LocalDomainAdmins)}{member},{(CN=%USERID%)}{mailaddress}
 entry
 entry
 ...
 
 [specialIPList]
 1.2.3.4
 123.234.0.0/16
 ::1
 
 Lines starting with a # OR ; are consider a comment. Empty lines will be ignored. An group definition stopps, if a new group definition starts or at the end of the file. Comments are not allowed inside a definition line.
 
 There are two possible methods to import entries from an external source in to a group - the execution of a system command or a LDAP query.
 To import entries via a system command like (eg. cat|grep or find or your self made shell script), write a single line that begins with exec: followed by the command to be executed - like:
 exec:cat /etc/anydir/*.txt|grep '@'
 The executed system command has to write a comma(,) or pipe(|) or linefeed(LF,CRLF) separated list of entries to STDOUT, that should become part of that group, where this line is used. There could be multiple and any combination of entry types in one group definition.
 
 If you are familar with the usage of LDAP, you can define LDAP querys to import entries from one or more LDAP server. This is done, defining one query per line. The syntax of such a line is:
 
 ldap:{host_and_protocol},{LDAP_group_query_filter}{LDAP_group_query_attribut_to_return},{LDAP_entry_query_filter}{LDAP_entry_query_attribut_to_return}
 
 If the 'host_and_protocol' part is empty {}, the default LDAP configuration will be used. An 'host_and_protocol' part should contain the following entries in the following structure:
 {host=&gt;127.0.0.1:389,base=&gt;(sep)DC=domain,DC=tld(sep),user=&gt;(sep)...(sep),password=&gt;(sep)pass(sep),timeout=&gt;..,scheme=&gt;ldap/ldaps,STARTTLS=&gt;0/1,version=&gt;2/3}
 The 'host' has to be set, if you want to define any other LDAP parameter. If any other parameter is not defined, the default LDAP configuration value will be used, except user and password. The port definition (:xxx) in the host setting is optional - if not defined, the default LDAP ports 389(LDAP) and 636(LDAPS) will be used. It is possible to define a comma(,) separated list of hosts for failover functionality like 'host=>'localhost:389,192.168.1.1:389,....'' - notice the quotes as terminator which are required in this case!
 The value of the base, password and user parameter has to start and end with a single character (sep) as terminator, that is not part of the value
 and is not used in the value. The parameter 'base' defines the LDAP search root like LDAPRoot .
 
 The 'LDAP_group_query_filter' and 'LDAP_group_query_attribut_to_return' are used to query a LDAP group for it's members (users). The resulting list will contain the requested attributes of all group members. The definition of these two parameters could look as follows:
 {(&(objectclass=dominoGroup)(CN=LocalDomainAdmins))}{member}
 
 It is possible to modify each returned value with a callback-code. This is for example usefull for MS-AD querys on the attribute 'proxyaddresses', which returns a list of all available mail addresses (SMTP,smtp,X400...).
 
 example: ldap:{},{(&(CN=firstname lastname)(proxyaddresses=smtp:*))<=s/^\s*smtp:\s*(.+)\s*$/$1/i}{proxyaddresses},{}{}
 
 <= is the required separator, s/^\s*smtp:\s*(.+)\s*$/$1/i is the callback code.
 The callback code has to return a value of not zero or undef on success. The code gets the LDAP result in the variable $_ and has to modify this variable in place on success.
 It is not allowed to use any of the following characters in the callback definiton of a ldap line: {}| 
 
 The 'LDAP_entry_query_filter' and 'LDAP_entry_query_attribut_to_return' are used to query each member from the first query, for it's email address. The literal '%USERID%' in the 'LDAP_entry_query_filter' will be replaced by each LDAP-attribute result of the first query. The definition of these two parameters could look as follows:
 {(&(objecttype=person)(CN=%USERID%)(o=%USERID%))}{mailaddress}
 or more simple
 {(&(objecttype=person)(CN=%USERID%))}{mailaddress}
 
 An callback code could be used the same way like for 'LDAP_group_query_filter' - {(&(objecttype=person)(CN=%USERID%))<=callback-code}{mailaddress}.
 
 To break long lines in to multiple, terminate a continued line with a slash '/'
 If you are able to get all results (eg. email addresses or domain names) with the 'LDAP_group_query' query, leave the definition of 'LDAP_entry_query_filter' and 'LDAP_entry_query_attribut_to_return' empty {}{}.
 
 The result of each group definition will be stored in a file in files/group_export/GROUPNAME.txt.
 The groups are build at every start of assp and if the defined file or an include file is stored (changed file time). To force a reload of all groups, open the file and click 'Save changes' or change the file time with an external shell script. It is also possible to use GroupsReloadEvery, to reload the Groups definition in time intervals, if the exec: or ldap: option are used.
"
    REFERENCE "Address and Domain Groups*"
    DEFVAL { "" }
    ::= {Groupdefinition 947}

SPAMControl  OBJECT IDENTIFIER ::= {asspConfig 4}
redRe  OBJECT-TYPE
    SYNTAX      OCTET STRING
    MAX-ACCESS  read-write
    STATUS      current
    DESCRIPTION
"
If an email matches this Perl regular expression it will be considered redlisted.
 redRe detects tags to process a mail like the recipient were redlisted - nothing else (no redlist addition/removal).
 The Redlist serves two purposes:
1) the Redlist is a list of addresses that cannot contribute to the
whitelist and which are not considered local even if their mail is
from a local computer. For example, if someone goes on a vacation and
turns on their autoresponder, put them on the redlist until
they return. Then as they reply to every spam they receive they won't
corrupt your non-spam collection or whitelist: \[autoreply\]
2) Redlisted addresses will not be added to the Whitelist when your
local user sends mail to that address, thereby preventing accidental
pollution of the Whitelist by, say, inadvertent replies by your
users to mails from the spammer.
Redlisted messages will not be stored in the SPAM/NOTSPAM-collection. As all fields marked by * this field accepts
a list separated by | or a specified file 'file:files/redre.txt'. 
"
    REFERENCE "Regular Expression to Identify Redlisted Mail*"
    DEFVAL { "file:files/redre.txt" }
    ::= {SPAMControl 20}

syncStatredRe  OBJECT-TYPE
    SYNTAX      OCTET STRING
    MAX-ACCESS  read-only
    STATUS      current
    DESCRIPTION
"
synchronization status for redRe
-1 - redRe could not be synchronized
 0 - synchronization not configured
 1 - out of sync - running master mode
 2 - in sync - running  mastermode
 3 - in sync - running slave mode
 4 - in sync - running master mode (wait to reach state 2)
"
    ::= {redRe 5}

syncStatStrredRe  OBJECT-TYPE
    SYNTAX      OCTET STRING
    MAX-ACCESS  read-only
    STATUS      current
    DESCRIPTION
"
synchronization status line from file assp_sync.cfg for redRe
 0 - synchronization not configured
 1 - out of sync - running master mode
 2 - in sync - running  mastermode
 3 - in sync - running slave mode
 4 - in sync - running master mode (wait to reach state 2)
"
    ::= {redRe 6}

EmailWhiteRemovalToRed  OBJECT-TYPE
    SYNTAX      OCTET STRING
    MAX-ACCESS  read-write
    STATUS      current
    DESCRIPTION
"
If set addresses which are removed from Whitelist via email-interface will automatically be added to the Redlist. The address can only be added again to the Whitelist after it is removed from the Redlist.
"
    REFERENCE "Add  Whitelist Removals To Redlist "
    DEFVAL { "" }
    ::= {SPAMControl 21}

syncStatEmailWhiteRemovalToRed  OBJECT-TYPE
    SYNTAX      OCTET STRING
    MAX-ACCESS  read-only
    STATUS      current
    DESCRIPTION
"
synchronization status for EmailWhiteRemovalToRed
-1 - EmailWhiteRemovalToRed could not be synchronized
 0 - synchronization not configured
 1 - out of sync - running master mode
 2 - in sync - running  mastermode
 3 - in sync - running slave mode
 4 - in sync - running master mode (wait to reach state 2)
"
    ::= {EmailWhiteRemovalToRed 5}

syncStatStrEmailWhiteRemovalToRed  OBJECT-TYPE
    SYNTAX      OCTET STRING
    MAX-ACCESS  read-only
    STATUS      current
    DESCRIPTION
"
synchronization status line from file assp_sync.cfg for EmailWhiteRemovalToRed
 0 - synchronization not configured
 1 - out of sync - running master mode
 2 - in sync - running  mastermode
 3 - in sync - running slave mode
 4 - in sync - running master mode (wait to reach state 2)
"
    ::= {EmailWhiteRemovalToRed 6}

SpamError  OBJECT-TYPE
    SYNTAX      OCTET STRING
    MAX-ACCESS  read-write
    STATUS      current
    DESCRIPTION
"
SMTP error message to reject spam. The literal LOCALDOMAIN will be replaced by the recipient domain. For example:554 5.7.1 Mail appears to be unsolicited -- send error reports to postmaster@LOCALDOMAIN. 
"
    REFERENCE "Spam Error"
    DEFVAL { "554 5.7.1 Mail appears to be unsolicited -- send error reports to postmaster@LOCALDOMAIN" }
    ::= {SPAMControl 22}

syncStatSpamError  OBJECT-TYPE
    SYNTAX      OCTET STRING
    MAX-ACCESS  read-only
    STATUS      current
    DESCRIPTION
"
synchronization status for SpamError
-1 - SpamError could not be synchronized
 0 - synchronization not configured
 1 - out of sync - running master mode
 2 - in sync - running  mastermode
 3 - in sync - running slave mode
 4 - in sync - running master mode (wait to reach state 2)
"
    ::= {SpamError 5}

syncStatStrSpamError  OBJECT-TYPE
    SYNTAX      OCTET STRING
    MAX-ACCESS  read-only
    STATUS      current
    DESCRIPTION
"
synchronization status line from file assp_sync.cfg for SpamError
 0 - synchronization not configured
 1 - out of sync - running master mode
 2 - in sync - running  mastermode
 3 - in sync - running slave mode
 4 - in sync - running master mode (wait to reach state 2)
"
    ::= {SpamError 6}

noGriplistUpload  OBJECT-TYPE
    SYNTAX      OCTET STRING
    MAX-ACCESS  read-write
    STATUS      current
    DESCRIPTION
"
Check this to disable the Griplist upload when rebuildspamdb runs. The Griplist contains IPs and their value between 0 and 1, lower is less spammy, higher is more spammy. This value is called the grip value. 
"
    REFERENCE "Don't Upload Griplist Stats"
    DEFVAL { "" }
    ::= {SPAMControl 23}

syncStatnoGriplistUpload  OBJECT-TYPE
    SYNTAX      OCTET STRING
    MAX-ACCESS  read-only
    STATUS      current
    DESCRIPTION
"
synchronization status for noGriplistUpload
-1 - noGriplistUpload could not be synchronized
 0 - synchronization not configured
 1 - out of sync - running master mode
 2 - in sync - running  mastermode
 3 - in sync - running slave mode
 4 - in sync - running master mode (wait to reach state 2)
"
    ::= {noGriplistUpload 5}

syncStatStrnoGriplistUpload  OBJECT-TYPE
    SYNTAX      OCTET STRING
    MAX-ACCESS  read-only
    STATUS      current
    DESCRIPTION
"
synchronization status line from file assp_sync.cfg for noGriplistUpload
 0 - synchronization not configured
 1 - out of sync - running master mode
 2 - in sync - running  mastermode
 3 - in sync - running slave mode
 4 - in sync - running master mode (wait to reach state 2)
"
    ::= {noGriplistUpload 6}

noGriplistDownload  OBJECT-TYPE
    SYNTAX      OCTET STRING
    MAX-ACCESS  read-write
    STATUS      current
    DESCRIPTION
"
Set this checkbox, if you don't use the Griplist. You have to disable also noGriplistUpload to download the Griplist.
"
    REFERENCE "Don't auto-download the Griplist file"
    DEFVAL { "" }
    ::= {SPAMControl 24}

syncStatnoGriplistDownload  OBJECT-TYPE
    SYNTAX      OCTET STRING
    MAX-ACCESS  read-only
    STATUS      current
    DESCRIPTION
"
synchronization status for noGriplistDownload
-1 - noGriplistDownload could not be synchronized
 0 - synchronization not configured
 1 - out of sync - running master mode
 2 - in sync - running  mastermode
 3 - in sync - running slave mode
 4 - in sync - running master mode (wait to reach state 2)
"
    ::= {noGriplistDownload 5}

syncStatStrnoGriplistDownload  OBJECT-TYPE
    SYNTAX      OCTET STRING
    MAX-ACCESS  read-only
    STATUS      current
    DESCRIPTION
"
synchronization status line from file assp_sync.cfg for noGriplistDownload
 0 - synchronization not configured
 1 - out of sync - running master mode
 2 - in sync - running  mastermode
 3 - in sync - running slave mode
 4 - in sync - running master mode (wait to reach state 2)
"
    ::= {noGriplistDownload 6}

AddIntendedForHeader  OBJECT-TYPE
    SYNTAX      OCTET STRING
    MAX-ACCESS  read-write
    STATUS      current
    DESCRIPTION
"
Adds two lines to the email header: 'X-Assp-Intended-For: user@domain' and 'X-Assp-Envelope-From: user@domain'.
"
    REFERENCE "Add Envelope-Recipient Header"
    DEFVAL { "1" }
    ::= {SPAMControl 25}

syncStatAddIntendedForHeader  OBJECT-TYPE
    SYNTAX      OCTET STRING
    MAX-ACCESS  read-only
    STATUS      current
    DESCRIPTION
"
synchronization status for AddIntendedForHeader
-1 - AddIntendedForHeader could not be synchronized
 0 - synchronization not configured
 1 - out of sync - running master mode
 2 - in sync - running  mastermode
 3 - in sync - running slave mode
 4 - in sync - running master mode (wait to reach state 2)
"
    ::= {AddIntendedForHeader 5}

syncStatStrAddIntendedForHeader  OBJECT-TYPE
    SYNTAX      OCTET STRING
    MAX-ACCESS  read-only
    STATUS      current
    DESCRIPTION
"
synchronization status line from file assp_sync.cfg for AddIntendedForHeader
 0 - synchronization not configured
 1 - out of sync - running master mode
 2 - in sync - running  mastermode
 3 - in sync - running slave mode
 4 - in sync - running master mode (wait to reach state 2)
"
    ::= {AddIntendedForHeader 6}

NoExternalSpamProb  OBJECT-TYPE
    SYNTAX      OCTET STRING
    MAX-ACCESS  read-write
    STATUS      current
    DESCRIPTION
"
Check this box if you don't want your X-Assp-Spam-Prob header on external mail
 Note this means mail from local users to local users will also be missing the header.
"
    REFERENCE "Block Outgoing Spam-Prob header"
    DEFVAL { "1" }
    ::= {SPAMControl 26}

syncStatNoExternalSpamProb  OBJECT-TYPE
    SYNTAX      OCTET STRING
    MAX-ACCESS  read-only
    STATUS      current
    DESCRIPTION
"
synchronization status for NoExternalSpamProb
-1 - NoExternalSpamProb could not be synchronized
 0 - synchronization not configured
 1 - out of sync - running master mode
 2 - in sync - running  mastermode
 3 - in sync - running slave mode
 4 - in sync - running master mode (wait to reach state 2)
"
    ::= {NoExternalSpamProb 5}

syncStatStrNoExternalSpamProb  OBJECT-TYPE
    SYNTAX      OCTET STRING
    MAX-ACCESS  read-only
    STATUS      current
    DESCRIPTION
"
synchronization status line from file assp_sync.cfg for NoExternalSpamProb
 0 - synchronization not configured
 1 - out of sync - running master mode
 2 - in sync - running  mastermode
 3 - in sync - running slave mode
 4 - in sync - running master mode (wait to reach state 2)
"
    ::= {NoExternalSpamProb 6}

AddSpamHeader  OBJECT-TYPE
    SYNTAX      OCTET STRING
    MAX-ACCESS  read-write
    STATUS      current
    DESCRIPTION
"
Adds a line to the email header 'X-Assp-Spam: YES' if the message is spam, or 'X-Assp-Spam: YES (Probably)' if it is possibly spam.
"
    REFERENCE "Add Spam Header"
    DEFVAL { "1" }
    ::= {SPAMControl 27}

syncStatAddSpamHeader  OBJECT-TYPE
    SYNTAX      OCTET STRING
    MAX-ACCESS  read-only
    STATUS      current
    DESCRIPTION
"
synchronization status for AddSpamHeader
-1 - AddSpamHeader could not be synchronized
 0 - synchronization not configured
 1 - out of sync - running master mode
 2 - in sync - running  mastermode
 3 - in sync - running slave mode
 4 - in sync - running master mode (wait to reach state 2)
"
    ::= {AddSpamHeader 5}

syncStatStrAddSpamHeader  OBJECT-TYPE
    SYNTAX      OCTET STRING
    MAX-ACCESS  read-only
    STATUS      current
    DESCRIPTION
"
synchronization status line from file assp_sync.cfg for AddSpamHeader
 0 - synchronization not configured
 1 - out of sync - running master mode
 2 - in sync - running  mastermode
 3 - in sync - running slave mode
 4 - in sync - running master mode (wait to reach state 2)
"
    ::= {AddSpamHeader 6}

AddCustomHeader  OBJECT-TYPE
    SYNTAX      OCTET STRING
    MAX-ACCESS  read-write
    STATUS      current
    DESCRIPTION
"
Adds a line to the email header if the message is spam. For example: 
"
    REFERENCE "Add Custom Header"
    DEFVAL { "X-Spam-Status:yes" }
    ::= {SPAMControl 28}

syncStatAddCustomHeader  OBJECT-TYPE
    SYNTAX      OCTET STRING
    MAX-ACCESS  read-only
    STATUS      current
    DESCRIPTION
"
synchronization status for AddCustomHeader
-1 - AddCustomHeader could not be synchronized
 0 - synchronization not configured
 1 - out of sync - running master mode
 2 - in sync - running  mastermode
 3 - in sync - running slave mode
 4 - in sync - running master mode (wait to reach state 2)
"
    ::= {AddCustomHeader 5}

syncStatStrAddCustomHeader  OBJECT-TYPE
    SYNTAX      OCTET STRING
    MAX-ACCESS  read-only
    STATUS      current
    DESCRIPTION
"
synchronization status line from file assp_sync.cfg for AddCustomHeader
 0 - synchronization not configured
 1 - out of sync - running master mode
 2 - in sync - running  mastermode
 3 - in sync - running slave mode
 4 - in sync - running master mode (wait to reach state 2)
"
    ::= {AddCustomHeader 6}

AddLevelHeader  OBJECT-TYPE
    SYNTAX      OCTET STRING
    MAX-ACCESS  read-write
    STATUS      current
    DESCRIPTION
"
Adds a line to the email header 'X-Assp-Spam-Level: **** ' showing the total message score represented by stars (1 - 20), every star represents five scoring points.
"
    REFERENCE "Add Graphical Level Header"
    DEFVAL { "1" }
    ::= {SPAMControl 29}

syncStatAddLevelHeader  OBJECT-TYPE
    SYNTAX      OCTET STRING
    MAX-ACCESS  read-only
    STATUS      current
    DESCRIPTION
"
synchronization status for AddLevelHeader
-1 - AddLevelHeader could not be synchronized
 0 - synchronization not configured
 1 - out of sync - running master mode
 2 - in sync - running  mastermode
 3 - in sync - running slave mode
 4 - in sync - running master mode (wait to reach state 2)
"
    ::= {AddLevelHeader 5}

syncStatStrAddLevelHeader  OBJECT-TYPE
    SYNTAX      OCTET STRING
    MAX-ACCESS  read-only
    STATUS      current
    DESCRIPTION
"
synchronization status line from file assp_sync.cfg for AddLevelHeader
 0 - synchronization not configured
 1 - out of sync - running master mode
 2 - in sync - running  mastermode
 3 - in sync - running slave mode
 4 - in sync - running master mode (wait to reach state 2)
"
    ::= {AddLevelHeader 6}

AddSubjectHeader  OBJECT-TYPE
    SYNTAX      OCTET STRING
    MAX-ACCESS  read-write
    STATUS      current
    DESCRIPTION
"
Adds a line to the email header 'X-ASSP-Original-Subject: the subject'.
"
    REFERENCE "Add X-ASSP-Original-Subject Header"
    DEFVAL { "" }
    ::= {SPAMControl 30}

syncStatAddSubjectHeader  OBJECT-TYPE
    SYNTAX      OCTET STRING
    MAX-ACCESS  read-only
    STATUS      current
    DESCRIPTION
"
synchronization status for AddSubjectHeader
-1 - AddSubjectHeader could not be synchronized
 0 - synchronization not configured
 1 - out of sync - running master mode
 2 - in sync - running  mastermode
 3 - in sync - running slave mode
 4 - in sync - running master mode (wait to reach state 2)
"
    ::= {AddSubjectHeader 5}

syncStatStrAddSubjectHeader  OBJECT-TYPE
    SYNTAX      OCTET STRING
    MAX-ACCESS  read-only
    STATUS      current
    DESCRIPTION
"
synchronization status line from file assp_sync.cfg for AddSubjectHeader
 0 - synchronization not configured
 1 - out of sync - running master mode
 2 - in sync - running  mastermode
 3 - in sync - running slave mode
 4 - in sync - running master mode (wait to reach state 2)
"
    ::= {AddSubjectHeader 6}

AddSpamReasonHeader  OBJECT-TYPE
    SYNTAX      OCTET STRING
    MAX-ACCESS  read-write
    STATUS      current
    DESCRIPTION
"
Adds a line to the email header 'X-Assp-Spam-Reason: ' explaining why the message is spam.
"
    REFERENCE "Add Spam Reason Header"
    DEFVAL { "1" }
    ::= {SPAMControl 31}

syncStatAddSpamReasonHeader  OBJECT-TYPE
    SYNTAX      OCTET STRING
    MAX-ACCESS  read-only
    STATUS      current
    DESCRIPTION
"
synchronization status for AddSpamReasonHeader
-1 - AddSpamReasonHeader could not be synchronized
 0 - synchronization not configured
 1 - out of sync - running master mode
 2 - in sync - running  mastermode
 3 - in sync - running slave mode
 4 - in sync - running master mode (wait to reach state 2)
"
    ::= {AddSpamReasonHeader 5}

syncStatStrAddSpamReasonHeader  OBJECT-TYPE
    SYNTAX      OCTET STRING
    MAX-ACCESS  read-only
    STATUS      current
    DESCRIPTION
"
synchronization status line from file assp_sync.cfg for AddSpamReasonHeader
 0 - synchronization not configured
 1 - out of sync - running master mode
 2 - in sync - running  mastermode
 3 - in sync - running slave mode
 4 - in sync - running master mode (wait to reach state 2)
"
    ::= {AddSpamReasonHeader 6}

StoreASSPHeader  OBJECT-TYPE
    SYNTAX      OCTET STRING
    MAX-ACCESS  read-write
    STATUS      current
    DESCRIPTION
"
Add 'X-Assp-' to the collected spam-mails.
"
    REFERENCE "Store Assp-Header into Spam Collection"
    DEFVAL { "" }
    ::= {SPAMControl 877}

syncStatStoreASSPHeader  OBJECT-TYPE
    SYNTAX      OCTET STRING
    MAX-ACCESS  read-only
    STATUS      current
    DESCRIPTION
"
synchronization status for StoreASSPHeader
-1 - StoreASSPHeader could not be synchronized
 0 - synchronization not configured
 1 - out of sync - running master mode
 2 - in sync - running  mastermode
 3 - in sync - running slave mode
 4 - in sync - running master mode (wait to reach state 2)
"
    ::= {StoreASSPHeader 5}

syncStatStrStoreASSPHeader  OBJECT-TYPE
    SYNTAX      OCTET STRING
    MAX-ACCESS  read-only
    STATUS      current
    DESCRIPTION
"
synchronization status line from file assp_sync.cfg for StoreASSPHeader
 0 - synchronization not configured
 1 - out of sync - running master mode
 2 - in sync - running  mastermode
 3 - in sync - running slave mode
 4 - in sync - running master mode (wait to reach state 2)
"
    ::= {StoreASSPHeader 6}

NotSpamTag  OBJECT-TYPE
    SYNTAX      OCTET STRING
    MAX-ACCESS  read-write
    STATUS      current
    DESCRIPTION
"
If an incoming email subject contains the TAG generated based on this value, it will be considered as defined in NotSpamTagProc . The literal 'NOTSPAMTAG' (will be replaced by a 10 digit not-spam-tag) can be used in any 5xx error reply (SpamError , RBLError , scriptError , URIBLerror ....) to ask for resending the mail with the TAG in the subject.
 Randomly picked up bit sequences of the text defined here, are used as 'SALT' to calculate a 10 digit not-spam-tag. This value must be at least 12 characters long. Leave this value empty to disable this feature.
 To define your own static TAGs, use whiteRe and/or npRe and change the error reply definitions accordingly.
 To generate a random 80 character string, run 'perl -e 'print chr(int(rand(94))+33)for(0...79);'' from command line and copy and paste the result to here.
"
    REFERENCE "Ham Password SALT"
    DEFVAL { "" }
    ::= {SPAMControl 1031}

syncStatNotSpamTag  OBJECT-TYPE
    SYNTAX      OCTET STRING
    MAX-ACCESS  read-only
    STATUS      current
    DESCRIPTION
"
synchronization status for NotSpamTag
-1 - NotSpamTag could not be synchronized
 0 - synchronization not configured
 1 - out of sync - running master mode
 2 - in sync - running  mastermode
 3 - in sync - running slave mode
 4 - in sync - running master mode (wait to reach state 2)
"
    ::= {NotSpamTag 5}

syncStatStrNotSpamTag  OBJECT-TYPE
    SYNTAX      OCTET STRING
    MAX-ACCESS  read-only
    STATUS      current
    DESCRIPTION
"
synchronization status line from file assp_sync.cfg for NotSpamTag
 0 - synchronization not configured
 1 - out of sync - running master mode
 2 - in sync - running  mastermode
 3 - in sync - running slave mode
 4 - in sync - running master mode (wait to reach state 2)
"
    ::= {NotSpamTag 6}

NotSpamTagProc  OBJECT-TYPE
    SYNTAX      OCTET STRING
    MAX-ACCESS  read-write
    STATUS      current
    DESCRIPTION
"
If a sender uses the Not-Spam-Tag , how should the mail be processed. Regardless of this setting, the IP address of the sender will not be penalized if a NotSpamTag is found.
"
    REFERENCE "Not-Spam-Tag will consider the mail as"
    DEFVAL { "1" }
    ::= {SPAMControl 1032}

syncStatNotSpamTagProc  OBJECT-TYPE
    SYNTAX      OCTET STRING
    MAX-ACCESS  read-only
    STATUS      current
    DESCRIPTION
"
synchronization status for NotSpamTagProc
-1 - NotSpamTagProc could not be synchronized
 0 - synchronization not configured
 1 - out of sync - running master mode
 2 - in sync - running  mastermode
 3 - in sync - running slave mode
 4 - in sync - running master mode (wait to reach state 2)
"
    ::= {NotSpamTagProc 5}

syncStatStrNotSpamTagProc  OBJECT-TYPE
    SYNTAX      OCTET STRING
    MAX-ACCESS  read-only
    STATUS      current
    DESCRIPTION
"
synchronization status line from file assp_sync.cfg for NotSpamTagProc
 0 - synchronization not configured
 1 - out of sync - running master mode
 2 - in sync - running  mastermode
 3 - in sync - running slave mode
 4 - in sync - running master mode (wait to reach state 2)
"
    ::= {NotSpamTagProc 6}

CopySpamampHam  OBJECT IDENTIFIER ::= {asspConfig 5}
sendAllSpam  OBJECT-TYPE
    SYNTAX      OCTET STRING
    MAX-ACCESS  read-write
    STATUS      current
    DESCRIPTION
"
If this is set ASSP will deliver a copy of spam mails to this address. For example: spammaster@mydomain.com. The literal USERNAME is replaced by the user part of the recipient, the literal DOMAIN is replaced by the domain part of the recipient.
 For example: USERNAME@Spam.DOMAIN, USERNAME+Spam@DOMAIN, catchallspamthis@DOMAIN. Separate multiple entries by comma or space. To deliver copy of spams based on the domain name (only some special hosted domains), use ccSpamInDomain .
"
    REFERENCE "Copy Spam and Send to this Address"
    DEFVAL { "" }
    ::= {CopySpamampHam 32}

syncStatsendAllSpam  OBJECT-TYPE
    SYNTAX      OCTET STRING
    MAX-ACCESS  read-only
    STATUS      current
    DESCRIPTION
"
synchronization status for sendAllSpam
-1 - sendAllSpam could not be synchronized
 0 - synchronization not configured
 1 - out of sync - running master mode
 2 - in sync - running  mastermode
 3 - in sync - running slave mode
 4 - in sync - running master mode (wait to reach state 2)
"
    ::= {sendAllSpam 5}

syncStatStrsendAllSpam  OBJECT-TYPE
    SYNTAX      OCTET STRING
    MAX-ACCESS  read-only
    STATUS      current
    DESCRIPTION
"
synchronization status line from file assp_sync.cfg for sendAllSpam
 0 - synchronization not configured
 1 - out of sync - running master mode
 2 - in sync - running  mastermode
 3 - in sync - running slave mode
 4 - in sync - running master mode (wait to reach state 2)
"
    ::= {sendAllSpam 6}

sendAllDestination  OBJECT-TYPE
    SYNTAX      OCTET STRING
    MAX-ACCESS  read-write
    STATUS      current
    DESCRIPTION
"
Port to connect to when Spam messages are copied. If blank they go to the main SMTP Destination. eg '10.0.1.3:1025', 'SSL:10.0.1.3:465', '1025', etc.
"
    REFERENCE "Copy Spam SMTP Destination"
    DEFVAL { "" }
    ::= {CopySpamampHam 33}

syncStatsendAllDestination  OBJECT-TYPE
    SYNTAX      OCTET STRING
    MAX-ACCESS  read-only
    STATUS      current
    DESCRIPTION
"
synchronization status for sendAllDestination
-1 - sendAllDestination could not be synchronized
 0 - synchronization not configured
 1 - out of sync - running master mode
 2 - in sync - running  mastermode
 3 - in sync - running slave mode
 4 - in sync - running master mode (wait to reach state 2)
"
    ::= {sendAllDestination 5}

syncStatStrsendAllDestination  OBJECT-TYPE
    SYNTAX      OCTET STRING
    MAX-ACCESS  read-only
    STATUS      current
    DESCRIPTION
"
synchronization status line from file assp_sync.cfg for sendAllDestination
 0 - synchronization not configured
 1 - out of sync - running master mode
 2 - in sync - running  mastermode
 3 - in sync - running slave mode
 4 - in sync - running master mode (wait to reach state 2)
"
    ::= {sendAllDestination 6}

ccSpamFilter  OBJECT-TYPE
    SYNTAX      OCTET STRING
    MAX-ACCESS  read-write
    STATUS      current
    DESCRIPTION
"
Restricts Copy Spam to these recipients. Accepts specific addresses (user@domain.com), user parts (user) or entire domains (@domain.com). Wildcards are supported (fribo*@domain.com).
"
    REFERENCE "Copy Spam to these Recipients Only*"
    DEFVAL { "" }
    ::= {CopySpamampHam 34}

syncStatccSpamFilter  OBJECT-TYPE
    SYNTAX      OCTET STRING
    MAX-ACCESS  read-only
    STATUS      current
    DESCRIPTION
"
synchronization status for ccSpamFilter
-1 - ccSpamFilter could not be synchronized
 0 - synchronization not configured
 1 - out of sync - running master mode
 2 - in sync - running  mastermode
 3 - in sync - running slave mode
 4 - in sync - running master mode (wait to reach state 2)
"
    ::= {ccSpamFilter 5}

syncStatStrccSpamFilter  OBJECT-TYPE
    SYNTAX      OCTET STRING
    MAX-ACCESS  read-only
    STATUS      current
    DESCRIPTION
"
synchronization status line from file assp_sync.cfg for ccSpamFilter
 0 - synchronization not configured
 1 - out of sync - running master mode
 2 - in sync - running  mastermode
 3 - in sync - running slave mode
 4 - in sync - running master mode (wait to reach state 2)
"
    ::= {ccSpamFilter 6}

ccSpamAlways  OBJECT-TYPE
    SYNTAX      OCTET STRING
    MAX-ACCESS  read-write
    STATUS      current
    DESCRIPTION
"
Copy Spam to these recipients regardless of collection mode. Accepts specific addresses (user@domain.com), user parts (user) or entire domains (@domain.com).  Wildcards are supported (fribo*@domain.com).
"
    REFERENCE "Copy Spam to these Recipients always*"
    DEFVAL { "" }
    ::= {CopySpamampHam 35}

syncStatccSpamAlways  OBJECT-TYPE
    SYNTAX      OCTET STRING
    MAX-ACCESS  read-only
    STATUS      current
    DESCRIPTION
"
synchronization status for ccSpamAlways
-1 - ccSpamAlways could not be synchronized
 0 - synchronization not configured
 1 - out of sync - running master mode
 2 - in sync - running  mastermode
 3 - in sync - running slave mode
 4 - in sync - running master mode (wait to reach state 2)
"
    ::= {ccSpamAlways 5}

syncStatStrccSpamAlways  OBJECT-TYPE
    SYNTAX      OCTET STRING
    MAX-ACCESS  read-only
    STATUS      current
    DESCRIPTION
"
synchronization status line from file assp_sync.cfg for ccSpamAlways
 0 - synchronization not configured
 1 - out of sync - running master mode
 2 - in sync - running  mastermode
 3 - in sync - running slave mode
 4 - in sync - running master mode (wait to reach state 2)
"
    ::= {ccSpamAlways 6}

ccSpamNeverRe  OBJECT-TYPE
    SYNTAX      OCTET STRING
    MAX-ACCESS  read-write
    STATUS      current
    DESCRIPTION
"
Never Copy Spam regardless of collection mode. Put anything here to identify messages which should not be copied.
"
    REFERENCE "Do Not Copy Spam Regex*"
    DEFVAL { "" }
    ::= {CopySpamampHam 36}

syncStatccSpamNeverRe  OBJECT-TYPE
    SYNTAX      OCTET STRING
    MAX-ACCESS  read-only
    STATUS      current
    DESCRIPTION
"
synchronization status for ccSpamNeverRe
-1 - ccSpamNeverRe could not be synchronized
 0 - synchronization not configured
 1 - out of sync - running master mode
 2 - in sync - running  mastermode
 3 - in sync - running slave mode
 4 - in sync - running master mode (wait to reach state 2)
"
    ::= {ccSpamNeverRe 5}

syncStatStrccSpamNeverRe  OBJECT-TYPE
    SYNTAX      OCTET STRING
    MAX-ACCESS  read-only
    STATUS      current
    DESCRIPTION
"
synchronization status line from file assp_sync.cfg for ccSpamNeverRe
 0 - synchronization not configured
 1 - out of sync - running master mode
 2 - in sync - running  mastermode
 3 - in sync - running slave mode
 4 - in sync - running master mode (wait to reach state 2)
"
    ::= {ccSpamNeverRe 6}

ccMaxScore  OBJECT-TYPE
    SYNTAX      OCTET STRING
    MAX-ACCESS  read-write
    STATUS      current
    DESCRIPTION
"
Messages whose score exceeds this threshold will not be copied.  For example: 75
"
    REFERENCE "Do Not Copy Messages Above This MessageTotal score"
    DEFVAL { "" }
    ::= {CopySpamampHam 37}

syncStatccMaxScore  OBJECT-TYPE
    SYNTAX      OCTET STRING
    MAX-ACCESS  read-only
    STATUS      current
    DESCRIPTION
"
synchronization status for ccMaxScore
-1 - ccMaxScore could not be synchronized
 0 - synchronization not configured
 1 - out of sync - running master mode
 2 - in sync - running  mastermode
 3 - in sync - running slave mode
 4 - in sync - running master mode (wait to reach state 2)
"
    ::= {ccMaxScore 5}

syncStatStrccMaxScore  OBJECT-TYPE
    SYNTAX      OCTET STRING
    MAX-ACCESS  read-only
    STATUS      current
    DESCRIPTION
"
synchronization status line from file assp_sync.cfg for ccMaxScore
 0 - synchronization not configured
 1 - out of sync - running master mode
 2 - in sync - running  mastermode
 3 - in sync - running slave mode
 4 - in sync - running master mode (wait to reach state 2)
"
    ::= {ccMaxScore 6}

ccMaxBytes  OBJECT-TYPE
    SYNTAX      OCTET STRING
    MAX-ACCESS  read-write
    STATUS      current
    DESCRIPTION
"
CCMail will cut off Spam mails, thereby reducing the load considerably (recommended).
"
    REFERENCE "Restrict Copy Spam to MaxBytes"
    DEFVAL { "1" }
    ::= {CopySpamampHam 38}

syncStatccMaxBytes  OBJECT-TYPE
    SYNTAX      OCTET STRING
    MAX-ACCESS  read-only
    STATUS      current
    DESCRIPTION
"
synchronization status for ccMaxBytes
-1 - ccMaxBytes could not be synchronized
 0 - synchronization not configured
 1 - out of sync - running master mode
 2 - in sync - running  mastermode
 3 - in sync - running slave mode
 4 - in sync - running master mode (wait to reach state 2)
"
    ::= {ccMaxBytes 5}

syncStatStrccMaxBytes  OBJECT-TYPE
    SYNTAX      OCTET STRING
    MAX-ACCESS  read-only
    STATUS      current
    DESCRIPTION
"
synchronization status line from file assp_sync.cfg for ccMaxBytes
 0 - synchronization not configured
 1 - out of sync - running master mode
 2 - in sync - running  mastermode
 3 - in sync - running slave mode
 4 - in sync - running master mode (wait to reach state 2)
"
    ::= {ccMaxBytes 6}

spamSubjectCC  OBJECT-TYPE
    SYNTAX      OCTET STRING
    MAX-ACCESS  read-write
    STATUS      current
    DESCRIPTION
"
If set, spamSubject gets prepended to the subject of the copied message.
"
    REFERENCE "Prepend Spam Subject to Copied Spam"
    DEFVAL { "" }
    ::= {CopySpamampHam 39}

syncStatspamSubjectCC  OBJECT-TYPE
    SYNTAX      OCTET STRING
    MAX-ACCESS  read-only
    STATUS      current
    DESCRIPTION
"
synchronization status for spamSubjectCC
-1 - spamSubjectCC could not be synchronized
 0 - synchronization not configured
 1 - out of sync - running master mode
 2 - in sync - running  mastermode
 3 - in sync - running slave mode
 4 - in sync - running master mode (wait to reach state 2)
"
    ::= {spamSubjectCC 5}

syncStatStrspamSubjectCC  OBJECT-TYPE
    SYNTAX      OCTET STRING
    MAX-ACCESS  read-only
    STATUS      current
    DESCRIPTION
"
synchronization status line from file assp_sync.cfg for spamSubjectCC
 0 - synchronization not configured
 1 - out of sync - running master mode
 2 - in sync - running  mastermode
 3 - in sync - running slave mode
 4 - in sync - running master mode (wait to reach state 2)
"
    ::= {spamSubjectCC 6}

spamTagCC  OBJECT-TYPE
    SYNTAX      OCTET STRING
    MAX-ACCESS  read-write
    STATUS      current
    DESCRIPTION
"
The check which caused the spam detection will be prepended to the subject of the message. For example: [DNSBL]
"
    REFERENCE "Prepend Spam Tag to Copied Spam"
    DEFVAL { "1" }
    ::= {CopySpamampHam 40}

syncStatspamTagCC  OBJECT-TYPE
    SYNTAX      OCTET STRING
    MAX-ACCESS  read-only
    STATUS      current
    DESCRIPTION
"
synchronization status for spamTagCC
-1 - spamTagCC could not be synchronized
 0 - synchronization not configured
 1 - out of sync - running master mode
 2 - in sync - running  mastermode
 3 - in sync - running slave mode
 4 - in sync - running master mode (wait to reach state 2)
"
    ::= {spamTagCC 5}

syncStatStrspamTagCC  OBJECT-TYPE
    SYNTAX      OCTET STRING
    MAX-ACCESS  read-only
    STATUS      current
    DESCRIPTION
"
synchronization status line from file assp_sync.cfg for spamTagCC
 0 - synchronization not configured
 1 - out of sync - running master mode
 2 - in sync - running  mastermode
 3 - in sync - running slave mode
 4 - in sync - running master mode (wait to reach state 2)
"
    ::= {spamTagCC 6}

sendAllHamDestination  OBJECT-TYPE
    SYNTAX      OCTET STRING
    MAX-ACCESS  read-write
    STATUS      current
    DESCRIPTION
"
Port to connect to when  Ham messages are copied. If blank they go to the Spam SMTP Destination. eg '10.0.1.3:1025', 'SSL:10.0.1.3:465',, '1025', etc.
"
    REFERENCE "Copy Not-Spam SMTP Destination"
    DEFVAL { "" }
    ::= {CopySpamampHam 41}

syncStatsendAllHamDestination  OBJECT-TYPE
    SYNTAX      OCTET STRING
    MAX-ACCESS  read-only
    STATUS      current
    DESCRIPTION
"
synchronization status for sendAllHamDestination
-1 - sendAllHamDestination could not be synchronized
 0 - synchronization not configured
 1 - out of sync - running master mode
 2 - in sync - running  mastermode
 3 - in sync - running slave mode
 4 - in sync - running master mode (wait to reach state 2)
"
    ::= {sendAllHamDestination 5}

syncStatStrsendAllHamDestination  OBJECT-TYPE
    SYNTAX      OCTET STRING
    MAX-ACCESS  read-only
    STATUS      current
    DESCRIPTION
"
synchronization status line from file assp_sync.cfg for sendAllHamDestination
 0 - synchronization not configured
 1 - out of sync - running master mode
 2 - in sync - running  mastermode
 3 - in sync - running slave mode
 4 - in sync - running master mode (wait to reach state 2)
"
    ::= {sendAllHamDestination 6}

sendHamInbound  OBJECT-TYPE
    SYNTAX      OCTET STRING
    MAX-ACCESS  read-write
    STATUS      current
    DESCRIPTION
"
If you put an address in this box  ASSP will forward a copy of notspam messages from outside to this address. The literal USERNAME is replaced by the user part of the recipient, the literal DOMAIN is replaced by the domain part of the recipient. For example: archiv@mydomain.com, USERNAME@mybackup.domain, catchallforthis@DOMAIN
"
    REFERENCE "Copy Incoming Not-Spam and Send to this Address"
    DEFVAL { "" }
    ::= {CopySpamampHam 42}

syncStatsendHamInbound  OBJECT-TYPE
    SYNTAX      OCTET STRING
    MAX-ACCESS  read-only
    STATUS      current
    DESCRIPTION
"
synchronization status for sendHamInbound
-1 - sendHamInbound could not be synchronized
 0 - synchronization not configured
 1 - out of sync - running master mode
 2 - in sync - running  mastermode
 3 - in sync - running slave mode
 4 - in sync - running master mode (wait to reach state 2)
"
    ::= {sendHamInbound 5}

syncStatStrsendHamInbound  OBJECT-TYPE
    SYNTAX      OCTET STRING
    MAX-ACCESS  read-only
    STATUS      current
    DESCRIPTION
"
synchronization status line from file assp_sync.cfg for sendHamInbound
 0 - synchronization not configured
 1 - out of sync - running master mode
 2 - in sync - running  mastermode
 3 - in sync - running slave mode
 4 - in sync - running master mode (wait to reach state 2)
"
    ::= {sendHamInbound 6}

sendHamOutbound  OBJECT-TYPE
    SYNTAX      OCTET STRING
    MAX-ACCESS  read-write
    STATUS      current
    DESCRIPTION
"
If you put an address in this box ASSP will forward a copy of outgoing notspam messages to this address.
"
    REFERENCE "Copy Outgoing Not-Spam and Send to this Address"
    DEFVAL { "" }
    ::= {CopySpamampHam 43}

syncStatsendHamOutbound  OBJECT-TYPE
    SYNTAX      OCTET STRING
    MAX-ACCESS  read-only
    STATUS      current
    DESCRIPTION
"
synchronization status for sendHamOutbound
-1 - sendHamOutbound could not be synchronized
 0 - synchronization not configured
 1 - out of sync - running master mode
 2 - in sync - running  mastermode
 3 - in sync - running slave mode
 4 - in sync - running master mode (wait to reach state 2)
"
    ::= {sendHamOutbound 5}

syncStatStrsendHamOutbound  OBJECT-TYPE
    SYNTAX      OCTET STRING
    MAX-ACCESS  read-only
    STATUS      current
    DESCRIPTION
"
synchronization status line from file assp_sync.cfg for sendHamOutbound
 0 - synchronization not configured
 1 - out of sync - running master mode
 2 - in sync - running  mastermode
 3 - in sync - running slave mode
 4 - in sync - running master mode (wait to reach state 2)
"
    ::= {sendHamOutbound 6}

ccHamFilter  OBJECT-TYPE
    SYNTAX      OCTET STRING
    MAX-ACCESS  read-write
    STATUS      current
    DESCRIPTION
"
Copy Not-Spam to these addresses only. Accepts specific addresses (user@domain.com), user parts (user) or entire domains (@domain.com). Wildcards are supported (fribo*@domain.com).
"
    REFERENCE "Copy Ham Filter*"
    DEFVAL { "" }
    ::= {CopySpamampHam 44}

syncStatccHamFilter  OBJECT-TYPE
    SYNTAX      OCTET STRING
    MAX-ACCESS  read-only
    STATUS      current
    DESCRIPTION
"
synchronization status for ccHamFilter
-1 - ccHamFilter could not be synchronized
 0 - synchronization not configured
 1 - out of sync - running master mode
 2 - in sync - running  mastermode
 3 - in sync - running slave mode
 4 - in sync - running master mode (wait to reach state 2)
"
    ::= {ccHamFilter 5}

syncStatStrccHamFilter  OBJECT-TYPE
    SYNTAX      OCTET STRING
    MAX-ACCESS  read-only
    STATUS      current
    DESCRIPTION
"
synchronization status line from file assp_sync.cfg for ccHamFilter
 0 - synchronization not configured
 1 - out of sync - running master mode
 2 - in sync - running  mastermode
 3 - in sync - running slave mode
 4 - in sync - running master mode (wait to reach state 2)
"
    ::= {ccHamFilter 6}

ccnHamFilter  OBJECT-TYPE
    SYNTAX      OCTET STRING
    MAX-ACCESS  read-write
    STATUS      current
    DESCRIPTION
"
Do Not Copy Ham to these addresses. Accepts specific addresses (user@domain.com), user parts (user) or entire domains (@domain.com). Wildcards are supported (fribo*@domain.com).
"
    REFERENCE "Do Not Copy Ham Filter*"
    DEFVAL { "" }
    ::= {CopySpamampHam 45}

syncStatccnHamFilter  OBJECT-TYPE
    SYNTAX      OCTET STRING
    MAX-ACCESS  read-only
    STATUS      current
    DESCRIPTION
"
synchronization status for ccnHamFilter
-1 - ccnHamFilter could not be synchronized
 0 - synchronization not configured
 1 - out of sync - running master mode
 2 - in sync - running  mastermode
 3 - in sync - running slave mode
 4 - in sync - running master mode (wait to reach state 2)
"
    ::= {ccnHamFilter 5}

syncStatStrccnHamFilter  OBJECT-TYPE
    SYNTAX      OCTET STRING
    MAX-ACCESS  read-only
    STATUS      current
    DESCRIPTION
"
synchronization status line from file assp_sync.cfg for ccnHamFilter
 0 - synchronization not configured
 1 - out of sync - running master mode
 2 - in sync - running  mastermode
 3 - in sync - running slave mode
 4 - in sync - running master mode (wait to reach state 2)
"
    ::= {ccnHamFilter 6}

ccMailReplaceRecpt  OBJECT-TYPE
    SYNTAX      OCTET STRING
    MAX-ACCESS  read-write
    STATUS      current
    DESCRIPTION
"
The recipient replacement (ReplaceRecpt) rules from the 'Recipients/Local Domains' section, will be used to replace ccMail recipients. For example: sendHamInbound = USERNAME@yourspamdomain.lan - in this case you are able to detect the target domain 'yourspamdomain.lan' in a rule and you can replace the recipient/domain depending on its values and/or on the senders address.

"
    REFERENCE "ccMail Recipient Replacement"
    DEFVAL { "" }
    ::= {CopySpamampHam 46}

syncStatccMailReplaceRecpt  OBJECT-TYPE
    SYNTAX      OCTET STRING
    MAX-ACCESS  read-only
    STATUS      current
    DESCRIPTION
"
synchronization status for ccMailReplaceRecpt
-1 - ccMailReplaceRecpt could not be synchronized
 0 - synchronization not configured
 1 - out of sync - running master mode
 2 - in sync - running  mastermode
 3 - in sync - running slave mode
 4 - in sync - running master mode (wait to reach state 2)
"
    ::= {ccMailReplaceRecpt 5}

syncStatStrccMailReplaceRecpt  OBJECT-TYPE
    SYNTAX      OCTET STRING
    MAX-ACCESS  read-only
    STATUS      current
    DESCRIPTION
"
synchronization status line from file assp_sync.cfg for ccMailReplaceRecpt
 0 - synchronization not configured
 1 - out of sync - running master mode
 2 - in sync - running  mastermode
 3 - in sync - running slave mode
 4 - in sync - running master mode (wait to reach state 2)
"
    ::= {ccMailReplaceRecpt 6}

ccSpamInDomain  OBJECT-TYPE
    SYNTAX      OCTET STRING
    MAX-ACCESS  read-write
    STATUS      current
    DESCRIPTION
"
ASSP will deliver an additional copy of spam emails of a domain to this address (even if sendAllSpam is not set) - if the domain of the recipient-address is matched. For example: monitorspam@example1.com|monitor@example2.com.
"
    REFERENCE "Copy Spam and Send to this Address per Domain*"
    DEFVAL { "" }
    ::= {CopySpamampHam 888}

syncStatccSpamInDomain  OBJECT-TYPE
    SYNTAX      OCTET STRING
    MAX-ACCESS  read-only
    STATUS      current
    DESCRIPTION
"
synchronization status for ccSpamInDomain
-1 - ccSpamInDomain could not be synchronized
 0 - synchronization not configured
 1 - out of sync - running master mode
 2 - in sync - running  mastermode
 3 - in sync - running slave mode
 4 - in sync - running master mode (wait to reach state 2)
"
    ::= {ccSpamInDomain 5}

syncStatStrccSpamInDomain  OBJECT-TYPE
    SYNTAX      OCTET STRING
    MAX-ACCESS  read-only
    STATUS      current
    DESCRIPTION
"
synchronization status line from file assp_sync.cfg for ccSpamInDomain
 0 - synchronization not configured
 1 - out of sync - running master mode
 2 - in sync - running  mastermode
 3 - in sync - running slave mode
 4 - in sync - running master mode (wait to reach state 2)
"
    ::= {ccSpamInDomain 6}

SPAMLoverHater  OBJECT IDENTIFIER ::= {asspConfig 6}
spamSubjectSL  OBJECT-TYPE
    SYNTAX      OCTET STRING
    MAX-ACCESS  read-write
    STATUS      current
    DESCRIPTION
"
If set, spamSubject and spamTag does NOT get prepended to the subject of the Spam-Lover-Message.
"
    REFERENCE "Suppress SpamSubject to Spam-Lover-Messages"
    DEFVAL { "" }
    ::= {SPAMLoverHater 47}

syncStatspamSubjectSL  OBJECT-TYPE
    SYNTAX      OCTET STRING
    MAX-ACCESS  read-only
    STATUS      current
    DESCRIPTION
"
synchronization status for spamSubjectSL
-1 - spamSubjectSL could not be synchronized
 0 - synchronization not configured
 1 - out of sync - running master mode
 2 - in sync - running  mastermode
 3 - in sync - running slave mode
 4 - in sync - running master mode (wait to reach state 2)
"
    ::= {spamSubjectSL 5}

syncStatStrspamSubjectSL  OBJECT-TYPE
    SYNTAX      OCTET STRING
    MAX-ACCESS  read-only
    STATUS      current
    DESCRIPTION
"
synchronization status line from file assp_sync.cfg for spamSubjectSL
 0 - synchronization not configured
 1 - out of sync - running master mode
 2 - in sync - running  mastermode
 3 - in sync - running slave mode
 4 - in sync - running master mode (wait to reach state 2)
"
    ::= {spamSubjectSL 6}

spamTagSL  OBJECT-TYPE
    SYNTAX      OCTET STRING
    MAX-ACCESS  read-write
    STATUS      current
    DESCRIPTION
"
If set, spamTags does NOT get prepended to the subject of the Spam-Lover-Message.
"
    REFERENCE "Suppress SpamTags to Spam-Lover-Messages"
    DEFVAL { "1" }
    ::= {SPAMLoverHater 48}

syncStatspamTagSL  OBJECT-TYPE
    SYNTAX      OCTET STRING
    MAX-ACCESS  read-only
    STATUS      current
    DESCRIPTION
"
synchronization status for spamTagSL
-1 - spamTagSL could not be synchronized
 0 - synchronization not configured
 1 - out of sync - running master mode
 2 - in sync - running  mastermode
 3 - in sync - running slave mode
 4 - in sync - running master mode (wait to reach state 2)
"
    ::= {spamTagSL 5}

syncStatStrspamTagSL  OBJECT-TYPE
    SYNTAX      OCTET STRING
    MAX-ACCESS  read-only
    STATUS      current
    DESCRIPTION
"
synchronization status line from file assp_sync.cfg for spamTagSL
 0 - synchronization not configured
 1 - out of sync - running master mode
 2 - in sync - running  mastermode
 3 - in sync - running slave mode
 4 - in sync - running master mode (wait to reach state 2)
"
    ::= {spamTagSL 6}

spamLovers  OBJECT-TYPE
    SYNTAX      OCTET STRING
    MAX-ACCESS  read-write
    STATUS      current
    DESCRIPTION
"
Messages to Spam-Lovers are processed and filtered by ASSP, but get tagged with spamSubject and are not blocked. When a
 Spam-Lover is not the sole recipient of a message, the message is processed
 normally, and if it is found to be spam, it will not be delivered to the Spam-Lover.
 delaySpamLovers are not included here and must be set additionally.
 Accepts specific addresses (user@domain.com), user parts (user) or entire domains (@domain.com). Wildcards are supported (fribo*@domain.com). Default: postmaster|abuse.For example: fribo*@thisdomain.com|jhanna|@sillyguys.org
 
 This option and all SpamLover-Options (...SpamLovers) below accepting a second score parameter like 'user@your-domain.com=>70'
 If such a parameter is defined in any option for an entry and the recipient address matches this entry and the message score exceeds the parameter value, the message will be considered spam.
 If there are multiple possible matches for a recipient address found, the generic longest match (and assigned value) will be used.
 ASSP will use the highest found value for all envelope recipients of an email.
 The according low limit is calculated as:
 for outgoing mails: value - ( PenaltyMessageLimit - PenaltyMessageLow )
 or
 for incoming and local mails: value - ( LocalPenaltyMessageLimit - LocalPenaltyMessageLow )
"
    REFERENCE "All Spam-Lover*"
    DEFVAL { "postmaster|abuse" }
    ::= {SPAMLoverHater 49}

syncStatspamLovers  OBJECT-TYPE
    SYNTAX      OCTET STRING
    MAX-ACCESS  read-only
    STATUS      current
    DESCRIPTION
"
synchronization status for spamLovers
-1 - spamLovers could not be synchronized
 0 - synchronization not configured
 1 - out of sync - running master mode
 2 - in sync - running  mastermode
 3 - in sync - running slave mode
 4 - in sync - running master mode (wait to reach state 2)
"
    ::= {spamLovers 5}

syncStatStrspamLovers  OBJECT-TYPE
    SYNTAX      OCTET STRING
    MAX-ACCESS  read-only
    STATUS      current
    DESCRIPTION
"
synchronization status line from file assp_sync.cfg for spamLovers
 0 - synchronization not configured
 1 - out of sync - running master mode
 2 - in sync - running  mastermode
 3 - in sync - running slave mode
 4 - in sync - running master mode (wait to reach state 2)
"
    ::= {spamLovers 6}

SpamLoversRe  OBJECT-TYPE
    SYNTAX      OCTET STRING
    MAX-ACCESS  read-write
    STATUS      current
    DESCRIPTION
"
If a message matches this regular expression it will be considered a Spam-Lover message.
"
    REFERENCE "Regular Expression to Identify Spam-Lover*"
    DEFVAL { "" }
    ::= {SPAMLoverHater 50}

syncStatSpamLoversRe  OBJECT-TYPE
    SYNTAX      OCTET STRING
    MAX-ACCESS  read-only
    STATUS      current
    DESCRIPTION
"
synchronization status for SpamLoversRe
-1 - SpamLoversRe could not be synchronized
 0 - synchronization not configured
 1 - out of sync - running master mode
 2 - in sync - running  mastermode
 3 - in sync - running slave mode
 4 - in sync - running master mode (wait to reach state 2)
"
    ::= {SpamLoversRe 5}

syncStatStrSpamLoversRe  OBJECT-TYPE
    SYNTAX      OCTET STRING
    MAX-ACCESS  read-only
    STATUS      current
    DESCRIPTION
"
synchronization status line from file assp_sync.cfg for SpamLoversRe
 0 - synchronization not configured
 1 - out of sync - running master mode
 2 - in sync - running  mastermode
 3 - in sync - running slave mode
 4 - in sync - running master mode (wait to reach state 2)
"
    ::= {SpamLoversRe 6}

baysSpamLovers  OBJECT-TYPE
    SYNTAX      OCTET STRING
    MAX-ACCESS  read-write
    STATUS      current
    DESCRIPTION
"

"
    REFERENCE "Bayesian Spam-Lover*"
    DEFVAL { "" }
    ::= {SPAMLoverHater 51}

syncStatbaysSpamLovers  OBJECT-TYPE
    SYNTAX      OCTET STRING
    MAX-ACCESS  read-only
    STATUS      current
    DESCRIPTION
"
synchronization status for baysSpamLovers
-1 - baysSpamLovers could not be synchronized
 0 - synchronization not configured
 1 - out of sync - running master mode
 2 - in sync - running  mastermode
 3 - in sync - running slave mode
 4 - in sync - running master mode (wait to reach state 2)
"
    ::= {baysSpamLovers 5}

syncStatStrbaysSpamLovers  OBJECT-TYPE
    SYNTAX      OCTET STRING
    MAX-ACCESS  read-only
    STATUS      current
    DESCRIPTION
"
synchronization status line from file assp_sync.cfg for baysSpamLovers
 0 - synchronization not configured
 1 - out of sync - running master mode
 2 - in sync - running  mastermode
 3 - in sync - running slave mode
 4 - in sync - running master mode (wait to reach state 2)
"
    ::= {baysSpamLovers 6}

baysSpamLoversRe  OBJECT-TYPE
    SYNTAX      OCTET STRING
    MAX-ACCESS  read-write
    STATUS      current
    DESCRIPTION
"
If a message matches this regular expression it will be considered a Bayesian Spam-Lover message. For example: password|news
"
    REFERENCE "Regular Expression to Identify Bayesian Spam-Lover*"
    DEFVAL { "" }
    ::= {SPAMLoverHater 52}

syncStatbaysSpamLoversRe  OBJECT-TYPE
    SYNTAX      OCTET STRING
    MAX-ACCESS  read-only
    STATUS      current
    DESCRIPTION
"
synchronization status for baysSpamLoversRe
-1 - baysSpamLoversRe could not be synchronized
 0 - synchronization not configured
 1 - out of sync - running master mode
 2 - in sync - running  mastermode
 3 - in sync - running slave mode
 4 - in sync - running master mode (wait to reach state 2)
"
    ::= {baysSpamLoversRe 5}

syncStatStrbaysSpamLoversRe  OBJECT-TYPE
    SYNTAX      OCTET STRING
    MAX-ACCESS  read-only
    STATUS      current
    DESCRIPTION
"
synchronization status line from file assp_sync.cfg for baysSpamLoversRe
 0 - synchronization not configured
 1 - out of sync - running master mode
 2 - in sync - running  mastermode
 3 - in sync - running slave mode
 4 - in sync - running master mode (wait to reach state 2)
"
    ::= {baysSpamLoversRe 6}

baysSpamLoversRed  OBJECT-TYPE
    SYNTAX      OCTET STRING
    MAX-ACCESS  read-write
    STATUS      current
    DESCRIPTION
"
If set (recommended), mail to Bayesian Spam-Lover will not be stored in the discarded folder (not in the Spam/Notspam folder).
"
    REFERENCE "Do not store Bayesian Spam-Lover in SpamDB"
    DEFVAL { "1" }
    ::= {SPAMLoverHater 53}

syncStatbaysSpamLoversRed  OBJECT-TYPE
    SYNTAX      OCTET STRING
    MAX-ACCESS  read-only
    STATUS      current
    DESCRIPTION
"
synchronization status for baysSpamLoversRed
-1 - baysSpamLoversRed could not be synchronized
 0 - synchronization not configured
 1 - out of sync - running master mode
 2 - in sync - running  mastermode
 3 - in sync - running slave mode
 4 - in sync - running master mode (wait to reach state 2)
"
    ::= {baysSpamLoversRed 5}

syncStatStrbaysSpamLoversRed  OBJECT-TYPE
    SYNTAX      OCTET STRING
    MAX-ACCESS  read-only
    STATUS      current
    DESCRIPTION
"
synchronization status line from file assp_sync.cfg for baysSpamLoversRed
 0 - synchronization not configured
 1 - out of sync - running master mode
 2 - in sync - running  mastermode
 3 - in sync - running slave mode
 4 - in sync - running master mode (wait to reach state 2)
"
    ::= {baysSpamLoversRed 6}

blSpamLovers  OBJECT-TYPE
    SYNTAX      OCTET STRING
    MAX-ACCESS  read-write
    STATUS      current
    DESCRIPTION
"

"
    REFERENCE "Blacklisted Domains Spam-Lover*"
    DEFVAL { "" }
    ::= {SPAMLoverHater 54}

syncStatblSpamLovers  OBJECT-TYPE
    SYNTAX      OCTET STRING
    MAX-ACCESS  read-only
    STATUS      current
    DESCRIPTION
"
synchronization status for blSpamLovers
-1 - blSpamLovers could not be synchronized
 0 - synchronization not configured
 1 - out of sync - running master mode
 2 - in sync - running  mastermode
 3 - in sync - running slave mode
 4 - in sync - running master mode (wait to reach state 2)
"
    ::= {blSpamLovers 5}

syncStatStrblSpamLovers  OBJECT-TYPE
    SYNTAX      OCTET STRING
    MAX-ACCESS  read-only
    STATUS      current
    DESCRIPTION
"
synchronization status line from file assp_sync.cfg for blSpamLovers
 0 - synchronization not configured
 1 - out of sync - running master mode
 2 - in sync - running  mastermode
 3 - in sync - running slave mode
 4 - in sync - running master mode (wait to reach state 2)
"
    ::= {blSpamLovers 6}

bombSpamLovers  OBJECT-TYPE
    SYNTAX      OCTET STRING
    MAX-ACCESS  read-write
    STATUS      current
    DESCRIPTION
"

"
    REFERENCE "Bomb Spam-Lover*"
    DEFVAL { "" }
    ::= {SPAMLoverHater 55}

syncStatbombSpamLovers  OBJECT-TYPE
    SYNTAX      OCTET STRING
    MAX-ACCESS  read-only
    STATUS      current
    DESCRIPTION
"
synchronization status for bombSpamLovers
-1 - bombSpamLovers could not be synchronized
 0 - synchronization not configured
 1 - out of sync - running master mode
 2 - in sync - running  mastermode
 3 - in sync - running slave mode
 4 - in sync - running master mode (wait to reach state 2)
"
    ::= {bombSpamLovers 5}

syncStatStrbombSpamLovers  OBJECT-TYPE
    SYNTAX      OCTET STRING
    MAX-ACCESS  read-only
    STATUS      current
    DESCRIPTION
"
synchronization status line from file assp_sync.cfg for bombSpamLovers
 0 - synchronization not configured
 1 - out of sync - running master mode
 2 - in sync - running  mastermode
 3 - in sync - running slave mode
 4 - in sync - running master mode (wait to reach state 2)
"
    ::= {bombSpamLovers 6}

hlSpamLovers  OBJECT-TYPE
    SYNTAX      OCTET STRING
    MAX-ACCESS  read-write
    STATUS      current
    DESCRIPTION
"

"
    REFERENCE "HELO Blacklisted Spam-Lover*"
    DEFVAL { "" }
    ::= {SPAMLoverHater 56}

syncStathlSpamLovers  OBJECT-TYPE
    SYNTAX      OCTET STRING
    MAX-ACCESS  read-only
    STATUS      current
    DESCRIPTION
"
synchronization status for hlSpamLovers
-1 - hlSpamLovers could not be synchronized
 0 - synchronization not configured
 1 - out of sync - running master mode
 2 - in sync - running  mastermode
 3 - in sync - running slave mode
 4 - in sync - running master mode (wait to reach state 2)
"
    ::= {hlSpamLovers 5}

syncStatStrhlSpamLovers  OBJECT-TYPE
    SYNTAX      OCTET STRING
    MAX-ACCESS  read-only
    STATUS      current
    DESCRIPTION
"
synchronization status line from file assp_sync.cfg for hlSpamLovers
 0 - synchronization not configured
 1 - out of sync - running master mode
 2 - in sync - running  mastermode
 3 - in sync - running slave mode
 4 - in sync - running master mode (wait to reach state 2)
"
    ::= {hlSpamLovers 6}

hiSpamLovers  OBJECT-TYPE
    SYNTAX      OCTET STRING
    MAX-ACCESS  read-write
    STATUS      current
    DESCRIPTION
"

"
    REFERENCE "Valid/Invalid Helo*"
    DEFVAL { "" }
    ::= {SPAMLoverHater 57}

syncStathiSpamLovers  OBJECT-TYPE
    SYNTAX      OCTET STRING
    MAX-ACCESS  read-only
    STATUS      current
    DESCRIPTION
"
synchronization status for hiSpamLovers
-1 - hiSpamLovers could not be synchronized
 0 - synchronization not configured
 1 - out of sync - running master mode
 2 - in sync - running  mastermode
 3 - in sync - running slave mode
 4 - in sync - running master mode (wait to reach state 2)
"
    ::= {hiSpamLovers 5}

syncStatStrhiSpamLovers  OBJECT-TYPE
    SYNTAX      OCTET STRING
    MAX-ACCESS  read-only
    STATUS      current
    DESCRIPTION
"
synchronization status line from file assp_sync.cfg for hiSpamLovers
 0 - synchronization not configured
 1 - out of sync - running master mode
 2 - in sync - running  mastermode
 3 - in sync - running slave mode
 4 - in sync - running master mode (wait to reach state 2)
"
    ::= {hiSpamLovers 6}

atSpamLovers  OBJECT-TYPE
    SYNTAX      OCTET STRING
    MAX-ACCESS  read-write
    STATUS      current
    DESCRIPTION
"

"
    REFERENCE "Bad Attachment Spam-Lover*"
    DEFVAL { "" }
    ::= {SPAMLoverHater 58}

syncStatatSpamLovers  OBJECT-TYPE
    SYNTAX      OCTET STRING
    MAX-ACCESS  read-only
    STATUS      current
    DESCRIPTION
"
synchronization status for atSpamLovers
-1 - atSpamLovers could not be synchronized
 0 - synchronization not configured
 1 - out of sync - running master mode
 2 - in sync - running  mastermode
 3 - in sync - running slave mode
 4 - in sync - running master mode (wait to reach state 2)
"
    ::= {atSpamLovers 5}

syncStatStratSpamLovers  OBJECT-TYPE
    SYNTAX      OCTET STRING
    MAX-ACCESS  read-only
    STATUS      current
    DESCRIPTION
"
synchronization status line from file assp_sync.cfg for atSpamLovers
 0 - synchronization not configured
 1 - out of sync - running master mode
 2 - in sync - running  mastermode
 3 - in sync - running slave mode
 4 - in sync - running master mode (wait to reach state 2)
"
    ::= {atSpamLovers 6}

spfSpamLovers  OBJECT-TYPE
    SYNTAX      OCTET STRING
    MAX-ACCESS  read-write
    STATUS      current
    DESCRIPTION
"

"
    REFERENCE "SPF Failures Spam-Lover*"
    DEFVAL { "" }
    ::= {SPAMLoverHater 59}

syncStatspfSpamLovers  OBJECT-TYPE
    SYNTAX      OCTET STRING
    MAX-ACCESS  read-only
    STATUS      current
    DESCRIPTION
"
synchronization status for spfSpamLovers
-1 - spfSpamLovers could not be synchronized
 0 - synchronization not configured
 1 - out of sync - running master mode
 2 - in sync - running  mastermode
 3 - in sync - running slave mode
 4 - in sync - running master mode (wait to reach state 2)
"
    ::= {spfSpamLovers 5}

syncStatStrspfSpamLovers  OBJECT-TYPE
    SYNTAX      OCTET STRING
    MAX-ACCESS  read-only
    STATUS      current
    DESCRIPTION
"
synchronization status line from file assp_sync.cfg for spfSpamLovers
 0 - synchronization not configured
 1 - out of sync - running master mode
 2 - in sync - running  mastermode
 3 - in sync - running slave mode
 4 - in sync - running master mode (wait to reach state 2)
"
    ::= {spfSpamLovers 6}

rblSpamLovers  OBJECT-TYPE
    SYNTAX      OCTET STRING
    MAX-ACCESS  read-write
    STATUS      current
    DESCRIPTION
"

"
    REFERENCE "DNSBL Failures Spam-Lover*"
    DEFVAL { "" }
    ::= {SPAMLoverHater 60}

syncStatrblSpamLovers  OBJECT-TYPE
    SYNTAX      OCTET STRING
    MAX-ACCESS  read-only
    STATUS      current
    DESCRIPTION
"
synchronization status for rblSpamLovers
-1 - rblSpamLovers could not be synchronized
 0 - synchronization not configured
 1 - out of sync - running master mode
 2 - in sync - running  mastermode
 3 - in sync - running slave mode
 4 - in sync - running master mode (wait to reach state 2)
"
    ::= {rblSpamLovers 5}

syncStatStrrblSpamLovers  OBJECT-TYPE
    SYNTAX      OCTET STRING
    MAX-ACCESS  read-only
    STATUS      current
    DESCRIPTION
"
synchronization status line from file assp_sync.cfg for rblSpamLovers
 0 - synchronization not configured
 1 - out of sync - running master mode
 2 - in sync - running  mastermode
 3 - in sync - running slave mode
 4 - in sync - running master mode (wait to reach state 2)
"
    ::= {rblSpamLovers 6}

uriblSpamLovers  OBJECT-TYPE
    SYNTAX      OCTET STRING
    MAX-ACCESS  read-write
    STATUS      current
    DESCRIPTION
"

"
    REFERENCE "URIBL Failures Spam-Lover*"
    DEFVAL { "" }
    ::= {SPAMLoverHater 61}

syncStaturiblSpamLovers  OBJECT-TYPE
    SYNTAX      OCTET STRING
    MAX-ACCESS  read-only
    STATUS      current
    DESCRIPTION
"
synchronization status for uriblSpamLovers
-1 - uriblSpamLovers could not be synchronized
 0 - synchronization not configured
 1 - out of sync - running master mode
 2 - in sync - running  mastermode
 3 - in sync - running slave mode
 4 - in sync - running master mode (wait to reach state 2)
"
    ::= {uriblSpamLovers 5}

syncStatStruriblSpamLovers  OBJECT-TYPE
    SYNTAX      OCTET STRING
    MAX-ACCESS  read-only
    STATUS      current
    DESCRIPTION
"
synchronization status line from file assp_sync.cfg for uriblSpamLovers
 0 - synchronization not configured
 1 - out of sync - running master mode
 2 - in sync - running  mastermode
 3 - in sync - running slave mode
 4 - in sync - running master mode (wait to reach state 2)
"
    ::= {uriblSpamLovers 6}

srsSpamLovers  OBJECT-TYPE
    SYNTAX      OCTET STRING
    MAX-ACCESS  read-write
    STATUS      current
    DESCRIPTION
"

"
    REFERENCE "Unsigned SRS Bounces Spam-Lover*"
    DEFVAL { "" }
    ::= {SPAMLoverHater 62}

syncStatsrsSpamLovers  OBJECT-TYPE
    SYNTAX      OCTET STRING
    MAX-ACCESS  read-only
    STATUS      current
    DESCRIPTION
"
synchronization status for srsSpamLovers
-1 - srsSpamLovers could not be synchronized
 0 - synchronization not configured
 1 - out of sync - running master mode
 2 - in sync - running  mastermode
 3 - in sync - running slave mode
 4 - in sync - running master mode (wait to reach state 2)
"
    ::= {srsSpamLovers 5}

syncStatStrsrsSpamLovers  OBJECT-TYPE
    SYNTAX      OCTET STRING
    MAX-ACCESS  read-only
    STATUS      current
    DESCRIPTION
"
synchronization status line from file assp_sync.cfg for srsSpamLovers
 0 - synchronization not configured
 1 - out of sync - running master mode
 2 - in sync - running  mastermode
 3 - in sync - running slave mode
 4 - in sync - running master mode (wait to reach state 2)
"
    ::= {srsSpamLovers 6}

delaySpamLovers  OBJECT-TYPE
    SYNTAX      OCTET STRING
    MAX-ACCESS  read-write
    STATUS      current
    DESCRIPTION
"

"
    REFERENCE "No Delaying Spam-Lover*"
    DEFVAL { "" }
    ::= {SPAMLoverHater 63}

syncStatdelaySpamLovers  OBJECT-TYPE
    SYNTAX      OCTET STRING
    MAX-ACCESS  read-only
    STATUS      current
    DESCRIPTION
"
synchronization status for delaySpamLovers
-1 - delaySpamLovers could not be synchronized
 0 - synchronization not configured
 1 - out of sync - running master mode
 2 - in sync - running  mastermode
 3 - in sync - running slave mode
 4 - in sync - running master mode (wait to reach state 2)
"
    ::= {delaySpamLovers 5}

syncStatStrdelaySpamLovers  OBJECT-TYPE
    SYNTAX      OCTET STRING
    MAX-ACCESS  read-only
    STATUS      current
    DESCRIPTION
"
synchronization status line from file assp_sync.cfg for delaySpamLovers
 0 - synchronization not configured
 1 - out of sync - running master mode
 2 - in sync - running  mastermode
 3 - in sync - running slave mode
 4 - in sync - running master mode (wait to reach state 2)
"
    ::= {delaySpamLovers 6}

isSpamLovers  OBJECT-TYPE
    SYNTAX      OCTET STRING
    MAX-ACCESS  read-write
    STATUS      current
    DESCRIPTION
"

"
    REFERENCE "Invalid Sender Spam-Lover*"
    DEFVAL { "" }
    ::= {SPAMLoverHater 64}

syncStatisSpamLovers  OBJECT-TYPE
    SYNTAX      OCTET STRING
    MAX-ACCESS  read-only
    STATUS      current
    DESCRIPTION
"
synchronization status for isSpamLovers
-1 - isSpamLovers could not be synchronized
 0 - synchronization not configured
 1 - out of sync - running master mode
 2 - in sync - running  mastermode
 3 - in sync - running slave mode
 4 - in sync - running master mode (wait to reach state 2)
"
    ::= {isSpamLovers 5}

syncStatStrisSpamLovers  OBJECT-TYPE
    SYNTAX      OCTET STRING
    MAX-ACCESS  read-only
    STATUS      current
    DESCRIPTION
"
synchronization status line from file assp_sync.cfg for isSpamLovers
 0 - synchronization not configured
 1 - out of sync - running master mode
 2 - in sync - running  mastermode
 3 - in sync - running slave mode
 4 - in sync - running master mode (wait to reach state 2)
"
    ::= {isSpamLovers 6}

mxaSpamLovers  OBJECT-TYPE
    SYNTAX      OCTET STRING
    MAX-ACCESS  read-write
    STATUS      current
    DESCRIPTION
"

"
    REFERENCE "Missing MX Spam-Lover*"
    DEFVAL { "" }
    ::= {SPAMLoverHater 65}

syncStatmxaSpamLovers  OBJECT-TYPE
    SYNTAX      OCTET STRING
    MAX-ACCESS  read-only
    STATUS      current
    DESCRIPTION
"
synchronization status for mxaSpamLovers
-1 - mxaSpamLovers could not be synchronized
 0 - synchronization not configured
 1 - out of sync - running master mode
 2 - in sync - running  mastermode
 3 - in sync - running slave mode
 4 - in sync - running master mode (wait to reach state 2)
"
    ::= {mxaSpamLovers 5}

syncStatStrmxaSpamLovers  OBJECT-TYPE
    SYNTAX      OCTET STRING
    MAX-ACCESS  read-only
    STATUS      current
    DESCRIPTION
"
synchronization status line from file assp_sync.cfg for mxaSpamLovers
 0 - synchronization not configured
 1 - out of sync - running master mode
 2 - in sync - running  mastermode
 3 - in sync - running slave mode
 4 - in sync - running master mode (wait to reach state 2)
"
    ::= {mxaSpamLovers 6}

ptrSpamLovers  OBJECT-TYPE
    SYNTAX      OCTET STRING
    MAX-ACCESS  read-write
    STATUS      current
    DESCRIPTION
"

"
    REFERENCE "Invalid/Missing PTR Spam-Lover*"
    DEFVAL { "" }
    ::= {SPAMLoverHater 66}

syncStatptrSpamLovers  OBJECT-TYPE
    SYNTAX      OCTET STRING
    MAX-ACCESS  read-only
    STATUS      current
    DESCRIPTION
"
synchronization status for ptrSpamLovers
-1 - ptrSpamLovers could not be synchronized
 0 - synchronization not configured
 1 - out of sync - running master mode
 2 - in sync - running  mastermode
 3 - in sync - running slave mode
 4 - in sync - running master mode (wait to reach state 2)
"
    ::= {ptrSpamLovers 5}

syncStatStrptrSpamLovers  OBJECT-TYPE
    SYNTAX      OCTET STRING
    MAX-ACCESS  read-only
    STATUS      current
    DESCRIPTION
"
synchronization status line from file assp_sync.cfg for ptrSpamLovers
 0 - synchronization not configured
 1 - out of sync - running master mode
 2 - in sync - running  mastermode
 3 - in sync - running slave mode
 4 - in sync - running master mode (wait to reach state 2)
"
    ::= {ptrSpamLovers 6}

pbSpamLovers  OBJECT-TYPE
    SYNTAX      OCTET STRING
    MAX-ACCESS  read-write
    STATUS      current
    DESCRIPTION
"

"
    REFERENCE "Penalty Box Blocking Spam-Lover *"
    DEFVAL { "" }
    ::= {SPAMLoverHater 67}

syncStatpbSpamLovers  OBJECT-TYPE
    SYNTAX      OCTET STRING
    MAX-ACCESS  read-only
    STATUS      current
    DESCRIPTION
"
synchronization status for pbSpamLovers
-1 - pbSpamLovers could not be synchronized
 0 - synchronization not configured
 1 - out of sync - running master mode
 2 - in sync - running  mastermode
 3 - in sync - running slave mode
 4 - in sync - running master mode (wait to reach state 2)
"
    ::= {pbSpamLovers 5}

syncStatStrpbSpamLovers  OBJECT-TYPE
    SYNTAX      OCTET STRING
    MAX-ACCESS  read-only
    STATUS      current
    DESCRIPTION
"
synchronization status line from file assp_sync.cfg for pbSpamLovers
 0 - synchronization not configured
 1 - out of sync - running master mode
 2 - in sync - running  mastermode
 3 - in sync - running slave mode
 4 - in sync - running master mode (wait to reach state 2)
"
    ::= {pbSpamLovers 6}

sbSpamLovers  OBJECT-TYPE
    SYNTAX      OCTET STRING
    MAX-ACCESS  read-write
    STATUS      current
    DESCRIPTION
"

"
    REFERENCE "Country Blocking Spam-Lover *"
    DEFVAL { "" }
    ::= {SPAMLoverHater 68}

syncStatsbSpamLovers  OBJECT-TYPE
    SYNTAX      OCTET STRING
    MAX-ACCESS  read-only
    STATUS      current
    DESCRIPTION
"
synchronization status for sbSpamLovers
-1 - sbSpamLovers could not be synchronized
 0 - synchronization not configured
 1 - out of sync - running master mode
 2 - in sync - running  mastermode
 3 - in sync - running slave mode
 4 - in sync - running master mode (wait to reach state 2)
"
    ::= {sbSpamLovers 5}

syncStatStrsbSpamLovers  OBJECT-TYPE
    SYNTAX      OCTET STRING
    MAX-ACCESS  read-only
    STATUS      current
    DESCRIPTION
"
synchronization status line from file assp_sync.cfg for sbSpamLovers
 0 - synchronization not configured
 1 - out of sync - running master mode
 2 - in sync - running  mastermode
 3 - in sync - running slave mode
 4 - in sync - running master mode (wait to reach state 2)
"
    ::= {sbSpamLovers 6}

spamHaters  OBJECT-TYPE
    SYNTAX      OCTET STRING
    MAX-ACCESS  read-write
    STATUS      current
    DESCRIPTION
"
Spam-Haters are used to override Spam-Lovers.
 Example: If you have set your entire domain as a Spam-Lover(s), but there are still some addresses you still wish to block spam for. If you add those addresses to the Spam-Haters field allows messages to only those addresses to be blocked while still allowing the messages to the other Spam-Lovers pass through. The message will only be blocked if all recipients are Spam-Haters. Accepts specific addresses (user@domain.com), user parts (user) or entire domains (@domain.com).  Wildcards are supported (fribo*@domain.com).For example: *fribo@thisdomain.com|jhanna|@sillyguys.org 
"
    REFERENCE "All Spam-Haters*"
    DEFVAL { "" }
    ::= {SPAMLoverHater 69}

syncStatspamHaters  OBJECT-TYPE
    SYNTAX      OCTET STRING
    MAX-ACCESS  read-only
    STATUS      current
    DESCRIPTION
"
synchronization status for spamHaters
-1 - spamHaters could not be synchronized
 0 - synchronization not configured
 1 - out of sync - running master mode
 2 - in sync - running  mastermode
 3 - in sync - running slave mode
 4 - in sync - running master mode (wait to reach state 2)
"
    ::= {spamHaters 5}

syncStatStrspamHaters  OBJECT-TYPE
    SYNTAX      OCTET STRING
    MAX-ACCESS  read-only
    STATUS      current
    DESCRIPTION
"
synchronization status line from file assp_sync.cfg for spamHaters
 0 - synchronization not configured
 1 - out of sync - running master mode
 2 - in sync - running  mastermode
 3 - in sync - running slave mode
 4 - in sync - running master mode (wait to reach state 2)
"
    ::= {spamHaters 6}

baysSpamHaters  OBJECT-TYPE
    SYNTAX      OCTET STRING
    MAX-ACCESS  read-write
    STATUS      current
    DESCRIPTION
"

"
    REFERENCE "Bayesian Spam-Hater*"
    DEFVAL { "" }
    ::= {SPAMLoverHater 70}

syncStatbaysSpamHaters  OBJECT-TYPE
    SYNTAX      OCTET STRING
    MAX-ACCESS  read-only
    STATUS      current
    DESCRIPTION
"
synchronization status for baysSpamHaters
-1 - baysSpamHaters could not be synchronized
 0 - synchronization not configured
 1 - out of sync - running master mode
 2 - in sync - running  mastermode
 3 - in sync - running slave mode
 4 - in sync - running master mode (wait to reach state 2)
"
    ::= {baysSpamHaters 5}

syncStatStrbaysSpamHaters  OBJECT-TYPE
    SYNTAX      OCTET STRING
    MAX-ACCESS  read-only
    STATUS      current
    DESCRIPTION
"
synchronization status line from file assp_sync.cfg for baysSpamHaters
 0 - synchronization not configured
 1 - out of sync - running master mode
 2 - in sync - running  mastermode
 3 - in sync - running slave mode
 4 - in sync - running master mode (wait to reach state 2)
"
    ::= {baysSpamHaters 6}

rblSpamHaters  OBJECT-TYPE
    SYNTAX      OCTET STRING
    MAX-ACCESS  read-write
    STATUS      current
    DESCRIPTION
"

"
    REFERENCE "DNSBL Failures Spam-Hater*"
    DEFVAL { "" }
    ::= {SPAMLoverHater 71}

syncStatrblSpamHaters  OBJECT-TYPE
    SYNTAX      OCTET STRING
    MAX-ACCESS  read-only
    STATUS      current
    DESCRIPTION
"
synchronization status for rblSpamHaters
-1 - rblSpamHaters could not be synchronized
 0 - synchronization not configured
 1 - out of sync - running master mode
 2 - in sync - running  mastermode
 3 - in sync - running slave mode
 4 - in sync - running master mode (wait to reach state 2)
"
    ::= {rblSpamHaters 5}

syncStatStrrblSpamHaters  OBJECT-TYPE
    SYNTAX      OCTET STRING
    MAX-ACCESS  read-only
    STATUS      current
    DESCRIPTION
"
synchronization status line from file assp_sync.cfg for rblSpamHaters
 0 - synchronization not configured
 1 - out of sync - running master mode
 2 - in sync - running  mastermode
 3 - in sync - running slave mode
 4 - in sync - running master mode (wait to reach state 2)
"
    ::= {rblSpamHaters 6}

hlSpamHaters  OBJECT-TYPE
    SYNTAX      OCTET STRING
    MAX-ACCESS  read-write
    STATUS      current
    DESCRIPTION
"

"
    REFERENCE "HELO Blacklisted Spam-Hater*"
    DEFVAL { "" }
    ::= {SPAMLoverHater 72}

syncStathlSpamHaters  OBJECT-TYPE
    SYNTAX      OCTET STRING
    MAX-ACCESS  read-only
    STATUS      current
    DESCRIPTION
"
synchronization status for hlSpamHaters
-1 - hlSpamHaters could not be synchronized
 0 - synchronization not configured
 1 - out of sync - running master mode
 2 - in sync - running  mastermode
 3 - in sync - running slave mode
 4 - in sync - running master mode (wait to reach state 2)
"
    ::= {hlSpamHaters 5}

syncStatStrhlSpamHaters  OBJECT-TYPE
    SYNTAX      OCTET STRING
    MAX-ACCESS  read-only
    STATUS      current
    DESCRIPTION
"
synchronization status line from file assp_sync.cfg for hlSpamHaters
 0 - synchronization not configured
 1 - out of sync - running master mode
 2 - in sync - running  mastermode
 3 - in sync - running slave mode
 4 - in sync - running master mode (wait to reach state 2)
"
    ::= {hlSpamHaters 6}

switchSpamLoverToScoring  OBJECT-TYPE
    SYNTAX      OCTET STRING
    MAX-ACCESS  read-write
    STATUS      current
    DESCRIPTION
"
Put the filter automatically in 'Message Scoring Mode' when DoPenaltyMessage is set (instead of stopping spam processing altogether). 
"
    REFERENCE "Switch Spam-Lover to Message Scoring"
    DEFVAL { "" }
    ::= {SPAMLoverHater 73}

syncStatswitchSpamLoverToScoring  OBJECT-TYPE
    SYNTAX      OCTET STRING
    MAX-ACCESS  read-only
    STATUS      current
    DESCRIPTION
"
synchronization status for switchSpamLoverToScoring
-1 - switchSpamLoverToScoring could not be synchronized
 0 - synchronization not configured
 1 - out of sync - running master mode
 2 - in sync - running  mastermode
 3 - in sync - running slave mode
 4 - in sync - running master mode (wait to reach state 2)
"
    ::= {switchSpamLoverToScoring 5}

syncStatStrswitchSpamLoverToScoring  OBJECT-TYPE
    SYNTAX      OCTET STRING
    MAX-ACCESS  read-only
    STATUS      current
    DESCRIPTION
"
synchronization status line from file assp_sync.cfg for switchSpamLoverToScoring
 0 - synchronization not configured
 1 - out of sync - running master mode
 2 - in sync - running  mastermode
 3 - in sync - running slave mode
 4 - in sync - running master mode (wait to reach state 2)
"
    ::= {switchSpamLoverToScoring 6}

groupSpamLovers  OBJECT-TYPE
    SYNTAX      OCTET STRING
    MAX-ACCESS  read-write
    STATUS      current
    DESCRIPTION
"
If set, the first envelope recipient consider a mail to be for spamlovers or not. If the first envelope recipient is any SpamLover, all other (following) envelope recipients must be also any SpamLover (or reverse) - if not, their address will be not accepted by ASSP for this single mail and '452 too many recipients' will be sent.
"
    REFERENCE "Group SpamLovers and Not SpamLovers per mail"
    DEFVAL { "" }
    ::= {SPAMLoverHater 880}

syncStatgroupSpamLovers  OBJECT-TYPE
    SYNTAX      OCTET STRING
    MAX-ACCESS  read-only
    STATUS      current
    DESCRIPTION
"
synchronization status for groupSpamLovers
-1 - groupSpamLovers could not be synchronized
 0 - synchronization not configured
 1 - out of sync - running master mode
 2 - in sync - running  mastermode
 3 - in sync - running slave mode
 4 - in sync - running master mode (wait to reach state 2)
"
    ::= {groupSpamLovers 5}

syncStatStrgroupSpamLovers  OBJECT-TYPE
    SYNTAX      OCTET STRING
    MAX-ACCESS  read-only
    STATUS      current
    DESCRIPTION
"
synchronization status line from file assp_sync.cfg for groupSpamLovers
 0 - synchronization not configured
 1 - out of sync - running master mode
 2 - in sync - running  mastermode
 3 - in sync - running slave mode
 4 - in sync - running master mode (wait to reach state 2)
"
    ::= {groupSpamLovers 6}

NoProcessing  OBJECT IDENTIFIER ::= {asspConfig 7}
noProcessingIPs  OBJECT-TYPE
    SYNTAX      OCTET STRING
    MAX-ACCESS  read-write
    STATUS      current
    DESCRIPTION
"
Mail from any of these IP's will pass through without processing. 
 For example: 145.145.145.145|146.145.
  To define IP's only for specific email addresses or domains (recipients) you must use the file:... option
  An entry (line) may look as follows:
  145.146.0.0/16=>*@local.domain|user@mydomain|user2@*.mydomain # comment
  It is possible to define a predefined group on any or both sides of the '=>' separator, like:
  [ipgroup]=>[usergroup]|user@mydomain
  NOTICE: the following combination of two entries, will lead in to a user/domain based matching - the global entry will be ignored!
  145.146.0.0/16 # comment
  145.146.0.0/16=>*@local.domain|user@mydomain|user2@*.mydomain # comment
  If multiple user/domain based entries are defined for the same IP, only the last one will be used!
  All fields marked by '*' accept  a filepath/filename : 'file:files/ipnp.txt'.
"
    REFERENCE "No Processing IPs*"
    DEFVAL { "file:files/ipnp.txt" }
    ::= {NoProcessing 74}

syncStatnoProcessingIPs  OBJECT-TYPE
    SYNTAX      OCTET STRING
    MAX-ACCESS  read-only
    STATUS      current
    DESCRIPTION
"
synchronization status for noProcessingIPs
-1 - noProcessingIPs could not be synchronized
 0 - synchronization not configured
 1 - out of sync - running master mode
 2 - in sync - running  mastermode
 3 - in sync - running slave mode
 4 - in sync - running master mode (wait to reach state 2)
"
    ::= {noProcessingIPs 5}

syncStatStrnoProcessingIPs  OBJECT-TYPE
    SYNTAX      OCTET STRING
    MAX-ACCESS  read-only
    STATUS      current
    DESCRIPTION
"
synchronization status line from file assp_sync.cfg for noProcessingIPs
 0 - synchronization not configured
 1 - out of sync - running master mode
 2 - in sync - running  mastermode
 3 - in sync - running slave mode
 4 - in sync - running master mode (wait to reach state 2)
"
    ::= {noProcessingIPs 6}

noProcessing  OBJECT-TYPE
    SYNTAX      OCTET STRING
    MAX-ACCESS  read-write
    STATUS      current
    DESCRIPTION
"
Mail solely to or from any of these addresses are proxied without processing. The envelope sender and recipients are checked. Like a more efficient version of Spam-Lovers &amp; redlist combined. Accepts specific addresses (user@domain.com), user parts (user) or entire domains (@domain.com).  Wildcards are supported (fribo*@domain.com). If you register TO addresses here, all recipients for a single mail must be marked as noprocessing to flag the mail as 'noprocessing'.
"
    REFERENCE "No Processing Addresses*"
    DEFVAL { "" }
    ::= {NoProcessing 75}

syncStatnoProcessing  OBJECT-TYPE
    SYNTAX      OCTET STRING
    MAX-ACCESS  read-only
    STATUS      current
    DESCRIPTION
"
synchronization status for noProcessing
-1 - noProcessing could not be synchronized
 0 - synchronization not configured
 1 - out of sync - running master mode
 2 - in sync - running  mastermode
 3 - in sync - running slave mode
 4 - in sync - running master mode (wait to reach state 2)
"
    ::= {noProcessing 5}

syncStatStrnoProcessing  OBJECT-TYPE
    SYNTAX      OCTET STRING
    MAX-ACCESS  read-only
    STATUS      current
    DESCRIPTION
"
synchronization status line from file assp_sync.cfg for noProcessing
 0 - synchronization not configured
 1 - out of sync - running master mode
 2 - in sync - running  mastermode
 3 - in sync - running slave mode
 4 - in sync - running master mode (wait to reach state 2)
"
    ::= {noProcessing 6}

noProcessingFrom  OBJECT-TYPE
    SYNTAX      OCTET STRING
    MAX-ACCESS  read-write
    STATUS      current
    DESCRIPTION
"
Mail solely from any of these addresses are proxied without processing. Accepts specific addresses (user@example.com), user parts (user) or entire domains (@example.com).  Wildcards are supported (fribo*@example.com).
"
    REFERENCE "No Processing Addresses From*"
    DEFVAL { "" }
    ::= {NoProcessing 76}

syncStatnoProcessingFrom  OBJECT-TYPE
    SYNTAX      OCTET STRING
    MAX-ACCESS  read-only
    STATUS      current
    DESCRIPTION
"
synchronization status for noProcessingFrom
-1 - noProcessingFrom could not be synchronized
 0 - synchronization not configured
 1 - out of sync - running master mode
 2 - in sync - running  mastermode
 3 - in sync - running slave mode
 4 - in sync - running master mode (wait to reach state 2)
"
    ::= {noProcessingFrom 5}

syncStatStrnoProcessingFrom  OBJECT-TYPE
    SYNTAX      OCTET STRING
    MAX-ACCESS  read-only
    STATUS      current
    DESCRIPTION
"
synchronization status line from file assp_sync.cfg for noProcessingFrom
 0 - synchronization not configured
 1 - out of sync - running master mode
 2 - in sync - running  mastermode
 3 - in sync - running slave mode
 4 - in sync - running master mode (wait to reach state 2)
"
    ::= {noProcessingFrom 6}

noProcessingDomains  OBJECT-TYPE
    SYNTAX      OCTET STRING
    MAX-ACCESS  read-write
    STATUS      current
    DESCRIPTION
"
Domains from which you want to receive all mail and  proxy without processing. Your ISP, domain registration, mail list servers, stock broker, or other key business partners might be good candidates. Note this matches the end of the address, so if you don't want to match subdomains then include the @. Note that buy.com would also match spambuy.com but .buy.com won't match buy.com. For example: sourceforge.net|@google.com|.buy.com
"
    REFERENCE "No Processing Domains*"
    DEFVAL { "sourceforge.net" }
    ::= {NoProcessing 77}

syncStatnoProcessingDomains  OBJECT-TYPE
    SYNTAX      OCTET STRING
    MAX-ACCESS  read-only
    STATUS      current
    DESCRIPTION
"
synchronization status for noProcessingDomains
-1 - noProcessingDomains could not be synchronized
 0 - synchronization not configured
 1 - out of sync - running master mode
 2 - in sync - running  mastermode
 3 - in sync - running slave mode
 4 - in sync - running master mode (wait to reach state 2)
"
    ::= {noProcessingDomains 5}

syncStatStrnoProcessingDomains  OBJECT-TYPE
    SYNTAX      OCTET STRING
    MAX-ACCESS  read-only
    STATUS      current
    DESCRIPTION
"
synchronization status line from file assp_sync.cfg for noProcessingDomains
 0 - synchronization not configured
 1 - out of sync - running master mode
 2 - in sync - running  mastermode
 3 - in sync - running slave mode
 4 - in sync - running master mode (wait to reach state 2)
"
    ::= {noProcessingDomains 6}

npRe  OBJECT-TYPE
    SYNTAX      OCTET STRING
    MAX-ACCESS  read-write
    STATUS      current
    DESCRIPTION
"
If a message matches this Perl regular expression ASSP will treat the message as a 'No Processing' mail. For example: 169\.254\.122\.|172\.16\.|\[autoreply\].
"
    REFERENCE "Regular Expression to Identify No Processing Mail*"
    DEFVAL { "" }
    ::= {NoProcessing 78}

syncStatnpRe  OBJECT-TYPE
    SYNTAX      OCTET STRING
    MAX-ACCESS  read-only
    STATUS      current
    DESCRIPTION
"
synchronization status for npRe
-1 - npRe could not be synchronized
 0 - synchronization not configured
 1 - out of sync - running master mode
 2 - in sync - running  mastermode
 3 - in sync - running slave mode
 4 - in sync - running master mode (wait to reach state 2)
"
    ::= {npRe 5}

syncStatStrnpRe  OBJECT-TYPE
    SYNTAX      OCTET STRING
    MAX-ACCESS  read-only
    STATUS      current
    DESCRIPTION
"
synchronization status line from file assp_sync.cfg for npRe
 0 - synchronization not configured
 1 - out of sync - running master mode
 2 - in sync - running  mastermode
 3 - in sync - running slave mode
 4 - in sync - running master mode (wait to reach state 2)
"
    ::= {npRe 6}

npSize  OBJECT-TYPE
    SYNTAX      OCTET STRING
    MAX-ACCESS  read-write
    STATUS      current
    DESCRIPTION
"
ASSP will treat incoming messages larger than this SIZE (in bytes) as 'No Processing' mail, after the header part of the mail is received without any error. Empty or 0 disables the feature.
"
    REFERENCE "Message Size Limit"
    DEFVAL { "500000" }
    ::= {NoProcessing 79}

syncStatnpSize  OBJECT-TYPE
    SYNTAX      OCTET STRING
    MAX-ACCESS  read-only
    STATUS      current
    DESCRIPTION
"
synchronization status for npSize
-1 - npSize could not be synchronized
 0 - synchronization not configured
 1 - out of sync - running master mode
 2 - in sync - running  mastermode
 3 - in sync - running slave mode
 4 - in sync - running master mode (wait to reach state 2)
"
    ::= {npSize 5}

syncStatStrnpSize  OBJECT-TYPE
    SYNTAX      OCTET STRING
    MAX-ACCESS  read-only
    STATUS      current
    DESCRIPTION
"
synchronization status line from file assp_sync.cfg for npSize
 0 - synchronization not configured
 1 - out of sync - running master mode
 2 - in sync - running  mastermode
 3 - in sync - running slave mode
 4 - in sync - running master mode (wait to reach state 2)
"
    ::= {npSize 6}

npSizeOut  OBJECT-TYPE
    SYNTAX      OCTET STRING
    MAX-ACCESS  read-write
    STATUS      current
    DESCRIPTION
"
ASSP will treat outgoing messages larger than this SIZE (in bytes) as 'No Processing' mail. Empty or 0 disables the feature. 
"
    REFERENCE "Message Size Limit Outgoing"
    DEFVAL { "500000" }
    ::= {NoProcessing 80}

syncStatnpSizeOut  OBJECT-TYPE
    SYNTAX      OCTET STRING
    MAX-ACCESS  read-only
    STATUS      current
    DESCRIPTION
"
synchronization status for npSizeOut
-1 - npSizeOut could not be synchronized
 0 - synchronization not configured
 1 - out of sync - running master mode
 2 - in sync - running  mastermode
 3 - in sync - running slave mode
 4 - in sync - running master mode (wait to reach state 2)
"
    ::= {npSizeOut 5}

syncStatStrnpSizeOut  OBJECT-TYPE
    SYNTAX      OCTET STRING
    MAX-ACCESS  read-only
    STATUS      current
    DESCRIPTION
"
synchronization status line from file assp_sync.cfg for npSizeOut
 0 - synchronization not configured
 1 - out of sync - running master mode
 2 - in sync - running  mastermode
 3 - in sync - running slave mode
 4 - in sync - running master mode (wait to reach state 2)
"
    ::= {npSizeOut 6}

processOnlyAddresses  OBJECT-TYPE
    SYNTAX      OCTET STRING
    MAX-ACCESS  read-write
    STATUS      current
    DESCRIPTION
"
Mail solely to or from any of these addresses will be processed by ASSP. All others will be proxied without processing. Accepts specific addresses (user@domain.com), user parts (user) or entire domains (@domain.com).  Wildcards are supported (fribo*@domain.com). Note that if an address matches both the NoProcessing and the OnlyTheseProcessing lists, the NoProcessing rules take precedence.
"
    REFERENCE "Process Only These Addresses*"
    DEFVAL { "" }
    ::= {NoProcessing 81}

syncStatprocessOnlyAddresses  OBJECT-TYPE
    SYNTAX      OCTET STRING
    MAX-ACCESS  read-only
    STATUS      current
    DESCRIPTION
"
synchronization status for processOnlyAddresses
-1 - processOnlyAddresses could not be synchronized
 0 - synchronization not configured
 1 - out of sync - running master mode
 2 - in sync - running  mastermode
 3 - in sync - running slave mode
 4 - in sync - running master mode (wait to reach state 2)
"
    ::= {processOnlyAddresses 5}

syncStatStrprocessOnlyAddresses  OBJECT-TYPE
    SYNTAX      OCTET STRING
    MAX-ACCESS  read-only
    STATUS      current
    DESCRIPTION
"
synchronization status line from file assp_sync.cfg for processOnlyAddresses
 0 - synchronization not configured
 1 - out of sync - running master mode
 2 - in sync - running  mastermode
 3 - in sync - running slave mode
 4 - in sync - running master mode (wait to reach state 2)
"
    ::= {processOnlyAddresses 6}

poTestMode  OBJECT-TYPE
    SYNTAX      OCTET STRING
    MAX-ACCESS  read-write
    STATUS      current
    DESCRIPTION
"

"
    REFERENCE "Enable Process Only Addresses"
    DEFVAL { "" }
    ::= {NoProcessing 82}

syncStatpoTestMode  OBJECT-TYPE
    SYNTAX      OCTET STRING
    MAX-ACCESS  read-only
    STATUS      current
    DESCRIPTION
"
synchronization status for poTestMode
-1 - poTestMode could not be synchronized
 0 - synchronization not configured
 1 - out of sync - running master mode
 2 - in sync - running  mastermode
 3 - in sync - running slave mode
 4 - in sync - running master mode (wait to reach state 2)
"
    ::= {poTestMode 5}

syncStatStrpoTestMode  OBJECT-TYPE
    SYNTAX      OCTET STRING
    MAX-ACCESS  read-only
    STATUS      current
    DESCRIPTION
"
synchronization status line from file assp_sync.cfg for poTestMode
 0 - synchronization not configured
 1 - out of sync - running master mode
 2 - in sync - running  mastermode
 3 - in sync - running slave mode
 4 - in sync - running master mode (wait to reach state 2)
"
    ::= {poTestMode 6}

Whitelisting  OBJECT IDENTIFIER ::= {asspConfig 8}
whiteListedIPs  OBJECT-TYPE
    SYNTAX      OCTET STRING
    MAX-ACCESS  read-write
    STATUS      current
    DESCRIPTION
"
They contribute to the Whitelist and to Notspam. For example: 145.145.145.145|146.145.|146.145.0.0/16. It is recommended to use the CIDR notation.
  To define IP's only for specific email addresses or domains (recipients) you must use the file:... option
  An entry (line) may look as follows:
  145.146.0.0/16=>*@local.domain|user@mydomain|user2@*.mydomain # comment
  It is possible to define a predefined group on any or both sides of the '=>' separator, like:
  [ipgroup]=>[usergroup]|user@mydomain
  NOTICE: the following combination of two entries, will lead in to a user/domain based matching - the global entry will be ignored!
  145.146.0.0/16 # comment
  145.146.0.0/16=>*@local.domain|user@mydomain|user2@*.mydomain # comment
  If multiple user/domain based entries are defined for the same IP, only the last one will be used!
   All fields marked by '*' accept  a filepath/filename : 'file:files/ipwl.txt'.
"
    REFERENCE "Whitelisted IPs*"
    DEFVAL { "file:files/ipwl.txt" }
    ::= {Whitelisting 83}

syncStatwhiteListedIPs  OBJECT-TYPE
    SYNTAX      OCTET STRING
    MAX-ACCESS  read-only
    STATUS      current
    DESCRIPTION
"
synchronization status for whiteListedIPs
-1 - whiteListedIPs could not be synchronized
 0 - synchronization not configured
 1 - out of sync - running master mode
 2 - in sync - running  mastermode
 3 - in sync - running slave mode
 4 - in sync - running master mode (wait to reach state 2)
"
    ::= {whiteListedIPs 5}

syncStatStrwhiteListedIPs  OBJECT-TYPE
    SYNTAX      OCTET STRING
    MAX-ACCESS  read-only
    STATUS      current
    DESCRIPTION
"
synchronization status line from file assp_sync.cfg for whiteListedIPs
 0 - synchronization not configured
 1 - out of sync - running master mode
 2 - in sync - running  mastermode
 3 - in sync - running slave mode
 4 - in sync - running master mode (wait to reach state 2)
"
    ::= {whiteListedIPs 6}

whiteRe  OBJECT-TYPE
    SYNTAX      OCTET STRING
    MAX-ACCESS  read-write
    STATUS      current
    DESCRIPTION
"
If an incoming email matches this Perl regular expression it will be considered whitelisted.For example: Secret Ham Password|307\D{0,3}730\D{0,3}4[12]\d\dFor help writing regular expressions click .IMPORTANT: The body is scanned in a later stage  AFTER all sender related checks are performed. So a white regular expression here might not prevent the message to be blocked by eg. invalid PTR. Set the sender related checks to score only if you want to make sure that the white regular expression will be seen. Some things you might include here are your office phone number or street address, spam rarely includes these details.  .
"
    REFERENCE "Regular Expression to Identify Non-Spam*"
    DEFVAL { "" }
    ::= {Whitelisting 84}

syncStatwhiteRe  OBJECT-TYPE
    SYNTAX      OCTET STRING
    MAX-ACCESS  read-only
    STATUS      current
    DESCRIPTION
"
synchronization status for whiteRe
-1 - whiteRe could not be synchronized
 0 - synchronization not configured
 1 - out of sync - running master mode
 2 - in sync - running  mastermode
 3 - in sync - running slave mode
 4 - in sync - running master mode (wait to reach state 2)
"
    ::= {whiteRe 5}

syncStatStrwhiteRe  OBJECT-TYPE
    SYNTAX      OCTET STRING
    MAX-ACCESS  read-only
    STATUS      current
    DESCRIPTION
"
synchronization status line from file assp_sync.cfg for whiteRe
 0 - synchronization not configured
 1 - out of sync - running master mode
 2 - in sync - running  mastermode
 3 - in sync - running slave mode
 4 - in sync - running master mode (wait to reach state 2)
"
    ::= {whiteRe 6}

whiteListedDomains  OBJECT-TYPE
    SYNTAX      OCTET STRING
    MAX-ACCESS  read-write
    STATUS      current
    DESCRIPTION
"
Domains and addresses from which you want to receive all mail. Your ISP, domain registration, mail list servers, stock broker, or other key business partners might be good candidates. Be careful not to put widely used or local domains here like google.com or hotmail.com or mydomain.com. Note this matches the end of the address, so if you don't want to match subdomains then include the @. Note that example.com would also match spamexample.com but .example.com won't match example.com. Wildcards are supported. For example: sourceforge.net|group*@google.com|.example.com
  It is possible to make email addresses whitelisted only for a set of local domains and/or local users. Use wildcards (* and ?) to define domains.
  Use the following syntax to do this:
  *@anydomain=>*@any_local_domain - for domain to domain
  *@*.anydomain=>*@any_local_domain - for any sub-domain to domain
  user@anydomain=>*@*.any_local_domain - for user to any sub-domain
  It is possible to define more than one entry at the left and the right side of the definition (=&gt;), like:
  *@anydomain|*@other_domain=>*@any_local_domain|*@other_local_domain - always separate multiple entries by pipes
  It is also possible to use a GroupDefinition in any or both sides, like:
  [sendergroup]=>[recipientgroup]
  [sendergroup1]|[sendergroup2]|*@domain=>[recipientgroup1]|[recipientgroup2]|user@local_domain
  NOTICE - that the local email addresses and domains are not checked to be local once
"
    REFERENCE "Whitelisted Domains and Addresses*"
    DEFVAL { "file:files/whitedomains.txt" }
    ::= {Whitelisting 85}

syncStatwhiteListedDomains  OBJECT-TYPE
    SYNTAX      OCTET STRING
    MAX-ACCESS  read-only
    STATUS      current
    DESCRIPTION
"
synchronization status for whiteListedDomains
-1 - whiteListedDomains could not be synchronized
 0 - synchronization not configured
 1 - out of sync - running master mode
 2 - in sync - running  mastermode
 3 - in sync - running slave mode
 4 - in sync - running master mode (wait to reach state 2)
"
    ::= {whiteListedDomains 5}

syncStatStrwhiteListedDomains  OBJECT-TYPE
    SYNTAX      OCTET STRING
    MAX-ACCESS  read-only
    STATUS      current
    DESCRIPTION
"
synchronization status line from file assp_sync.cfg for whiteListedDomains
 0 - synchronization not configured
 1 - out of sync - running master mode
 2 - in sync - running  mastermode
 3 - in sync - running slave mode
 4 - in sync - running master mode (wait to reach state 2)
"
    ::= {whiteListedDomains 6}

wildcardUser  OBJECT-TYPE
    SYNTAX      OCTET STRING
    MAX-ACCESS  read-write
    STATUS      current
    DESCRIPTION
"
If you add this user via email-interface(eg: *@domain.com), the whole domain will be whitelisted. For example: '*'
"
    REFERENCE "Wildcard User for White Domain "
    DEFVAL { "*" }
    ::= {Whitelisting 86}

syncStatwildcardUser  OBJECT-TYPE
    SYNTAX      OCTET STRING
    MAX-ACCESS  read-only
    STATUS      current
    DESCRIPTION
"
synchronization status for wildcardUser
-1 - wildcardUser could not be synchronized
 0 - synchronization not configured
 1 - out of sync - running master mode
 2 - in sync - running  mastermode
 3 - in sync - running slave mode
 4 - in sync - running master mode (wait to reach state 2)
"
    ::= {wildcardUser 5}

syncStatStrwildcardUser  OBJECT-TYPE
    SYNTAX      OCTET STRING
    MAX-ACCESS  read-only
    STATUS      current
    DESCRIPTION
"
synchronization status line from file assp_sync.cfg for wildcardUser
 0 - synchronization not configured
 1 - out of sync - running master mode
 2 - in sync - running  mastermode
 3 - in sync - running slave mode
 4 - in sync - running master mode (wait to reach state 2)
"
    ::= {wildcardUser 6}

ValidateRWL  OBJECT-TYPE
    SYNTAX      OCTET STRING
    MAX-ACCESS  read-write
    STATUS      current
    DESCRIPTION
"
RWL: Real-time white list. These are lists of IP addresses that have
 somehow been verified to be from a known good host. Senders that pass RWL validation will pass IP-based filters. This requires an installed  module in PERL. 
"
    REFERENCE "Enable Realtime Whitelist Validation"
    DEFVAL { "" }
    ::= {Whitelisting 87}

syncStatValidateRWL  OBJECT-TYPE
    SYNTAX      OCTET STRING
    MAX-ACCESS  read-only
    STATUS      current
    DESCRIPTION
"
synchronization status for ValidateRWL
-1 - ValidateRWL could not be synchronized
 0 - synchronization not configured
 1 - out of sync - running master mode
 2 - in sync - running  mastermode
 3 - in sync - running slave mode
 4 - in sync - running master mode (wait to reach state 2)
"
    ::= {ValidateRWL 5}

syncStatStrValidateRWL  OBJECT-TYPE
    SYNTAX      OCTET STRING
    MAX-ACCESS  read-only
    STATUS      current
    DESCRIPTION
"
synchronization status line from file assp_sync.cfg for ValidateRWL
 0 - synchronization not configured
 1 - out of sync - running master mode
 2 - in sync - running  mastermode
 3 - in sync - running slave mode
 4 - in sync - running master mode (wait to reach state 2)
"
    ::= {ValidateRWL 6}

RWLwhitelisting  OBJECT-TYPE
    SYNTAX      OCTET STRING
    MAX-ACCESS  read-write
    STATUS      current
    DESCRIPTION
"
If set, the message will also pass Bayesian Filter and URIBL.
"
    REFERENCE "Whitelist all RWL Validated Addresses"
    DEFVAL { "" }
    ::= {Whitelisting 88}

syncStatRWLwhitelisting  OBJECT-TYPE
    SYNTAX      OCTET STRING
    MAX-ACCESS  read-only
    STATUS      current
    DESCRIPTION
"
synchronization status for RWLwhitelisting
-1 - RWLwhitelisting could not be synchronized
 0 - synchronization not configured
 1 - out of sync - running master mode
 2 - in sync - running  mastermode
 3 - in sync - running slave mode
 4 - in sync - running master mode (wait to reach state 2)
"
    ::= {RWLwhitelisting 5}

syncStatStrRWLwhitelisting  OBJECT-TYPE
    SYNTAX      OCTET STRING
    MAX-ACCESS  read-only
    STATUS      current
    DESCRIPTION
"
synchronization status line from file assp_sync.cfg for RWLwhitelisting
 0 - synchronization not configured
 1 - out of sync - running master mode
 2 - in sync - running  mastermode
 3 - in sync - running slave mode
 4 - in sync - running master mode (wait to reach state 2)
"
    ::= {RWLwhitelisting 6}

RWLServiceProvider  OBJECT-TYPE
    SYNTAX      OCTET STRING
    MAX-ACCESS  read-write
    STATUS      current
    DESCRIPTION
"
Host Names of RWLs to use separated by '|'.
 Examples are:
 list.dnswl.org|query.bondedsender.org|cml.anti-spam.org.cn|iadb.isipp.com|hul.habeas.com 
"
    REFERENCE "RWL Service Providers*"
    DEFVAL { "file:files/dnsrws.txt" }
    ::= {Whitelisting 89}

syncStatRWLServiceProvider  OBJECT-TYPE
    SYNTAX      OCTET STRING
    MAX-ACCESS  read-only
    STATUS      current
    DESCRIPTION
"
synchronization status for RWLServiceProvider
-1 - RWLServiceProvider could not be synchronized
 0 - synchronization not configured
 1 - out of sync - running master mode
 2 - in sync - running  mastermode
 3 - in sync - running slave mode
 4 - in sync - running master mode (wait to reach state 2)
"
    ::= {RWLServiceProvider 5}

syncStatStrRWLServiceProvider  OBJECT-TYPE
    SYNTAX      OCTET STRING
    MAX-ACCESS  read-only
    STATUS      current
    DESCRIPTION
"
synchronization status line from file assp_sync.cfg for RWLServiceProvider
 0 - synchronization not configured
 1 - out of sync - running master mode
 2 - in sync - running  mastermode
 3 - in sync - running slave mode
 4 - in sync - running master mode (wait to reach state 2)
"
    ::= {RWLServiceProvider 6}

RWLmaxreplies  OBJECT-TYPE
    SYNTAX      OCTET STRING
    MAX-ACCESS  read-write
    STATUS      current
    DESCRIPTION
"
A reply is affirmative or negative reply from a RWL. The RWL module will wait for this number of replies (negative or positive) from the RWLs listed under Service Provider for up to the Maximum Time below. This number should be equal to or less than the number of RWL Service Providers listed to allow for randomly unavailable RWLs. 
"
    REFERENCE "Maximum Replies"
    DEFVAL { "4" }
    ::= {Whitelisting 90}

syncStatRWLmaxreplies  OBJECT-TYPE
    SYNTAX      OCTET STRING
    MAX-ACCESS  read-only
    STATUS      current
    DESCRIPTION
"
synchronization status for RWLmaxreplies
-1 - RWLmaxreplies could not be synchronized
 0 - synchronization not configured
 1 - out of sync - running master mode
 2 - in sync - running  mastermode
 3 - in sync - running slave mode
 4 - in sync - running master mode (wait to reach state 2)
"
    ::= {RWLmaxreplies 5}

syncStatStrRWLmaxreplies  OBJECT-TYPE
    SYNTAX      OCTET STRING
    MAX-ACCESS  read-only
    STATUS      current
    DESCRIPTION
"
synchronization status line from file assp_sync.cfg for RWLmaxreplies
 0 - synchronization not configured
 1 - out of sync - running master mode
 2 - in sync - running  mastermode
 3 - in sync - running slave mode
 4 - in sync - running master mode (wait to reach state 2)
"
    ::= {RWLmaxreplies 6}

RWLminhits  OBJECT-TYPE
    SYNTAX      OCTET STRING
    MAX-ACCESS  read-write
    STATUS      current
    DESCRIPTION
"
A hit is an affirmative response from a RWL. The RWL module will check all of the RWLs listed under Service Provider, and flag the email with a RWL pass flag if equal to or more than this number of RWLs return a positive whitelisted response. This number should be less than or equal to Maximum Replies above and greater than 0
"
    REFERENCE "Minimum Hits"
    DEFVAL { "1" }
    ::= {Whitelisting 91}

syncStatRWLminhits  OBJECT-TYPE
    SYNTAX      OCTET STRING
    MAX-ACCESS  read-only
    STATUS      current
    DESCRIPTION
"
synchronization status for RWLminhits
-1 - RWLminhits could not be synchronized
 0 - synchronization not configured
 1 - out of sync - running master mode
 2 - in sync - running  mastermode
 3 - in sync - running slave mode
 4 - in sync - running master mode (wait to reach state 2)
"
    ::= {RWLminhits 5}

syncStatStrRWLminhits  OBJECT-TYPE
    SYNTAX      OCTET STRING
    MAX-ACCESS  read-only
    STATUS      current
    DESCRIPTION
"
synchronization status line from file assp_sync.cfg for RWLminhits
 0 - synchronization not configured
 1 - out of sync - running master mode
 2 - in sync - running  mastermode
 3 - in sync - running slave mode
 4 - in sync - running master mode (wait to reach state 2)
"
    ::= {RWLminhits 6}

RWLmaxtime  OBJECT-TYPE
    SYNTAX      OCTET STRING
    MAX-ACCESS  read-write
    STATUS      current
    DESCRIPTION
"
This sets the maximum time to spend on each message performing RWL checks
"
    REFERENCE "Maximum Time"
    DEFVAL { "10" }
    ::= {Whitelisting 92}

syncStatRWLmaxtime  OBJECT-TYPE
    SYNTAX      OCTET STRING
    MAX-ACCESS  read-only
    STATUS      current
    DESCRIPTION
"
synchronization status for RWLmaxtime
-1 - RWLmaxtime could not be synchronized
 0 - synchronization not configured
 1 - out of sync - running master mode
 2 - in sync - running  mastermode
 3 - in sync - running slave mode
 4 - in sync - running master mode (wait to reach state 2)
"
    ::= {RWLmaxtime 5}

syncStatStrRWLmaxtime  OBJECT-TYPE
    SYNTAX      OCTET STRING
    MAX-ACCESS  read-only
    STATUS      current
    DESCRIPTION
"
synchronization status line from file assp_sync.cfg for RWLmaxtime
 0 - synchronization not configured
 1 - out of sync - running master mode
 2 - in sync - running  mastermode
 3 - in sync - running slave mode
 4 - in sync - running master mode (wait to reach state 2)
"
    ::= {RWLmaxtime 6}

noRWL  OBJECT-TYPE
    SYNTAX      OCTET STRING
    MAX-ACCESS  read-write
    STATUS      current
    DESCRIPTION
"
Enter IP addresses that you don't want to be RWL validated, separated by pipes (|). For example: 145.145.145.145|146.145.
"
    REFERENCE "Don't Validate RWL for these IPs*"
    DEFVAL { "" }
    ::= {Whitelisting 93}

syncStatnoRWL  OBJECT-TYPE
    SYNTAX      OCTET STRING
    MAX-ACCESS  read-only
    STATUS      current
    DESCRIPTION
"
synchronization status for noRWL
-1 - noRWL could not be synchronized
 0 - synchronization not configured
 1 - out of sync - running master mode
 2 - in sync - running  mastermode
 3 - in sync - running slave mode
 4 - in sync - running master mode (wait to reach state 2)
"
    ::= {noRWL 5}

syncStatStrnoRWL  OBJECT-TYPE
    SYNTAX      OCTET STRING
    MAX-ACCESS  read-only
    STATUS      current
    DESCRIPTION
"
synchronization status line from file assp_sync.cfg for noRWL
 0 - synchronization not configured
 1 - out of sync - running master mode
 2 - in sync - running  mastermode
 3 - in sync - running slave mode
 4 - in sync - running master mode (wait to reach state 2)
"
    ::= {noRWL 6}

AddRWLHeader  OBJECT-TYPE
    SYNTAX      OCTET STRING
    MAX-ACCESS  read-write
    STATUS      current
    DESCRIPTION
"
Add X-Assp-Received-RWL header to header of all mails processed by RWL.
"
    REFERENCE "Add X-Assp-Received-RWL Header"
    DEFVAL { "1" }
    ::= {Whitelisting 94}

syncStatAddRWLHeader  OBJECT-TYPE
    SYNTAX      OCTET STRING
    MAX-ACCESS  read-only
    STATUS      current
    DESCRIPTION
"
synchronization status for AddRWLHeader
-1 - AddRWLHeader could not be synchronized
 0 - synchronization not configured
 1 - out of sync - running master mode
 2 - in sync - running  mastermode
 3 - in sync - running slave mode
 4 - in sync - running master mode (wait to reach state 2)
"
    ::= {AddRWLHeader 5}

syncStatStrAddRWLHeader  OBJECT-TYPE
    SYNTAX      OCTET STRING
    MAX-ACCESS  read-only
    STATUS      current
    DESCRIPTION
"
synchronization status line from file assp_sync.cfg for AddRWLHeader
 0 - synchronization not configured
 1 - out of sync - running master mode
 2 - in sync - running  mastermode
 3 - in sync - running slave mode
 4 - in sync - running master mode (wait to reach state 2)
"
    ::= {AddRWLHeader 6}

RWLCacheInterval  OBJECT-TYPE
    SYNTAX      OCTET STRING
    MAX-ACCESS  read-write
    STATUS      current
    DESCRIPTION
"
IP's in cache will be removed after this interval in days. 0 will disable the cache. 
"
    REFERENCE "RWL Cache Refresh Interval"
    DEFVAL { "7" }
    ::= {Whitelisting 95}

syncStatRWLCacheInterval  OBJECT-TYPE
    SYNTAX      OCTET STRING
    MAX-ACCESS  read-only
    STATUS      current
    DESCRIPTION
"
synchronization status for RWLCacheInterval
-1 - RWLCacheInterval could not be synchronized
 0 - synchronization not configured
 1 - out of sync - running master mode
 2 - in sync - running  mastermode
 3 - in sync - running slave mode
 4 - in sync - running master mode (wait to reach state 2)
"
    ::= {RWLCacheInterval 5}

syncStatStrRWLCacheInterval  OBJECT-TYPE
    SYNTAX      OCTET STRING
    MAX-ACCESS  read-only
    STATUS      current
    DESCRIPTION
"
synchronization status line from file assp_sync.cfg for RWLCacheInterval
 0 - synchronization not configured
 1 - out of sync - running master mode
 2 - in sync - running  mastermode
 3 - in sync - running slave mode
 4 - in sync - running master mode (wait to reach state 2)
"
    ::= {RWLCacheInterval 6}

MaxWhitelistDays  OBJECT-TYPE
    SYNTAX      OCTET STRING
    MAX-ACCESS  read-write
    STATUS      current
    DESCRIPTION
"
This is the number of days an address will be kept on the whitelist and personal blacklist without any email to/from this address. Set it to 0 to keep the entries infinity.
"
    REFERENCE "Max Whitelist/Personal Black Days"
    DEFVAL { "365" }
    ::= {Whitelisting 96}

syncStatMaxWhitelistDays  OBJECT-TYPE
    SYNTAX      OCTET STRING
    MAX-ACCESS  read-only
    STATUS      current
    DESCRIPTION
"
synchronization status for MaxWhitelistDays
-1 - MaxWhitelistDays could not be synchronized
 0 - synchronization not configured
 1 - out of sync - running master mode
 2 - in sync - running  mastermode
 3 - in sync - running slave mode
 4 - in sync - running master mode (wait to reach state 2)
"
    ::= {MaxWhitelistDays 5}

syncStatStrMaxWhitelistDays  OBJECT-TYPE
    SYNTAX      OCTET STRING
    MAX-ACCESS  read-only
    STATUS      current
    DESCRIPTION
"
synchronization status line from file assp_sync.cfg for MaxWhitelistDays
 0 - synchronization not configured
 1 - out of sync - running master mode
 2 - in sync - running  mastermode
 3 - in sync - running slave mode
 4 - in sync - running master mode (wait to reach state 2)
"
    ::= {MaxWhitelistDays 6}

WhitelistOnly  OBJECT-TYPE
    SYNTAX      OCTET STRING
    MAX-ACCESS  read-write
    STATUS      current
    DESCRIPTION
"
Check this if you don't want Bayesian filtering and want to reject all mail from anyone not whitelisted. To do this related to local user addresses, use InternalAndWhiteAddresses and switch this option off.
"
    REFERENCE "Reject All But Whitelisted Mail"
    DEFVAL { "" }
    ::= {Whitelisting 97}

syncStatWhitelistOnly  OBJECT-TYPE
    SYNTAX      OCTET STRING
    MAX-ACCESS  read-only
    STATUS      current
    DESCRIPTION
"
synchronization status for WhitelistOnly
-1 - WhitelistOnly could not be synchronized
 0 - synchronization not configured
 1 - out of sync - running master mode
 2 - in sync - running  mastermode
 3 - in sync - running slave mode
 4 - in sync - running master mode (wait to reach state 2)
"
    ::= {WhitelistOnly 5}

syncStatStrWhitelistOnly  OBJECT-TYPE
    SYNTAX      OCTET STRING
    MAX-ACCESS  read-only
    STATUS      current
    DESCRIPTION
"
synchronization status line from file assp_sync.cfg for WhitelistOnly
 0 - synchronization not configured
 1 - out of sync - running master mode
 2 - in sync - running  mastermode
 3 - in sync - running slave mode
 4 - in sync - running master mode (wait to reach state 2)
"
    ::= {WhitelistOnly 6}

NoAutoWhite  OBJECT-TYPE
    SYNTAX      OCTET STRING
    MAX-ACCESS  read-write
    STATUS      current
    DESCRIPTION
"
Check this box to  allow additions to the whitelist by email interface only.
"
    REFERENCE "Only Email-Interface Addition to Whitelist."
    DEFVAL { "" }
    ::= {Whitelisting 98}

syncStatNoAutoWhite  OBJECT-TYPE
    SYNTAX      OCTET STRING
    MAX-ACCESS  read-only
    STATUS      current
    DESCRIPTION
"
synchronization status for NoAutoWhite
-1 - NoAutoWhite could not be synchronized
 0 - synchronization not configured
 1 - out of sync - running master mode
 2 - in sync - running  mastermode
 3 - in sync - running slave mode
 4 - in sync - running master mode (wait to reach state 2)
"
    ::= {NoAutoWhite 5}

syncStatStrNoAutoWhite  OBJECT-TYPE
    SYNTAX      OCTET STRING
    MAX-ACCESS  read-only
    STATUS      current
    DESCRIPTION
"
synchronization status line from file assp_sync.cfg for NoAutoWhite
 0 - synchronization not configured
 1 - out of sync - running master mode
 2 - in sync - running  mastermode
 3 - in sync - running slave mode
 4 - in sync - running master mode (wait to reach state 2)
"
    ::= {NoAutoWhite 6}

NotGreedyWhitelist  OBJECT-TYPE
    SYNTAX      OCTET STRING
    MAX-ACCESS  read-write
    STATUS      current
    DESCRIPTION
"
Normal operation includes addresses in the FROM, SENDER, REPLY-TO, ERRORS-TO, or LIST-* header fields.
  This allows nearly all list email to be whitelisted.
  If set to 'envelope-sender only', only this address is compared/added.
  If set to 'check all addresses - one match for white - add all', one match in any of this fields is enough to get white and all addresses will be added to whitelist.
  If set to 'check all addresses - all matches for white - update all', all defined addresses in all defined fields must be already whitelisted for a message to get a whitelisted state and all addresses will updated in whitelist. Notice: this setting will overwrite a match in whiteListedDomains , if a not whitelisted sender is found.
  If any address is found in redlist, no whitelist addition will be done and the message gets not white. 
  If the penalty score of a message has reached PenaltyMessageLow, no whitelist addition will be done.
  This setting is ignored, for mails to add/remove whitelist entries via email-interface.
"
    REFERENCE "Only the envelope-sender is added/compared to the whitelist"
    DEFVAL { "0" }
    ::= {Whitelisting 99}

syncStatNotGreedyWhitelist  OBJECT-TYPE
    SYNTAX      OCTET STRING
    MAX-ACCESS  read-only
    STATUS      current
    DESCRIPTION
"
synchronization status for NotGreedyWhitelist
-1 - NotGreedyWhitelist could not be synchronized
 0 - synchronization not configured
 1 - out of sync - running master mode
 2 - in sync - running  mastermode
 3 - in sync - running slave mode
 4 - in sync - running master mode (wait to reach state 2)
"
    ::= {NotGreedyWhitelist 5}

syncStatStrNotGreedyWhitelist  OBJECT-TYPE
    SYNTAX      OCTET STRING
    MAX-ACCESS  read-only
    STATUS      current
    DESCRIPTION
"
synchronization status line from file assp_sync.cfg for NotGreedyWhitelist
 0 - synchronization not configured
 1 - out of sync - running master mode
 2 - in sync - running  mastermode
 3 - in sync - running slave mode
 4 - in sync - running master mode (wait to reach state 2)
"
    ::= {NotGreedyWhitelist 6}

WhitelistLocalOnly  OBJECT-TYPE
    SYNTAX      OCTET STRING
    MAX-ACCESS  read-write
    STATUS      current
    DESCRIPTION
"
Normal operation allows all local, authenticated, or whitelisted users to contribute to the whitelist.
  Check this box to not allow whitelisted users to add to the whitelist.
"
    REFERENCE "Only local or authenticated users contribute to the whitelist."
    DEFVAL { "" }
    ::= {Whitelisting 100}

syncStatWhitelistLocalOnly  OBJECT-TYPE
    SYNTAX      OCTET STRING
    MAX-ACCESS  read-only
    STATUS      current
    DESCRIPTION
"
synchronization status for WhitelistLocalOnly
-1 - WhitelistLocalOnly could not be synchronized
 0 - synchronization not configured
 1 - out of sync - running master mode
 2 - in sync - running  mastermode
 3 - in sync - running slave mode
 4 - in sync - running master mode (wait to reach state 2)
"
    ::= {WhitelistLocalOnly 5}

syncStatStrWhitelistLocalOnly  OBJECT-TYPE
    SYNTAX      OCTET STRING
    MAX-ACCESS  read-only
    STATUS      current
    DESCRIPTION
"
synchronization status line from file assp_sync.cfg for WhitelistLocalOnly
 0 - synchronization not configured
 1 - out of sync - running master mode
 2 - in sync - running  mastermode
 3 - in sync - running slave mode
 4 - in sync - running master mode (wait to reach state 2)
"
    ::= {WhitelistLocalOnly 6}

WhitelistLocalFromOnly  OBJECT-TYPE
    SYNTAX      OCTET STRING
    MAX-ACCESS  read-write
    STATUS      current
    DESCRIPTION
"
Check this box to prevent sender with non-local domains from contributing to the whitelist. (for example: redirected messages).
"
    REFERENCE "Only users with a local domain in mailfrom contribute to the whitelist."
    DEFVAL { "1" }
    ::= {Whitelisting 101}

syncStatWhitelistLocalFromOnly  OBJECT-TYPE
    SYNTAX      OCTET STRING
    MAX-ACCESS  read-only
    STATUS      current
    DESCRIPTION
"
synchronization status for WhitelistLocalFromOnly
-1 - WhitelistLocalFromOnly could not be synchronized
 0 - synchronization not configured
 1 - out of sync - running master mode
 2 - in sync - running  mastermode
 3 - in sync - running slave mode
 4 - in sync - running master mode (wait to reach state 2)
"
    ::= {WhitelistLocalFromOnly 5}

syncStatStrWhitelistLocalFromOnly  OBJECT-TYPE
    SYNTAX      OCTET STRING
    MAX-ACCESS  read-only
    STATUS      current
    DESCRIPTION
"
synchronization status line from file assp_sync.cfg for WhitelistLocalFromOnly
 0 - synchronization not configured
 1 - out of sync - running master mode
 2 - in sync - running  mastermode
 3 - in sync - running slave mode
 4 - in sync - running master mode (wait to reach state 2)
"
    ::= {WhitelistLocalFromOnly 6}

WhitelistAuth  OBJECT-TYPE
    SYNTAX      OCTET STRING
    MAX-ACCESS  read-write
    STATUS      current
    DESCRIPTION
"
Mails from authenticated users will be processed as whitelisted.
"
    REFERENCE "Whitelist mails from authenticated users."
    DEFVAL { "" }
    ::= {Whitelisting 102}

syncStatWhitelistAuth  OBJECT-TYPE
    SYNTAX      OCTET STRING
    MAX-ACCESS  read-only
    STATUS      current
    DESCRIPTION
"
synchronization status for WhitelistAuth
-1 - WhitelistAuth could not be synchronized
 0 - synchronization not configured
 1 - out of sync - running master mode
 2 - in sync - running  mastermode
 3 - in sync - running slave mode
 4 - in sync - running master mode (wait to reach state 2)
"
    ::= {WhitelistAuth 5}

syncStatStrWhitelistAuth  OBJECT-TYPE
    SYNTAX      OCTET STRING
    MAX-ACCESS  read-only
    STATUS      current
    DESCRIPTION
"
synchronization status line from file assp_sync.cfg for WhitelistAuth
 0 - synchronization not configured
 1 - out of sync - running master mode
 2 - in sync - running  mastermode
 3 - in sync - running slave mode
 4 - in sync - running master mode (wait to reach state 2)
"
    ::= {WhitelistAuth 6}

UpdateWhitelist  OBJECT-TYPE
    SYNTAX      OCTET STRING
    MAX-ACCESS  read-write
    STATUS      current
    DESCRIPTION
"
Save a copy of the white list every this many seconds. Empty or Zero will prevent any saving and the cleanup of old records.
  
"
    REFERENCE "Save Whitelist <sup>s</sup>"
    DEFVAL { "3600" }
    ::= {Whitelisting 103}

syncStatUpdateWhitelist  OBJECT-TYPE
    SYNTAX      OCTET STRING
    MAX-ACCESS  read-only
    STATUS      current
    DESCRIPTION
"
synchronization status for UpdateWhitelist
-1 - UpdateWhitelist could not be synchronized
 0 - synchronization not configured
 1 - out of sync - running master mode
 2 - in sync - running  mastermode
 3 - in sync - running slave mode
 4 - in sync - running master mode (wait to reach state 2)
"
    ::= {UpdateWhitelist 5}

syncStatStrUpdateWhitelist  OBJECT-TYPE
    SYNTAX      OCTET STRING
    MAX-ACCESS  read-only
    STATUS      current
    DESCRIPTION
"
synchronization status line from file assp_sync.cfg for UpdateWhitelist
 0 - synchronization not configured
 1 - out of sync - running master mode
 2 - in sync - running  mastermode
 3 - in sync - running slave mode
 4 - in sync - running master mode (wait to reach state 2)
"
    ::= {UpdateWhitelist 6}

GreedyWhitelistAdditions  OBJECT-TYPE
    SYNTAX      OCTET STRING
    MAX-ACCESS  read-write
    STATUS      current
    DESCRIPTION
"
Defines what sender addresses are added to the whitelist if a message is considered to be from a whitelisted sender. NotGreedyWhitelist is considered in determining if a message is from a whitelisted sender.
"
    REFERENCE "How add Greedy Senders to Whitelist"
    DEFVAL { "1" }
    ::= {Whitelisting 878}

syncStatGreedyWhitelistAdditions  OBJECT-TYPE
    SYNTAX      OCTET STRING
    MAX-ACCESS  read-only
    STATUS      current
    DESCRIPTION
"
synchronization status for GreedyWhitelistAdditions
-1 - GreedyWhitelistAdditions could not be synchronized
 0 - synchronization not configured
 1 - out of sync - running master mode
 2 - in sync - running  mastermode
 3 - in sync - running slave mode
 4 - in sync - running master mode (wait to reach state 2)
"
    ::= {GreedyWhitelistAdditions 5}

syncStatStrGreedyWhitelistAdditions  OBJECT-TYPE
    SYNTAX      OCTET STRING
    MAX-ACCESS  read-only
    STATUS      current
    DESCRIPTION
"
synchronization status line from file assp_sync.cfg for GreedyWhitelistAdditions
 0 - synchronization not configured
 1 - out of sync - running master mode
 2 - in sync - running  mastermode
 3 - in sync - running slave mode
 4 - in sync - running master mode (wait to reach state 2)
"
    ::= {GreedyWhitelistAdditions 6}

WhitelistPrivacyLevel  OBJECT-TYPE
    SYNTAX      OCTET STRING
    MAX-ACCESS  read-write
    STATUS      current
    DESCRIPTION
"
Sets the privacy level of the whitelistdb . If an (local) user adds an email address to the whitelist:
  (0) global &amp; private - this email address is automaticaly whitelisted for all other local users
  (1) domain &amp; private - this email address is automaticaly whitelisted for all other local users in the same local domain
  (2) private only - this email address is only whitelisted for this single local user
  (0-1) unless another user has removed this email address from his whitelist. Default is zero, which is the legacy setting.
  NOTICE: independant from this setting, the whitelistdb is filled with all three entries (global,domain,private), to make it possible to change this value.
"
    REFERENCE "PrivacyLevel of the Whitelist"
    DEFVAL { "0" }
    ::= {Whitelisting 974}

syncStatWhitelistPrivacyLevel  OBJECT-TYPE
    SYNTAX      OCTET STRING
    MAX-ACCESS  read-only
    STATUS      current
    DESCRIPTION
"
synchronization status for WhitelistPrivacyLevel
-1 - WhitelistPrivacyLevel could not be synchronized
 0 - synchronization not configured
 1 - out of sync - running master mode
 2 - in sync - running  mastermode
 3 - in sync - running slave mode
 4 - in sync - running master mode (wait to reach state 2)
"
    ::= {WhitelistPrivacyLevel 5}

syncStatStrWhitelistPrivacyLevel  OBJECT-TYPE
    SYNTAX      OCTET STRING
    MAX-ACCESS  read-only
    STATUS      current
    DESCRIPTION
"
synchronization status line from file assp_sync.cfg for WhitelistPrivacyLevel
 0 - synchronization not configured
 1 - out of sync - running master mode
 2 - in sync - running  mastermode
 3 - in sync - running slave mode
 4 - in sync - running master mode (wait to reach state 2)
"
    ::= {WhitelistPrivacyLevel 6}

NoAutoWhiteAdresses  OBJECT-TYPE
    SYNTAX      OCTET STRING
    MAX-ACCESS  read-write
    STATUS      current
    DESCRIPTION
"
Mail solely to or from any of these addresses are excluded from automatic whitelist additions. Accepts specific addresses (user@domain.com), user parts (user) or entire domains (@domain.com).  Wildcards are supported (fribo*@domain.com).
"
    REFERENCE "No AutoWhite Addresses*"
    DEFVAL { "" }
    ::= {Whitelisting 997}

syncStatNoAutoWhiteAdresses  OBJECT-TYPE
    SYNTAX      OCTET STRING
    MAX-ACCESS  read-only
    STATUS      current
    DESCRIPTION
"
synchronization status for NoAutoWhiteAdresses
-1 - NoAutoWhiteAdresses could not be synchronized
 0 - synchronization not configured
 1 - out of sync - running master mode
 2 - in sync - running  mastermode
 3 - in sync - running slave mode
 4 - in sync - running master mode (wait to reach state 2)
"
    ::= {NoAutoWhiteAdresses 5}

syncStatStrNoAutoWhiteAdresses  OBJECT-TYPE
    SYNTAX      OCTET STRING
    MAX-ACCESS  read-only
    STATUS      current
    DESCRIPTION
"
synchronization status line from file assp_sync.cfg for NoAutoWhiteAdresses
 0 - synchronization not configured
 1 - out of sync - running master mode
 2 - in sync - running  mastermode
 3 - in sync - running slave mode
 4 - in sync - running master mode (wait to reach state 2)
"
    ::= {NoAutoWhiteAdresses 6}

Relaying  OBJECT IDENTIFIER ::= {asspConfig 9}
acceptAllMail  OBJECT-TYPE
    SYNTAX      OCTET STRING
    MAX-ACCESS  read-write
    STATUS      current
    DESCRIPTION
"
Relaying is allowed for these IPs. They contribute also to the whitelist. Before setting this option, please read the complete section - it is recommended to configure relayPort to send mails from your LAN to the internet. This can take either a directly entered list of IP's separated by pipes or a file 'file:files/acceptall.txt'.For example: 145.145.145.145|146.145.
"
    REFERENCE "Accept All Mail*"
    DEFVAL { "" }
    ::= {Relaying 104}

syncStatacceptAllMail  OBJECT-TYPE
    SYNTAX      OCTET STRING
    MAX-ACCESS  read-only
    STATUS      current
    DESCRIPTION
"
synchronization status for acceptAllMail
-1 - acceptAllMail could not be synchronized
 0 - synchronization not configured
 1 - out of sync - running master mode
 2 - in sync - running  mastermode
 3 - in sync - running slave mode
 4 - in sync - running master mode (wait to reach state 2)
"
    ::= {acceptAllMail 5}

syncStatStracceptAllMail  OBJECT-TYPE
    SYNTAX      OCTET STRING
    MAX-ACCESS  read-only
    STATUS      current
    DESCRIPTION
"
synchronization status line from file assp_sync.cfg for acceptAllMail
 0 - synchronization not configured
 1 - out of sync - running master mode
 2 - in sync - running  mastermode
 3 - in sync - running slave mode
 4 - in sync - running master mode (wait to reach state 2)
"
    ::= {acceptAllMail 6}

DoLocalSenderDomain  OBJECT-TYPE
    SYNTAX      OCTET STRING
    MAX-ACCESS  read-write
    STATUS      current
    DESCRIPTION
"
If activated, each local sender address must have a valid Local Domain. acceptAllMail and redlisted mails breaks this rule.
"
    REFERENCE "Do Local Domain Check for Local Sender"
    DEFVAL { "" }
    ::= {Relaying 105}

syncStatDoLocalSenderDomain  OBJECT-TYPE
    SYNTAX      OCTET STRING
    MAX-ACCESS  read-only
    STATUS      current
    DESCRIPTION
"
synchronization status for DoLocalSenderDomain
-1 - DoLocalSenderDomain could not be synchronized
 0 - synchronization not configured
 1 - out of sync - running master mode
 2 - in sync - running  mastermode
 3 - in sync - running slave mode
 4 - in sync - running master mode (wait to reach state 2)
"
    ::= {DoLocalSenderDomain 5}

syncStatStrDoLocalSenderDomain  OBJECT-TYPE
    SYNTAX      OCTET STRING
    MAX-ACCESS  read-only
    STATUS      current
    DESCRIPTION
"
synchronization status line from file assp_sync.cfg for DoLocalSenderDomain
 0 - synchronization not configured
 1 - out of sync - running master mode
 2 - in sync - running  mastermode
 3 - in sync - running slave mode
 4 - in sync - running master mode (wait to reach state 2)
"
    ::= {DoLocalSenderDomain 6}

DoLocalSenderAddress  OBJECT-TYPE
    SYNTAX      OCTET STRING
    MAX-ACCESS  read-write
    STATUS      current
    DESCRIPTION
"
If activated, each local sender address must have a valid Local Address. acceptAllMail and redlisted mails breaks this rule.
"
    REFERENCE "Do Local Address Check for Local Sender"
    DEFVAL { "" }
    ::= {Relaying 106}

syncStatDoLocalSenderAddress  OBJECT-TYPE
    SYNTAX      OCTET STRING
    MAX-ACCESS  read-only
    STATUS      current
    DESCRIPTION
"
synchronization status for DoLocalSenderAddress
-1 - DoLocalSenderAddress could not be synchronized
 0 - synchronization not configured
 1 - out of sync - running master mode
 2 - in sync - running  mastermode
 3 - in sync - running slave mode
 4 - in sync - running master mode (wait to reach state 2)
"
    ::= {DoLocalSenderAddress 5}

syncStatStrDoLocalSenderAddress  OBJECT-TYPE
    SYNTAX      OCTET STRING
    MAX-ACCESS  read-only
    STATUS      current
    DESCRIPTION
"
synchronization status line from file assp_sync.cfg for DoLocalSenderAddress
 0 - synchronization not configured
 1 - out of sync - running master mode
 2 - in sync - running  mastermode
 3 - in sync - running slave mode
 4 - in sync - running master mode (wait to reach state 2)
"
    ::= {DoLocalSenderAddress 6}

nolocalDomains  OBJECT-TYPE
    SYNTAX      OCTET STRING
    MAX-ACCESS  read-write
    STATUS      current
    DESCRIPTION
"
Do not check relaying based on localDomains. Let the mailserver do it. NOT RECOMMENDED.
"
    REFERENCE "Skip Local Domain Check"
    DEFVAL { "" }
    ::= {Relaying 107}

syncStatnolocalDomains  OBJECT-TYPE
    SYNTAX      OCTET STRING
    MAX-ACCESS  read-only
    STATUS      current
    DESCRIPTION
"
synchronization status for nolocalDomains
-1 - nolocalDomains could not be synchronized
 0 - synchronization not configured
 1 - out of sync - running master mode
 2 - in sync - running  mastermode
 3 - in sync - running slave mode
 4 - in sync - running master mode (wait to reach state 2)
"
    ::= {nolocalDomains 5}

syncStatStrnolocalDomains  OBJECT-TYPE
    SYNTAX      OCTET STRING
    MAX-ACCESS  read-only
    STATUS      current
    DESCRIPTION
"
synchronization status line from file assp_sync.cfg for nolocalDomains
 0 - synchronization not configured
 1 - out of sync - running master mode
 2 - in sync - running  mastermode
 3 - in sync - running slave mode
 4 - in sync - running master mode (wait to reach state 2)
"
    ::= {nolocalDomains 6}

ldLDAP  OBJECT-TYPE
    SYNTAX      OCTET STRING
    MAX-ACCESS  read-write
    STATUS      current
    DESCRIPTION
"
Check local domains against an LDAP database.Note: Checking this requires filling in LDAP DomainFilter ( ldLDAPFilter ) in the LDAP section.This requires an installed  module in Perl.
"
    REFERENCE "Do LDAP lookup for local domains"
    DEFVAL { "" }
    ::= {Relaying 108}

syncStatldLDAP  OBJECT-TYPE
    SYNTAX      OCTET STRING
    MAX-ACCESS  read-only
    STATUS      current
    DESCRIPTION
"
synchronization status for ldLDAP
-1 - ldLDAP could not be synchronized
 0 - synchronization not configured
 1 - out of sync - running master mode
 2 - in sync - running  mastermode
 3 - in sync - running slave mode
 4 - in sync - running master mode (wait to reach state 2)
"
    ::= {ldLDAP 5}

syncStatStrldLDAP  OBJECT-TYPE
    SYNTAX      OCTET STRING
    MAX-ACCESS  read-only
    STATUS      current
    DESCRIPTION
"
synchronization status line from file assp_sync.cfg for ldLDAP
 0 - synchronization not configured
 1 - out of sync - running master mode
 2 - in sync - running  mastermode
 3 - in sync - running slave mode
 4 - in sync - running master mode (wait to reach state 2)
"
    ::= {ldLDAP 6}

ispip  OBJECT-TYPE
    SYNTAX      OCTET STRING
    MAX-ACCESS  read-write
    STATUS      current
    DESCRIPTION
"
Enter any addresses that are your ISP or backup MX servers, separated by pipes (|). These addresses will (necessarily) bypass Griplist, IP Limiting, Delaying, Penalty Box, SPF, DNSBL &amp; SRS checks unless the IP can be determined by (ispHostnames) ISP/Secondary Hostnames. For example: 127.0.0.1|172.16..
"
    REFERENCE "ISP/Secondary MX Servers*"
    DEFVAL { "" }
    ::= {Relaying 109}

syncStatispip  OBJECT-TYPE
    SYNTAX      OCTET STRING
    MAX-ACCESS  read-only
    STATUS      current
    DESCRIPTION
"
synchronization status for ispip
-1 - ispip could not be synchronized
 0 - synchronization not configured
 1 - out of sync - running master mode
 2 - in sync - running  mastermode
 3 - in sync - running slave mode
 4 - in sync - running master mode (wait to reach state 2)
"
    ::= {ispip 5}

syncStatStrispip  OBJECT-TYPE
    SYNTAX      OCTET STRING
    MAX-ACCESS  read-only
    STATUS      current
    DESCRIPTION
"
synchronization status line from file assp_sync.cfg for ispip
 0 - synchronization not configured
 1 - out of sync - running master mode
 2 - in sync - running  mastermode
 3 - in sync - running slave mode
 4 - in sync - running master mode (wait to reach state 2)
"
    ::= {ispip 6}

contentOnlyRe  OBJECT-TYPE
    SYNTAX      OCTET STRING
    MAX-ACCESS  read-write
    STATUS      current
    DESCRIPTION
"
Put anything here to identify messages which should bypass PB, Sender Validation, Griplist, IP Limiting, Delaying, SPF, DNSBL &amp; SRS checks. For example:  email addresses of people who are forwarding from other accounts to their mailbox on your server.
"
    REFERENCE "Regular Expression to Identify Forwarded Messages*"
    DEFVAL { "" }
    ::= {Relaying 110}

syncStatcontentOnlyRe  OBJECT-TYPE
    SYNTAX      OCTET STRING
    MAX-ACCESS  read-only
    STATUS      current
    DESCRIPTION
"
synchronization status for contentOnlyRe
-1 - contentOnlyRe could not be synchronized
 0 - synchronization not configured
 1 - out of sync - running master mode
 2 - in sync - running  mastermode
 3 - in sync - running slave mode
 4 - in sync - running master mode (wait to reach state 2)
"
    ::= {contentOnlyRe 5}

syncStatStrcontentOnlyRe  OBJECT-TYPE
    SYNTAX      OCTET STRING
    MAX-ACCESS  read-only
    STATUS      current
    DESCRIPTION
"
synchronization status line from file assp_sync.cfg for contentOnlyRe
 0 - synchronization not configured
 1 - out of sync - running master mode
 2 - in sync - running  mastermode
 3 - in sync - running slave mode
 4 - in sync - running master mode (wait to reach state 2)
"
    ::= {contentOnlyRe 6}

ispHostnames  OBJECT-TYPE
    SYNTAX      OCTET STRING
    MAX-ACCESS  read-write
    STATUS      current
    DESCRIPTION
"
Hostnames (regular expression) to lookup the IP that connected to the ISP/Secondary server.If found, this address is used to perform IP-based checks on forwarded messages. For example: mx1\.yourisp\.com or mx1\.yourisp\.net|mx2\.yoursecondary\.com . This hostnames are found in the 'Received:' header, like  'Received: from ...123.123.123.123... by mx1.yourisp.com'. Leave this blank to disable the feature. 
"
    REFERENCE "Regular Expression to Identify ISP/Secondary Hostnames*"
    DEFVAL { "" }
    ::= {Relaying 111}

syncStatispHostnames  OBJECT-TYPE
    SYNTAX      OCTET STRING
    MAX-ACCESS  read-only
    STATUS      current
    DESCRIPTION
"
synchronization status for ispHostnames
-1 - ispHostnames could not be synchronized
 0 - synchronization not configured
 1 - out of sync - running master mode
 2 - in sync - running  mastermode
 3 - in sync - running slave mode
 4 - in sync - running master mode (wait to reach state 2)
"
    ::= {ispHostnames 5}

syncStatStrispHostnames  OBJECT-TYPE
    SYNTAX      OCTET STRING
    MAX-ACCESS  read-only
    STATUS      current
    DESCRIPTION
"
synchronization status line from file assp_sync.cfg for ispHostnames
 0 - synchronization not configured
 1 - out of sync - running master mode
 2 - in sync - running  mastermode
 3 - in sync - running slave mode
 4 - in sync - running master mode (wait to reach state 2)
"
    ::= {ispHostnames 6}

send250OKISP  OBJECT-TYPE
    SYNTAX      OCTET STRING
    MAX-ACCESS  read-write
    STATUS      current
    DESCRIPTION
"
Set this checkbox if you want ASSP to reply to IP's in ISPIP with '250 OK' instead of SMTP error code '554 5.7.1'.
"
    REFERENCE "Send 250 OK To ISP/Secondary MX Servers"
    DEFVAL { "1" }
    ::= {Relaying 112}

syncStatsend250OKISP  OBJECT-TYPE
    SYNTAX      OCTET STRING
    MAX-ACCESS  read-only
    STATUS      current
    DESCRIPTION
"
synchronization status for send250OKISP
-1 - send250OKISP could not be synchronized
 0 - synchronization not configured
 1 - out of sync - running master mode
 2 - in sync - running  mastermode
 3 - in sync - running slave mode
 4 - in sync - running master mode (wait to reach state 2)
"
    ::= {send250OKISP 5}

syncStatStrsend250OKISP  OBJECT-TYPE
    SYNTAX      OCTET STRING
    MAX-ACCESS  read-only
    STATUS      current
    DESCRIPTION
"
synchronization status line from file assp_sync.cfg for send250OKISP
 0 - synchronization not configured
 1 - out of sync - running master mode
 2 - in sync - running  mastermode
 3 - in sync - running slave mode
 4 - in sync - running master mode (wait to reach state 2)
"
    ::= {send250OKISP 6}

ispgripvalue  OBJECT-TYPE
    SYNTAX      OCTET STRING
    MAX-ACCESS  read-write
    STATUS      current
    DESCRIPTION
"
It is recommended  to set it to 0.5 (Completely GReyIP) for ISP and Secondary MX servers. If left blank the Griplist X value is used (percentage of spam messages in relation to total). Note: value has to be greater than 0 and less than 1, where 0 = never spam and 1 = always spam
"
    REFERENCE "ISP/Secondary MX Grip Value"
    DEFVAL { "0.5" }
    ::= {Relaying 113}

syncStatispgripvalue  OBJECT-TYPE
    SYNTAX      OCTET STRING
    MAX-ACCESS  read-only
    STATUS      current
    DESCRIPTION
"
synchronization status for ispgripvalue
-1 - ispgripvalue could not be synchronized
 0 - synchronization not configured
 1 - out of sync - running master mode
 2 - in sync - running  mastermode
 3 - in sync - running slave mode
 4 - in sync - running master mode (wait to reach state 2)
"
    ::= {ispgripvalue 5}

syncStatStrispgripvalue  OBJECT-TYPE
    SYNTAX      OCTET STRING
    MAX-ACCESS  read-only
    STATUS      current
    DESCRIPTION
"
synchronization status line from file assp_sync.cfg for ispgripvalue
 0 - synchronization not configured
 1 - out of sync - running master mode
 2 - in sync - running  mastermode
 3 - in sync - running slave mode
 4 - in sync - running master mode (wait to reach state 2)
"
    ::= {ispgripvalue 6}

BounceSenders  OBJECT-TYPE
    SYNTAX      OCTET STRING
    MAX-ACCESS  read-write
    STATUS      current
    DESCRIPTION
"
Envelope sender addresses treated as bounce origins. Null sender (&lt;&gt;) is always included.
 Accepts specific addresses (postmaster@domain.com), usernames (mailer-daemon), or entire domains (@bounces.domain.com)Separate entries with pipes: |. For example: postmaster|mailer-daemon
"
    REFERENCE "Bounce Senders*"
    DEFVAL { "postmaster|mailer-daemon" }
    ::= {Relaying 114}

syncStatBounceSenders  OBJECT-TYPE
    SYNTAX      OCTET STRING
    MAX-ACCESS  read-only
    STATUS      current
    DESCRIPTION
"
synchronization status for BounceSenders
-1 - BounceSenders could not be synchronized
 0 - synchronization not configured
 1 - out of sync - running master mode
 2 - in sync - running  mastermode
 3 - in sync - running slave mode
 4 - in sync - running master mode (wait to reach state 2)
"
    ::= {BounceSenders 5}

syncStatStrBounceSenders  OBJECT-TYPE
    SYNTAX      OCTET STRING
    MAX-ACCESS  read-only
    STATUS      current
    DESCRIPTION
"
synchronization status line from file assp_sync.cfg for BounceSenders
 0 - synchronization not configured
 1 - out of sync - running master mode
 2 - in sync - running  mastermode
 3 - in sync - running slave mode
 4 - in sync - running master mode (wait to reach state 2)
"
    ::= {BounceSenders 6}

PopB4SMTPFile  OBJECT-TYPE
    SYNTAX      OCTET STRING
    MAX-ACCESS  read-write
    STATUS      current
    DESCRIPTION
"
Enter the DB database filename of your POP before SMTP implementation with records stored for dotted-quad IP addresses.For example: /etc/mail/popip.db
"
    REFERENCE "Pop Before SMTP DB File"
    DEFVAL { "" }
    ::= {Relaying 115}

syncStatPopB4SMTPFile  OBJECT-TYPE
    SYNTAX      OCTET STRING
    MAX-ACCESS  read-only
    STATUS      current
    DESCRIPTION
"
synchronization status for PopB4SMTPFile
-1 - PopB4SMTPFile could not be synchronized
 0 - synchronization not configured
 1 - out of sync - running master mode
 2 - in sync - running  mastermode
 3 - in sync - running slave mode
 4 - in sync - running master mode (wait to reach state 2)
"
    ::= {PopB4SMTPFile 5}

syncStatStrPopB4SMTPFile  OBJECT-TYPE
    SYNTAX      OCTET STRING
    MAX-ACCESS  read-only
    STATUS      current
    DESCRIPTION
"
synchronization status line from file assp_sync.cfg for PopB4SMTPFile
 0 - synchronization not configured
 1 - out of sync - running master mode
 2 - in sync - running  mastermode
 3 - in sync - running slave mode
 4 - in sync - running master mode (wait to reach state 2)
"
    ::= {PopB4SMTPFile 6}

PopB4SMTPMerak  OBJECT-TYPE
    SYNTAX      OCTET STRING
    MAX-ACCESS  read-write
    STATUS      current
    DESCRIPTION
"
If set Merak 7.5.2 is supported.
"
    REFERENCE "Pop Before SMTP Merak Style"
    DEFVAL { "" }
    ::= {Relaying 116}

syncStatPopB4SMTPMerak  OBJECT-TYPE
    SYNTAX      OCTET STRING
    MAX-ACCESS  read-only
    STATUS      current
    DESCRIPTION
"
synchronization status for PopB4SMTPMerak
-1 - PopB4SMTPMerak could not be synchronized
 0 - synchronization not configured
 1 - out of sync - running master mode
 2 - in sync - running  mastermode
 3 - in sync - running slave mode
 4 - in sync - running master mode (wait to reach state 2)
"
    ::= {PopB4SMTPMerak 5}

syncStatStrPopB4SMTPMerak  OBJECT-TYPE
    SYNTAX      OCTET STRING
    MAX-ACCESS  read-only
    STATUS      current
    DESCRIPTION
"
synchronization status line from file assp_sync.cfg for PopB4SMTPMerak
 0 - synchronization not configured
 1 - out of sync - running master mode
 2 - in sync - running  mastermode
 3 - in sync - running slave mode
 4 - in sync - running master mode (wait to reach state 2)
"
    ::= {PopB4SMTPMerak 6}

relayHost  OBJECT-TYPE
    SYNTAX      OCTET STRING
    MAX-ACCESS  read-write
    STATUS      current
    DESCRIPTION
"
Your isp's mail relayhost (smarthost). For example: mail.isp.com:25If you run Exchange/Notes and you want assp to update the nonspam database and the whitelist, then enter your isp's smtp relay host here. Blank means no relayhost. Only required if clients don't deliver through SMTP. Separate multiple entries by '|'.
  If you need to connect to the relay host using native SSL, write 'SSL:' in front of the IP/host definition. In this case the Perl module  must be installed and enabled ( useIOSocketSSL ).
  Examples: your_ISP_Server:25, 149.1.1.1:25, SSL:149.1.1.2:465|any_other_host:25 !
"
    REFERENCE "Relay Host"
    DEFVAL { "" }
    ::= {Relaying 117}

syncStatrelayHost  OBJECT-TYPE
    SYNTAX      OCTET STRING
    MAX-ACCESS  read-only
    STATUS      current
    DESCRIPTION
"
synchronization status for relayHost
-1 - relayHost could not be synchronized
 0 - synchronization not configured
 1 - out of sync - running master mode
 2 - in sync - running  mastermode
 3 - in sync - running slave mode
 4 - in sync - running master mode (wait to reach state 2)
"
    ::= {relayHost 5}

syncStatStrrelayHost  OBJECT-TYPE
    SYNTAX      OCTET STRING
    MAX-ACCESS  read-only
    STATUS      current
    DESCRIPTION
"
synchronization status line from file assp_sync.cfg for relayHost
 0 - synchronization not configured
 1 - out of sync - running master mode
 2 - in sync - running  mastermode
 3 - in sync - running slave mode
 4 - in sync - running master mode (wait to reach state 2)
"
    ::= {relayHost 6}

relayPort  OBJECT-TYPE
    SYNTAX      OCTET STRING
    MAX-ACCESS  read-write
    STATUS      current
    DESCRIPTION
"
Tell your mail server to connect to this IP/port as its smarthost / relayhost. For example: 225 Note that you'll want to keep the relayPort protected from external access by your firewall.You can supply an interface:port to limit connections. Separate multiple entries by '|'.Examples: 225, 127.0.0.1:225, 192.168.1.1:225|192.168.2.1:225 !
"
    REFERENCE "Relay Port"
    DEFVAL { "" }
    ::= {Relaying 118}

syncStatrelayPort  OBJECT-TYPE
    SYNTAX      OCTET STRING
    MAX-ACCESS  read-only
    STATUS      current
    DESCRIPTION
"
synchronization status for relayPort
-1 - relayPort could not be synchronized
 0 - synchronization not configured
 1 - out of sync - running master mode
 2 - in sync - running  mastermode
 3 - in sync - running slave mode
 4 - in sync - running master mode (wait to reach state 2)
"
    ::= {relayPort 5}

syncStatStrrelayPort  OBJECT-TYPE
    SYNTAX      OCTET STRING
    MAX-ACCESS  read-only
    STATUS      current
    DESCRIPTION
"
synchronization status line from file assp_sync.cfg for relayPort
 0 - synchronization not configured
 1 - out of sync - running master mode
 2 - in sync - running  mastermode
 3 - in sync - running slave mode
 4 - in sync - running master mode (wait to reach state 2)
"
    ::= {relayPort 6}

NoRelaying  OBJECT-TYPE
    SYNTAX      OCTET STRING
    MAX-ACCESS  read-write
    STATUS      current
    DESCRIPTION
"
SMTP error message to deny relaying.
"
    REFERENCE "No Relaying Error "
    DEFVAL { "530 Relaying not allowed" }
    ::= {Relaying 119}

syncStatNoRelaying  OBJECT-TYPE
    SYNTAX      OCTET STRING
    MAX-ACCESS  read-only
    STATUS      current
    DESCRIPTION
"
synchronization status for NoRelaying
-1 - NoRelaying could not be synchronized
 0 - synchronization not configured
 1 - out of sync - running master mode
 2 - in sync - running  mastermode
 3 - in sync - running slave mode
 4 - in sync - running master mode (wait to reach state 2)
"
    ::= {NoRelaying 5}

syncStatStrNoRelaying  OBJECT-TYPE
    SYNTAX      OCTET STRING
    MAX-ACCESS  read-only
    STATUS      current
    DESCRIPTION
"
synchronization status line from file assp_sync.cfg for NoRelaying
 0 - synchronization not configured
 1 - out of sync - running master mode
 2 - in sync - running  mastermode
 3 - in sync - running slave mode
 4 - in sync - running master mode (wait to reach state 2)
"
    ::= {NoRelaying 6}

defaultLocalHost  OBJECT-TYPE
    SYNTAX      OCTET STRING
    MAX-ACCESS  read-write
    STATUS      current
    DESCRIPTION
"
If you want to be able to send mail to local users without a domain name then put the default local domain here. Blank disables this feature. For example: mydomain.com .
"
    REFERENCE "Default Local Host"
    DEFVAL { "assp.local" }
    ::= {Relaying 120}

genDKIM  OBJECT-TYPE
    SYNTAX      OCTET STRING
    MAX-ACCESS  read-write
    STATUS      current
    DESCRIPTION
"
If selected, ASSP will add DKIM signatures to relayed messages if it finds a valid DKIM configuration in DKIMgenConfig for the sending domain. This will also be done for noprocessing mails. This requires an installed  module in PERL.
"
    REFERENCE "Generate and Add DKIM  signatures to relayed messages"
    DEFVAL { "" }
    ::= {Relaying 121}

syncStatgenDKIM  OBJECT-TYPE
    SYNTAX      OCTET STRING
    MAX-ACCESS  read-only
    STATUS      current
    DESCRIPTION
"
synchronization status for genDKIM
-1 - genDKIM could not be synchronized
 0 - synchronization not configured
 1 - out of sync - running master mode
 2 - in sync - running  mastermode
 3 - in sync - running slave mode
 4 - in sync - running master mode (wait to reach state 2)
"
    ::= {genDKIM 5}

syncStatStrgenDKIM  OBJECT-TYPE
    SYNTAX      OCTET STRING
    MAX-ACCESS  read-only
    STATUS      current
    DESCRIPTION
"
synchronization status line from file assp_sync.cfg for genDKIM
 0 - synchronization not configured
 1 - out of sync - running master mode
 2 - in sync - running  mastermode
 3 - in sync - running slave mode
 4 - in sync - running master mode (wait to reach state 2)
"
    ::= {genDKIM 6}

DKIMgenConfig  OBJECT-TYPE
    SYNTAX      OCTET STRING
    MAX-ACCESS  read-write
    STATUS      current
    DESCRIPTION
"
The file that contains the DKIM configuration. A description how to configure DKIM could be found in the default file dkim/dkimconfig.txt.

"
    REFERENCE "The File with the DKIM configurations*"
    DEFVAL { "file:dkim/dkimconfig.txt" }
    ::= {Relaying 122}

syncStatDKIMgenConfig  OBJECT-TYPE
    SYNTAX      OCTET STRING
    MAX-ACCESS  read-only
    STATUS      current
    DESCRIPTION
"
synchronization status for DKIMgenConfig
-1 - DKIMgenConfig could not be synchronized
 0 - synchronization not configured
 1 - out of sync - running master mode
 2 - in sync - running  mastermode
 3 - in sync - running slave mode
 4 - in sync - running master mode (wait to reach state 2)
"
    ::= {DKIMgenConfig 5}

syncStatStrDKIMgenConfig  OBJECT-TYPE
    SYNTAX      OCTET STRING
    MAX-ACCESS  read-only
    STATUS      current
    DESCRIPTION
"
synchronization status line from file assp_sync.cfg for DKIMgenConfig
 0 - synchronization not configured
 1 - out of sync - running master mode
 2 - in sync - running  mastermode
 3 - in sync - running slave mode
 4 - in sync - running master mode (wait to reach state 2)
"
    ::= {DKIMgenConfig 6}

LocalFrequencyInt  OBJECT-TYPE
    SYNTAX      OCTET STRING
    MAX-ACCESS  read-write
    STATUS      current
    DESCRIPTION
"
The time interval in seconds in which the number of envelope recipients per sending address has not to exceed a specific number ( LocalFrequencyNumRcpt ).
  Use this in combination with LocalFrequencyNumRcpt to limit the number of recipients in a given interval, to prevent local abuse - for example from highjacked local accounts. A value of 0 (default) will disable this feature and clean the cache within five minutes. It is recommended to enable DoLocalSenderAddress and/or DoLocalSenderDomain, if you want to use this feature. To give users the chance to inform an admin about such blocked mails, local mails to EmailAdmins are never blocked because of that feature.
  
"
    REFERENCE "Local Frequency Interval"
    DEFVAL { "0" }
    ::= {Relaying 872}

syncStatLocalFrequencyInt  OBJECT-TYPE
    SYNTAX      OCTET STRING
    MAX-ACCESS  read-only
    STATUS      current
    DESCRIPTION
"
synchronization status for LocalFrequencyInt
-1 - LocalFrequencyInt could not be synchronized
 0 - synchronization not configured
 1 - out of sync - running master mode
 2 - in sync - running  mastermode
 3 - in sync - running slave mode
 4 - in sync - running master mode (wait to reach state 2)
"
    ::= {LocalFrequencyInt 5}

syncStatStrLocalFrequencyInt  OBJECT-TYPE
    SYNTAX      OCTET STRING
    MAX-ACCESS  read-only
    STATUS      current
    DESCRIPTION
"
synchronization status line from file assp_sync.cfg for LocalFrequencyInt
 0 - synchronization not configured
 1 - out of sync - running master mode
 2 - in sync - running  mastermode
 3 - in sync - running slave mode
 4 - in sync - running master mode (wait to reach state 2)
"
    ::= {LocalFrequencyInt 6}

LocalFrequencyNumRcpt  OBJECT-TYPE
    SYNTAX      OCTET STRING
    MAX-ACCESS  read-write
    STATUS      current
    DESCRIPTION
"
The number of envelope recipients per sending address that has not to exceed in a specific time interval ( LocalFrequencyInt ).
  Use this in combination with LocalFrequencyInt to limit the number of recipients in a given interval, to prevent local abuse - for example from highjacked local accounts. A value of 0 (default) will disable this feature and clean the cache within five minutes. It is recommended to enable DoLocalSenderAddress and/or DoLocalSenderDomain, if you want to use this feature. To give users the chance to inform an admin about such blocked mails, local mails to EmailAdmins are never blocked because of that feature. 
  
"
    REFERENCE "Local Frequency Recipient Number"
    DEFVAL { "0" }
    ::= {Relaying 873}

syncStatLocalFrequencyNumRcpt  OBJECT-TYPE
    SYNTAX      OCTET STRING
    MAX-ACCESS  read-only
    STATUS      current
    DESCRIPTION
"
synchronization status for LocalFrequencyNumRcpt
-1 - LocalFrequencyNumRcpt could not be synchronized
 0 - synchronization not configured
 1 - out of sync - running master mode
 2 - in sync - running  mastermode
 3 - in sync - running slave mode
 4 - in sync - running master mode (wait to reach state 2)
"
    ::= {LocalFrequencyNumRcpt 5}

syncStatStrLocalFrequencyNumRcpt  OBJECT-TYPE
    SYNTAX      OCTET STRING
    MAX-ACCESS  read-only
    STATUS      current
    DESCRIPTION
"
synchronization status line from file assp_sync.cfg for LocalFrequencyNumRcpt
 0 - synchronization not configured
 1 - out of sync - running master mode
 2 - in sync - running  mastermode
 3 - in sync - running slave mode
 4 - in sync - running master mode (wait to reach state 2)
"
    ::= {LocalFrequencyNumRcpt 6}

LocalFrequencyOnly  OBJECT-TYPE
    SYNTAX      OCTET STRING
    MAX-ACCESS  read-write
    STATUS      current
    DESCRIPTION
"
A list of local addresses, for which the 'local frequency check' should be done. Leave this field blank (default), to do the check for every address.
  Accepts specific addresses (user@domain.com), user parts (user) or entire domains (@domain.com).  Wildcards are supported (fribo*@domain.com).
  For example: fribo*@thisdomain.com|jhanna|@sillyguys.org 
"
    REFERENCE "Check local Frequency for this Users only*"
    DEFVAL { "" }
    ::= {Relaying 874}

syncStatLocalFrequencyOnly  OBJECT-TYPE
    SYNTAX      OCTET STRING
    MAX-ACCESS  read-only
    STATUS      current
    DESCRIPTION
"
synchronization status for LocalFrequencyOnly
-1 - LocalFrequencyOnly could not be synchronized
 0 - synchronization not configured
 1 - out of sync - running master mode
 2 - in sync - running  mastermode
 3 - in sync - running slave mode
 4 - in sync - running master mode (wait to reach state 2)
"
    ::= {LocalFrequencyOnly 5}

syncStatStrLocalFrequencyOnly  OBJECT-TYPE
    SYNTAX      OCTET STRING
    MAX-ACCESS  read-only
    STATUS      current
    DESCRIPTION
"
synchronization status line from file assp_sync.cfg for LocalFrequencyOnly
 0 - synchronization not configured
 1 - out of sync - running master mode
 2 - in sync - running  mastermode
 3 - in sync - running slave mode
 4 - in sync - running master mode (wait to reach state 2)
"
    ::= {LocalFrequencyOnly 6}

NoLocalFrequency  OBJECT-TYPE
    SYNTAX      OCTET STRING
    MAX-ACCESS  read-write
    STATUS      current
    DESCRIPTION
"
A list of local addresses, for which the 'local frequency check' should not be done. Noprocessing messages will skip this check.
  Accepts specific addresses (user@domain.com), user parts (user) or entire domains (@domain.com).  Wildcards are supported (fribo*@domain.com).
  For example: fribo*@thisdomain.com|jhanna|@sillyguys.org 
"
    REFERENCE "Check local Frequency NOT for this Users*"
    DEFVAL { "" }
    ::= {Relaying 875}

syncStatNoLocalFrequency  OBJECT-TYPE
    SYNTAX      OCTET STRING
    MAX-ACCESS  read-only
    STATUS      current
    DESCRIPTION
"
synchronization status for NoLocalFrequency
-1 - NoLocalFrequency could not be synchronized
 0 - synchronization not configured
 1 - out of sync - running master mode
 2 - in sync - running  mastermode
 3 - in sync - running slave mode
 4 - in sync - running master mode (wait to reach state 2)
"
    ::= {NoLocalFrequency 5}

syncStatStrNoLocalFrequency  OBJECT-TYPE
    SYNTAX      OCTET STRING
    MAX-ACCESS  read-only
    STATUS      current
    DESCRIPTION
"
synchronization status line from file assp_sync.cfg for NoLocalFrequency
 0 - synchronization not configured
 1 - out of sync - running master mode
 2 - in sync - running  mastermode
 3 - in sync - running slave mode
 4 - in sync - running master mode (wait to reach state 2)
"
    ::= {NoLocalFrequency 6}

allowRelayCon  OBJECT-TYPE
    SYNTAX      OCTET STRING
    MAX-ACCESS  read-write
    STATUS      current
    DESCRIPTION
"
Enter any addresses that are allowed to use the relayPort , separated by pipes (|). If empty, any ip address is allowed to connect to the relayPort. If this option is defined, keep in mind : Addresses defined in acceptAllMail are NOT automaticly included and have to be also defined here, if them should allow to use the relayPort. For example: 127.0.0.1|172.16..
 If you use MS Office 365, you should define the  here and you should configure your firewall to redirect connection from the hosted Exchange server to the relayPort .
"
    REFERENCE "Allow Relay Connection from these IP's*"
    DEFVAL { "" }
    ::= {Relaying 883}

syncStatallowRelayCon  OBJECT-TYPE
    SYNTAX      OCTET STRING
    MAX-ACCESS  read-only
    STATUS      current
    DESCRIPTION
"
synchronization status for allowRelayCon
-1 - allowRelayCon could not be synchronized
 0 - synchronization not configured
 1 - out of sync - running master mode
 2 - in sync - running  mastermode
 3 - in sync - running slave mode
 4 - in sync - running master mode (wait to reach state 2)
"
    ::= {allowRelayCon 5}

syncStatStrallowRelayCon  OBJECT-TYPE
    SYNTAX      OCTET STRING
    MAX-ACCESS  read-only
    STATUS      current
    DESCRIPTION
"
synchronization status line from file assp_sync.cfg for allowRelayCon
 0 - synchronization not configured
 1 - out of sync - running master mode
 2 - in sync - running  mastermode
 3 - in sync - running slave mode
 4 - in sync - running master mode (wait to reach state 2)
"
    ::= {allowRelayCon 6}

relayAuthUser  OBJECT-TYPE
    SYNTAX      OCTET STRING
    MAX-ACCESS  read-write
    STATUS      current
    DESCRIPTION
"
The username used for SMTP AUTH authentication to the relayhost  - for example, if your ISP need authentication on the SMTP port! Supported authentication methods are PLAIN, LOGIN, CRAM-MD5 and DIGEST-MD5 . If the relayhost offers multiple methods, the one with highest security option will be used. The Perl module  must be installed to use this feature! The usage of this feature will be skipped, if the sending MTA uses the AUTH command. Leave this blank, if you do not want use this feature.
"
    REFERENCE "User to Authenticate to Relay Host"
    DEFVAL { "" }
    ::= {Relaying 904}

syncStatrelayAuthUser  OBJECT-TYPE
    SYNTAX      OCTET STRING
    MAX-ACCESS  read-only
    STATUS      current
    DESCRIPTION
"
synchronization status for relayAuthUser
-1 - relayAuthUser could not be synchronized
 0 - synchronization not configured
 1 - out of sync - running master mode
 2 - in sync - running  mastermode
 3 - in sync - running slave mode
 4 - in sync - running master mode (wait to reach state 2)
"
    ::= {relayAuthUser 5}

syncStatStrrelayAuthUser  OBJECT-TYPE
    SYNTAX      OCTET STRING
    MAX-ACCESS  read-only
    STATUS      current
    DESCRIPTION
"
synchronization status line from file assp_sync.cfg for relayAuthUser
 0 - synchronization not configured
 1 - out of sync - running master mode
 2 - in sync - running  mastermode
 3 - in sync - running slave mode
 4 - in sync - running master mode (wait to reach state 2)
"
    ::= {relayAuthUser 6}

relayAuthPass  OBJECT-TYPE
    SYNTAX      OCTET STRING
    MAX-ACCESS  read-write
    STATUS      current
    DESCRIPTION
"
The password used for SMTP AUTH authentication to the relayhost ! Leave this blank, if you do not want use this feature.
"
    REFERENCE "Password to Authenticate to Relay Host"
    DEFVAL { "" }
    ::= {Relaying 905}

syncStatrelayAuthPass  OBJECT-TYPE
    SYNTAX      OCTET STRING
    MAX-ACCESS  read-only
    STATUS      current
    DESCRIPTION
"
synchronization status for relayAuthPass
-1 - relayAuthPass could not be synchronized
 0 - synchronization not configured
 1 - out of sync - running master mode
 2 - in sync - running  mastermode
 3 - in sync - running slave mode
 4 - in sync - running master mode (wait to reach state 2)
"
    ::= {relayAuthPass 5}

syncStatStrrelayAuthPass  OBJECT-TYPE
    SYNTAX      OCTET STRING
    MAX-ACCESS  read-only
    STATUS      current
    DESCRIPTION
"
synchronization status line from file assp_sync.cfg for relayAuthPass
 0 - synchronization not configured
 1 - out of sync - running master mode
 2 - in sync - running  mastermode
 3 - in sync - running slave mode
 4 - in sync - running master mode (wait to reach state 2)
"
    ::= {relayAuthPass 6}

NoLocalFrequencyIP  OBJECT-TYPE
    SYNTAX      OCTET STRING
    MAX-ACCESS  read-write
    STATUS      current
    DESCRIPTION
"
A list of local IP-addresses, for which the 'local frequency check' should not be done.
  For example: 145.145.145.145|145.146. 
"
    REFERENCE "Check local Frequency NOT for this IP's*"
    DEFVAL { "" }
    ::= {Relaying 1011}

syncStatNoLocalFrequencyIP  OBJECT-TYPE
    SYNTAX      OCTET STRING
    MAX-ACCESS  read-only
    STATUS      current
    DESCRIPTION
"
synchronization status for NoLocalFrequencyIP
-1 - NoLocalFrequencyIP could not be synchronized
 0 - synchronization not configured
 1 - out of sync - running master mode
 2 - in sync - running  mastermode
 3 - in sync - running slave mode
 4 - in sync - running master mode (wait to reach state 2)
"
    ::= {NoLocalFrequencyIP 5}

syncStatStrNoLocalFrequencyIP  OBJECT-TYPE
    SYNTAX      OCTET STRING
    MAX-ACCESS  read-only
    STATUS      current
    DESCRIPTION
"
synchronization status line from file assp_sync.cfg for NoLocalFrequencyIP
 0 - synchronization not configured
 1 - out of sync - running master mode
 2 - in sync - running  mastermode
 3 - in sync - running slave mode
 4 - in sync - running master mode (wait to reach state 2)
"
    ::= {NoLocalFrequencyIP 6}

RelayOnlyLocalSender  OBJECT-TYPE
    SYNTAX      OCTET STRING
    MAX-ACCESS  read-write
    STATUS      current
    DESCRIPTION
"
If set, the envelope sender (MAIL FROM:) is immediatly checked after the DATA command is received (to be valid). If the sender address could not be validated, the connection is droped.
  The connection will be droped regardless any other assp setting ( except EmailSenderOK ).
  It is recommended to switch this to ON, if you use for example MS Office 365. At least, it is wise, to switch this ( or RelayOnlyLocalDomains ) to ON in every case
"
    REFERENCE "Allow Relaying Only for Local Sender"
    DEFVAL { "" }
    ::= {Relaying 1038}

syncStatRelayOnlyLocalSender  OBJECT-TYPE
    SYNTAX      OCTET STRING
    MAX-ACCESS  read-only
    STATUS      current
    DESCRIPTION
"
synchronization status for RelayOnlyLocalSender
-1 - RelayOnlyLocalSender could not be synchronized
 0 - synchronization not configured
 1 - out of sync - running master mode
 2 - in sync - running  mastermode
 3 - in sync - running slave mode
 4 - in sync - running master mode (wait to reach state 2)
"
    ::= {RelayOnlyLocalSender 5}

syncStatStrRelayOnlyLocalSender  OBJECT-TYPE
    SYNTAX      OCTET STRING
    MAX-ACCESS  read-only
    STATUS      current
    DESCRIPTION
"
synchronization status line from file assp_sync.cfg for RelayOnlyLocalSender
 0 - synchronization not configured
 1 - out of sync - running master mode
 2 - in sync - running  mastermode
 3 - in sync - running slave mode
 4 - in sync - running master mode (wait to reach state 2)
"
    ::= {RelayOnlyLocalSender 6}

RelayOnlyLocalDomains  OBJECT-TYPE
    SYNTAX      OCTET STRING
    MAX-ACCESS  read-write
    STATUS      current
    DESCRIPTION
"
If set, the envelope sender domain (MAIL FROM:) is immediatly checked after the DATA command is received (to be a local domain). If the sender domain could not be validated, the connection is droped.
  The connection will be droped regardless any other assp setting ( except EmailSenderOK ).
  It is recommended to switch this to ON, if you use for example MS Office 365. At least, it is wise, to switch this ( or RelayOnlyLocalSender ) to ON in every case
"
    REFERENCE "Allow Relaying Only for Local Domains"
    DEFVAL { "" }
    ::= {Relaying 1039}

syncStatRelayOnlyLocalDomains  OBJECT-TYPE
    SYNTAX      OCTET STRING
    MAX-ACCESS  read-only
    STATUS      current
    DESCRIPTION
"
synchronization status for RelayOnlyLocalDomains
-1 - RelayOnlyLocalDomains could not be synchronized
 0 - synchronization not configured
 1 - out of sync - running master mode
 2 - in sync - running  mastermode
 3 - in sync - running slave mode
 4 - in sync - running master mode (wait to reach state 2)
"
    ::= {RelayOnlyLocalDomains 5}

syncStatStrRelayOnlyLocalDomains  OBJECT-TYPE
    SYNTAX      OCTET STRING
    MAX-ACCESS  read-only
    STATUS      current
    DESCRIPTION
"
synchronization status line from file assp_sync.cfg for RelayOnlyLocalDomains
 0 - synchronization not configured
 1 - out of sync - running master mode
 2 - in sync - running  mastermode
 3 - in sync - running slave mode
 4 - in sync - running master mode (wait to reach state 2)
"
    ::= {RelayOnlyLocalDomains 6}

RecipientsLocalDomains  OBJECT IDENTIFIER ::= {asspConfig 10}
sendAllPostmaster  OBJECT-TYPE
    SYNTAX      OCTET STRING
    MAX-ACCESS  read-write
    STATUS      current
    DESCRIPTION
"
ASSP will deliver messages addressed to all postmasters of your local domains to this address. For example: postmaster@mydomain.com
"
    REFERENCE "Catchall Address for Messages to Postmaster"
    DEFVAL { "" }
    ::= {RecipientsLocalDomains 125}

syncStatsendAllPostmaster  OBJECT-TYPE
    SYNTAX      OCTET STRING
    MAX-ACCESS  read-only
    STATUS      current
    DESCRIPTION
"
synchronization status for sendAllPostmaster
-1 - sendAllPostmaster could not be synchronized
 0 - synchronization not configured
 1 - out of sync - running master mode
 2 - in sync - running  mastermode
 3 - in sync - running slave mode
 4 - in sync - running master mode (wait to reach state 2)
"
    ::= {sendAllPostmaster 5}

syncStatStrsendAllPostmaster  OBJECT-TYPE
    SYNTAX      OCTET STRING
    MAX-ACCESS  read-only
    STATUS      current
    DESCRIPTION
"
synchronization status line from file assp_sync.cfg for sendAllPostmaster
 0 - synchronization not configured
 1 - out of sync - running master mode
 2 - in sync - running  mastermode
 3 - in sync - running slave mode
 4 - in sync - running master mode (wait to reach state 2)
"
    ::= {sendAllPostmaster 6}

sendAllPostmasterNP  OBJECT-TYPE
    SYNTAX      OCTET STRING
    MAX-ACCESS  read-write
    STATUS      current
    DESCRIPTION
"

"
    REFERENCE "Skip Spam Checks for Postmaster Catchall"
    DEFVAL { "" }
    ::= {RecipientsLocalDomains 126}

syncStatsendAllPostmasterNP  OBJECT-TYPE
    SYNTAX      OCTET STRING
    MAX-ACCESS  read-only
    STATUS      current
    DESCRIPTION
"
synchronization status for sendAllPostmasterNP
-1 - sendAllPostmasterNP could not be synchronized
 0 - synchronization not configured
 1 - out of sync - running master mode
 2 - in sync - running  mastermode
 3 - in sync - running slave mode
 4 - in sync - running master mode (wait to reach state 2)
"
    ::= {sendAllPostmasterNP 5}

syncStatStrsendAllPostmasterNP  OBJECT-TYPE
    SYNTAX      OCTET STRING
    MAX-ACCESS  read-only
    STATUS      current
    DESCRIPTION
"
synchronization status line from file assp_sync.cfg for sendAllPostmasterNP
 0 - synchronization not configured
 1 - out of sync - running master mode
 2 - in sync - running  mastermode
 3 - in sync - running slave mode
 4 - in sync - running master mode (wait to reach state 2)
"
    ::= {sendAllPostmasterNP 6}

sendAllAbuse  OBJECT-TYPE
    SYNTAX      OCTET STRING
    MAX-ACCESS  read-write
    STATUS      current
    DESCRIPTION
"
ASSP will deliver messages to all abuse addresses of your local domains to this address. For example: abuse@mydomain.com
"
    REFERENCE "Catchall Address for Messages to Abuse"
    DEFVAL { "" }
    ::= {RecipientsLocalDomains 127}

syncStatsendAllAbuse  OBJECT-TYPE
    SYNTAX      OCTET STRING
    MAX-ACCESS  read-only
    STATUS      current
    DESCRIPTION
"
synchronization status for sendAllAbuse
-1 - sendAllAbuse could not be synchronized
 0 - synchronization not configured
 1 - out of sync - running master mode
 2 - in sync - running  mastermode
 3 - in sync - running slave mode
 4 - in sync - running master mode (wait to reach state 2)
"
    ::= {sendAllAbuse 5}

syncStatStrsendAllAbuse  OBJECT-TYPE
    SYNTAX      OCTET STRING
    MAX-ACCESS  read-only
    STATUS      current
    DESCRIPTION
"
synchronization status line from file assp_sync.cfg for sendAllAbuse
 0 - synchronization not configured
 1 - out of sync - running master mode
 2 - in sync - running  mastermode
 3 - in sync - running slave mode
 4 - in sync - running master mode (wait to reach state 2)
"
    ::= {sendAllAbuse 6}

sendAllAbuseNP  OBJECT-TYPE
    SYNTAX      OCTET STRING
    MAX-ACCESS  read-write
    STATUS      current
    DESCRIPTION
"

"
    REFERENCE "Skip Spam Checks for Abuse Catchall"
    DEFVAL { "" }
    ::= {RecipientsLocalDomains 128}

syncStatsendAllAbuseNP  OBJECT-TYPE
    SYNTAX      OCTET STRING
    MAX-ACCESS  read-only
    STATUS      current
    DESCRIPTION
"
synchronization status for sendAllAbuseNP
-1 - sendAllAbuseNP could not be synchronized
 0 - synchronization not configured
 1 - out of sync - running master mode
 2 - in sync - running  mastermode
 3 - in sync - running slave mode
 4 - in sync - running master mode (wait to reach state 2)
"
    ::= {sendAllAbuseNP 5}

syncStatStrsendAllAbuseNP  OBJECT-TYPE
    SYNTAX      OCTET STRING
    MAX-ACCESS  read-only
    STATUS      current
    DESCRIPTION
"
synchronization status line from file assp_sync.cfg for sendAllAbuseNP
 0 - synchronization not configured
 1 - out of sync - running master mode
 2 - in sync - running  mastermode
 3 - in sync - running slave mode
 4 - in sync - running master mode (wait to reach state 2)
"
    ::= {sendAllAbuseNP 6}

DoRFC822  OBJECT-TYPE
    SYNTAX      OCTET STRING
    MAX-ACCESS  read-write
    STATUS      current
    DESCRIPTION
"
If activated, the envelope sender and/or each envelope recipient is checked to conform with the email format defined in RFC 822. For an invalid sender address 'nofromValencePB' is used for scoring - for invalid recipient addresses, each is scored with irValencePB .
  For the sender address in addition a top level domain existence and DNS name server registration check is done.
  The default setting is 'sender' - recommended settings are 'sender' or 'both'!
"
    REFERENCE "Validate addresses to conform with RFC 822"
    DEFVAL { "2" }
    ::= {RecipientsLocalDomains 129}

syncStatDoRFC822  OBJECT-TYPE
    SYNTAX      OCTET STRING
    MAX-ACCESS  read-only
    STATUS      current
    DESCRIPTION
"
synchronization status for DoRFC822
-1 - DoRFC822 could not be synchronized
 0 - synchronization not configured
 1 - out of sync - running master mode
 2 - in sync - running  mastermode
 3 - in sync - running slave mode
 4 - in sync - running master mode (wait to reach state 2)
"
    ::= {DoRFC822 5}

syncStatStrDoRFC822  OBJECT-TYPE
    SYNTAX      OCTET STRING
    MAX-ACCESS  read-only
    STATUS      current
    DESCRIPTION
"
synchronization status line from file assp_sync.cfg for DoRFC822
 0 - synchronization not configured
 1 - out of sync - running master mode
 2 - in sync - running  mastermode
 3 - in sync - running slave mode
 4 - in sync - running master mode (wait to reach state 2)
"
    ::= {DoRFC822 6}

LocalAddressesFlat  OBJECT-TYPE
    SYNTAX      OCTET STRING
    MAX-ACCESS  read-write
    STATUS      current
    DESCRIPTION
"
These email addresses are the list of your local addresses. You can list specific addresses (user@mydomain.com), addresses at any local domain (user), or entire domains (@mydomain.com).  Wildcards are supported (fribo*@domain.com). (|).For example: fribo@thisdomain.com|jhanna|@sillyguys.org or place them in a plain ASCII file one address per line:file:files/localuser.txt. You can use entries like @mydomain.com=>vrfyhost:port to VRFY users on your MTA, for more information read localDomains. You can use an entry like ALL=>vrfyhost:port to define a VRFY host for all domain entries ( better use Groups ).
"
    REFERENCE "Lookup valid Local Addresses from here*"
    DEFVAL { "" }
    ::= {RecipientsLocalDomains 130}

syncStatLocalAddressesFlat  OBJECT-TYPE
    SYNTAX      OCTET STRING
    MAX-ACCESS  read-only
    STATUS      current
    DESCRIPTION
"
synchronization status for LocalAddressesFlat
-1 - LocalAddressesFlat could not be synchronized
 0 - synchronization not configured
 1 - out of sync - running master mode
 2 - in sync - running  mastermode
 3 - in sync - running slave mode
 4 - in sync - running master mode (wait to reach state 2)
"
    ::= {LocalAddressesFlat 5}

syncStatStrLocalAddressesFlat  OBJECT-TYPE
    SYNTAX      OCTET STRING
    MAX-ACCESS  read-only
    STATUS      current
    DESCRIPTION
"
synchronization status line from file assp_sync.cfg for LocalAddressesFlat
 0 - synchronization not configured
 1 - out of sync - running master mode
 2 - in sync - running  mastermode
 3 - in sync - running slave mode
 4 - in sync - running master mode (wait to reach state 2)
"
    ::= {LocalAddressesFlat 6}

LocalAddressesFlatDomains  OBJECT-TYPE
    SYNTAX      OCTET STRING
    MAX-ACCESS  read-write
    STATUS      current
    DESCRIPTION
"
Will handle entries without '@' as full domains
"
    REFERENCE "Use Addresses without '@' as Domains"
    DEFVAL { "0" }
    ::= {RecipientsLocalDomains 131}

syncStatLocalAddressesFlatDomains  OBJECT-TYPE
    SYNTAX      OCTET STRING
    MAX-ACCESS  read-only
    STATUS      current
    DESCRIPTION
"
synchronization status for LocalAddressesFlatDomains
-1 - LocalAddressesFlatDomains could not be synchronized
 0 - synchronization not configured
 1 - out of sync - running master mode
 2 - in sync - running  mastermode
 3 - in sync - running slave mode
 4 - in sync - running master mode (wait to reach state 2)
"
    ::= {LocalAddressesFlatDomains 5}

syncStatStrLocalAddressesFlatDomains  OBJECT-TYPE
    SYNTAX      OCTET STRING
    MAX-ACCESS  read-only
    STATUS      current
    DESCRIPTION
"
synchronization status line from file assp_sync.cfg for LocalAddressesFlatDomains
 0 - synchronization not configured
 1 - out of sync - running master mode
 2 - in sync - running  mastermode
 3 - in sync - running slave mode
 4 - in sync - running master mode (wait to reach state 2)
"
    ::= {LocalAddressesFlatDomains 6}

RejectTheseLocalAddresses  OBJECT-TYPE
    SYNTAX      OCTET STRING
    MAX-ACCESS  read-write
    STATUS      current
    DESCRIPTION
"
If ANY recipient is on reject list, message will not be delivered. Used for disabled legitimate accounts, where a user may have left the company. This stops wildcard mailboxes from getting these messages.
"
    REFERENCE "Reject These Local Addresses*"
    DEFVAL { "" }
    ::= {RecipientsLocalDomains 132}

syncStatRejectTheseLocalAddresses  OBJECT-TYPE
    SYNTAX      OCTET STRING
    MAX-ACCESS  read-only
    STATUS      current
    DESCRIPTION
"
synchronization status for RejectTheseLocalAddresses
-1 - RejectTheseLocalAddresses could not be synchronized
 0 - synchronization not configured
 1 - out of sync - running master mode
 2 - in sync - running  mastermode
 3 - in sync - running slave mode
 4 - in sync - running master mode (wait to reach state 2)
"
    ::= {RejectTheseLocalAddresses 5}

syncStatStrRejectTheseLocalAddresses  OBJECT-TYPE
    SYNTAX      OCTET STRING
    MAX-ACCESS  read-only
    STATUS      current
    DESCRIPTION
"
synchronization status line from file assp_sync.cfg for RejectTheseLocalAddresses
 0 - synchronization not configured
 1 - out of sync - running master mode
 2 - in sync - running  mastermode
 3 - in sync - running slave mode
 4 - in sync - running master mode (wait to reach state 2)
"
    ::= {RejectTheseLocalAddresses 6}

localDomains  OBJECT-TYPE
    SYNTAX      OCTET STRING
    MAX-ACCESS  read-write
    STATUS      current
    DESCRIPTION
"
Check local domains against these addresses. Add a fake domain like 'assp-nospam.org' for the email interface if you run MS Exchange. When mailing to eg. 'spam@assp-nospam.org' MS Exchange forwards it outbound to ASSP who handles the different options. As in every field marked by '*' separate addresses with | or use file 'file:files/localdomains.txt'. Wildcards are supported. For example: *mydomain.com|*.mydomain.com|here.org 
 Use the syntax: *mydomain.com=>smtp.mydomain.com|other.com=>mx.other.com:port|other2.com=>mx.other.com:port,mx2.other.com:port to verify the recipient addresses with the SMTP-VRFY (if VRFY is not supported 'MAIL FROM:' and 'RCPT TO:' will be used) command on other SMTP servers. The entry behind => must be the hostname:port or ip-address:port of the MTA which is used to verify 'RCPT TO' addresses with a VRFY command! If :port is not defined, port :25 will be used. You can use an entry like ALL=>vrfyhost:port to define a VRFY host for all local domain entries that don't have a MTA defined ( better use Groups ). Separate multiple VRFY hosts for failover by comma ','. You have to enable the SMTP 'VRFY' command on your MTA - the 'EXPN' command should be enabled! This requires an installed  module in PERL. 
 If you have configured LDAP and enabled DoLDAP and ASSP finds a VRFY entry for a domain, LDAP search will be done first and if this fails, the VRFY will be used. So VRFY could be used for LDAP backup/fallback/failover!
 It is recommended to configure 'ldaplistdb' in the 'File Paths and Database' section when using this verify extension - so ASSP will store all verified recipients addresses there to minimize the querys on MTA's. There is no need to configure LDAP, but both VRFY and LDAP are using ldaplistdb. Please go to the 'LDAP setup' section to configure MaxLDAPlistDays and LDAPcrossCheckInterval or start a crosscheck now with forceLDAPcrossCheck. This three parameters belong also to VRFY.
"
    REFERENCE "Local Domains*"
    DEFVAL { "putYourDomains.com|here.org" }
    ::= {RecipientsLocalDomains 133}

syncStatlocalDomains  OBJECT-TYPE
    SYNTAX      OCTET STRING
    MAX-ACCESS  read-only
    STATUS      current
    DESCRIPTION
"
synchronization status for localDomains
-1 - localDomains could not be synchronized
 0 - synchronization not configured
 1 - out of sync - running master mode
 2 - in sync - running  mastermode
 3 - in sync - running slave mode
 4 - in sync - running master mode (wait to reach state 2)
"
    ::= {localDomains 5}

syncStatStrlocalDomains  OBJECT-TYPE
    SYNTAX      OCTET STRING
    MAX-ACCESS  read-only
    STATUS      current
    DESCRIPTION
"
synchronization status line from file assp_sync.cfg for localDomains
 0 - synchronization not configured
 1 - out of sync - running master mode
 2 - in sync - running  mastermode
 3 - in sync - running slave mode
 4 - in sync - running master mode (wait to reach state 2)
"
    ::= {localDomains 6}

VRFYQueryTimeOut  OBJECT-TYPE
    SYNTAX      OCTET STRING
    MAX-ACCESS  read-write
    STATUS      current
    DESCRIPTION
"
The number of seconds ASSP will wait for an answer of the MTA that is queryed with the VRFY command to verify a recipient address.
"
    REFERENCE "SMTP VRFY-Query Timeout"
    DEFVAL { "5" }
    ::= {RecipientsLocalDomains 134}

syncStatVRFYQueryTimeOut  OBJECT-TYPE
    SYNTAX      OCTET STRING
    MAX-ACCESS  read-only
    STATUS      current
    DESCRIPTION
"
synchronization status for VRFYQueryTimeOut
-1 - VRFYQueryTimeOut could not be synchronized
 0 - synchronization not configured
 1 - out of sync - running master mode
 2 - in sync - running  mastermode
 3 - in sync - running slave mode
 4 - in sync - running master mode (wait to reach state 2)
"
    ::= {VRFYQueryTimeOut 5}

syncStatStrVRFYQueryTimeOut  OBJECT-TYPE
    SYNTAX      OCTET STRING
    MAX-ACCESS  read-only
    STATUS      current
    DESCRIPTION
"
synchronization status line from file assp_sync.cfg for VRFYQueryTimeOut
 0 - synchronization not configured
 1 - out of sync - running master mode
 2 - in sync - running  mastermode
 3 - in sync - running slave mode
 4 - in sync - running master mode (wait to reach state 2)
"
    ::= {VRFYQueryTimeOut 6}

VRFYforceRCPTTO  OBJECT-TYPE
    SYNTAX      OCTET STRING
    MAX-ACCESS  read-write
    STATUS      current
    DESCRIPTION
"
Define MTA's here for which you want ASSP to force the usage of MAIL FROM:,RCPT TO: instead of the VRFY command. The definition of each MTA has to be the same as defined in LocalAddresses_Flat and/or localDomains (after the '=>') for example: smtp.mydomain.com|mx.other.com:port|10.1.1.1|10.1.1.2:125 .
"
    REFERENCE "Force the usage of RCPT TO*"
    DEFVAL { "" }
    ::= {RecipientsLocalDomains 135}

syncStatVRFYforceRCPTTO  OBJECT-TYPE
    SYNTAX      OCTET STRING
    MAX-ACCESS  read-only
    STATUS      current
    DESCRIPTION
"
synchronization status for VRFYforceRCPTTO
-1 - VRFYforceRCPTTO could not be synchronized
 0 - synchronization not configured
 1 - out of sync - running master mode
 2 - in sync - running  mastermode
 3 - in sync - running slave mode
 4 - in sync - running master mode (wait to reach state 2)
"
    ::= {VRFYforceRCPTTO 5}

syncStatStrVRFYforceRCPTTO  OBJECT-TYPE
    SYNTAX      OCTET STRING
    MAX-ACCESS  read-only
    STATUS      current
    DESCRIPTION
"
synchronization status line from file assp_sync.cfg for VRFYforceRCPTTO
 0 - synchronization not configured
 1 - out of sync - running master mode
 2 - in sync - running  mastermode
 3 - in sync - running slave mode
 4 - in sync - running master mode (wait to reach state 2)
"
    ::= {VRFYforceRCPTTO 6}

DoLDAP  OBJECT-TYPE
    SYNTAX      OCTET STRING
    MAX-ACCESS  read-write
    STATUS      current
    DESCRIPTION
"
Check local addresses against an LDAP database before accepting the message.Note: Checking this requires filling in the other LDAP parameters below.This requires an installed  module in PERL.
"
    REFERENCE "Do LDAP lookup for valid local addresses"
    DEFVAL { "" }
    ::= {RecipientsLocalDomains 136}

syncStatDoLDAP  OBJECT-TYPE
    SYNTAX      OCTET STRING
    MAX-ACCESS  read-only
    STATUS      current
    DESCRIPTION
"
synchronization status for DoLDAP
-1 - DoLDAP could not be synchronized
 0 - synchronization not configured
 1 - out of sync - running master mode
 2 - in sync - running  mastermode
 3 - in sync - running slave mode
 4 - in sync - running master mode (wait to reach state 2)
"
    ::= {DoLDAP 5}

syncStatStrDoLDAP  OBJECT-TYPE
    SYNTAX      OCTET STRING
    MAX-ACCESS  read-only
    STATUS      current
    DESCRIPTION
"
synchronization status line from file assp_sync.cfg for DoLDAP
 0 - synchronization not configured
 1 - out of sync - running master mode
 2 - in sync - running  mastermode
 3 - in sync - running slave mode
 4 - in sync - running master mode (wait to reach state 2)
"
    ::= {DoLDAP 6}

LocalAddressesNP  OBJECT-TYPE
    SYNTAX      OCTET STRING
    MAX-ACCESS  read-write
    STATUS      current
    DESCRIPTION
"
If a recipient is found in NoProcessing, the user validation is skipped. 
"
    REFERENCE "Do Not  Validate Local Addresses if in NoProcessing List"
    DEFVAL { "" }
    ::= {RecipientsLocalDomains 137}

syncStatLocalAddressesNP  OBJECT-TYPE
    SYNTAX      OCTET STRING
    MAX-ACCESS  read-only
    STATUS      current
    DESCRIPTION
"
synchronization status for LocalAddressesNP
-1 - LocalAddressesNP could not be synchronized
 0 - synchronization not configured
 1 - out of sync - running master mode
 2 - in sync - running  mastermode
 3 - in sync - running slave mode
 4 - in sync - running master mode (wait to reach state 2)
"
    ::= {LocalAddressesNP 5}

syncStatStrLocalAddressesNP  OBJECT-TYPE
    SYNTAX      OCTET STRING
    MAX-ACCESS  read-only
    STATUS      current
    DESCRIPTION
"
synchronization status line from file assp_sync.cfg for LocalAddressesNP
 0 - synchronization not configured
 1 - out of sync - running master mode
 2 - in sync - running  mastermode
 3 - in sync - running slave mode
 4 - in sync - running master mode (wait to reach state 2)
"
    ::= {LocalAddressesNP 6}

CatchAll  OBJECT-TYPE
    SYNTAX      OCTET STRING
    MAX-ACCESS  read-write
    STATUS      current
    DESCRIPTION
"
ASSP will send to this addresses/domain if no valid user is found in LocalAddresses_Flat/LDAP. For example: catchall@domain1.com|catchall@domain2.com
"
    REFERENCE "Catchall per Domain*"
    DEFVAL { "" }
    ::= {RecipientsLocalDomains 139}

syncStatCatchAll  OBJECT-TYPE
    SYNTAX      OCTET STRING
    MAX-ACCESS  read-only
    STATUS      current
    DESCRIPTION
"
synchronization status for CatchAll
-1 - CatchAll could not be synchronized
 0 - synchronization not configured
 1 - out of sync - running master mode
 2 - in sync - running  mastermode
 3 - in sync - running slave mode
 4 - in sync - running master mode (wait to reach state 2)
"
    ::= {CatchAll 5}

syncStatStrCatchAll  OBJECT-TYPE
    SYNTAX      OCTET STRING
    MAX-ACCESS  read-only
    STATUS      current
    DESCRIPTION
"
synchronization status line from file assp_sync.cfg for CatchAll
 0 - synchronization not configured
 1 - out of sync - running master mode
 2 - in sync - running  mastermode
 3 - in sync - running slave mode
 4 - in sync - running master mode (wait to reach state 2)
"
    ::= {CatchAll 6}

CatchAllAll  OBJECT-TYPE
    SYNTAX      OCTET STRING
    MAX-ACCESS  read-write
    STATUS      current
    DESCRIPTION
"
ASSP will send to this address if no valid user is found  in LocalAddresses_Flat/LDAP and no match is found in Catchall per Domain. For example: catchall@domain.com
"
    REFERENCE "Catchall for All Domains"
    DEFVAL { "" }
    ::= {RecipientsLocalDomains 140}

syncStatCatchAllAll  OBJECT-TYPE
    SYNTAX      OCTET STRING
    MAX-ACCESS  read-only
    STATUS      current
    DESCRIPTION
"
synchronization status for CatchAllAll
-1 - CatchAllAll could not be synchronized
 0 - synchronization not configured
 1 - out of sync - running master mode
 2 - in sync - running  mastermode
 3 - in sync - running slave mode
 4 - in sync - running master mode (wait to reach state 2)
"
    ::= {CatchAllAll 5}

syncStatStrCatchAllAll  OBJECT-TYPE
    SYNTAX      OCTET STRING
    MAX-ACCESS  read-only
    STATUS      current
    DESCRIPTION
"
synchronization status line from file assp_sync.cfg for CatchAllAll
 0 - synchronization not configured
 1 - out of sync - running master mode
 2 - in sync - running  mastermode
 3 - in sync - running slave mode
 4 - in sync - running master mode (wait to reach state 2)
"
    ::= {CatchAllAll 6}

CatchallallISP2NULL  OBJECT-TYPE
    SYNTAX      OCTET STRING
    MAX-ACCESS  read-write
    STATUS      current
    DESCRIPTION
"
If set, ASSP will move all ISP connections with wrong recipient addresses to a NULL-connection. The ISP will receive '250 OK' until the mail has passed, but the mail will not be sent to your MTA. This is done after CatchAll but before CatchAllAll is checked.
"
    REFERENCE "Move ISP Connection with wrong Recipient Address to NULL"
    DEFVAL { "" }
    ::= {RecipientsLocalDomains 141}

syncStatCatchallallISP2NULL  OBJECT-TYPE
    SYNTAX      OCTET STRING
    MAX-ACCESS  read-only
    STATUS      current
    DESCRIPTION
"
synchronization status for CatchallallISP2NULL
-1 - CatchallallISP2NULL could not be synchronized
 0 - synchronization not configured
 1 - out of sync - running master mode
 2 - in sync - running  mastermode
 3 - in sync - running slave mode
 4 - in sync - running master mode (wait to reach state 2)
"
    ::= {CatchallallISP2NULL 5}

syncStatStrCatchallallISP2NULL  OBJECT-TYPE
    SYNTAX      OCTET STRING
    MAX-ACCESS  read-only
    STATUS      current
    DESCRIPTION
"
synchronization status line from file assp_sync.cfg for CatchallallISP2NULL
 0 - synchronization not configured
 1 - out of sync - running master mode
 2 - in sync - running  mastermode
 3 - in sync - running slave mode
 4 - in sync - running master mode (wait to reach state 2)
"
    ::= {CatchallallISP2NULL 6}

NullAddresses  OBJECT-TYPE
    SYNTAX      OCTET STRING
    MAX-ACCESS  read-write
    STATUS      current
    DESCRIPTION
"
ASSP will dump a message silently when encountering such an address in 'MAIL FROM:' or 'RCPT TO:'. Accepts specific addresses (null@example.com), user parts (nobody) or entire domains (@example.com).
"
    REFERENCE "NULL Connection Addresses*"
    DEFVAL { "" }
    ::= {RecipientsLocalDomains 142}

syncStatNullAddresses  OBJECT-TYPE
    SYNTAX      OCTET STRING
    MAX-ACCESS  read-only
    STATUS      current
    DESCRIPTION
"
synchronization status for NullAddresses
-1 - NullAddresses could not be synchronized
 0 - synchronization not configured
 1 - out of sync - running master mode
 2 - in sync - running  mastermode
 3 - in sync - running slave mode
 4 - in sync - running master mode (wait to reach state 2)
"
    ::= {NullAddresses 5}

syncStatStrNullAddresses  OBJECT-TYPE
    SYNTAX      OCTET STRING
    MAX-ACCESS  read-only
    STATUS      current
    DESCRIPTION
"
synchronization status line from file assp_sync.cfg for NullAddresses
 0 - synchronization not configured
 1 - out of sync - running master mode
 2 - in sync - running  mastermode
 3 - in sync - running slave mode
 4 - in sync - running master mode (wait to reach state 2)
"
    ::= {NullAddresses 6}

InternalAddresses  OBJECT-TYPE
    SYNTAX      OCTET STRING
    MAX-ACCESS  read-write
    STATUS      current
    DESCRIPTION
"
These local addresses accept mail only from local domains. Accepts specific addresses (user@domain.com), user parts (user) or entire domains (@domain.com). Wildcards are supported (fribo*@domain.com).
"
    REFERENCE "Accept Mail from Local Domains only*"
    DEFVAL { "" }
    ::= {RecipientsLocalDomains 143}

syncStatInternalAddresses  OBJECT-TYPE
    SYNTAX      OCTET STRING
    MAX-ACCESS  read-only
    STATUS      current
    DESCRIPTION
"
synchronization status for InternalAddresses
-1 - InternalAddresses could not be synchronized
 0 - synchronization not configured
 1 - out of sync - running master mode
 2 - in sync - running  mastermode
 3 - in sync - running slave mode
 4 - in sync - running master mode (wait to reach state 2)
"
    ::= {InternalAddresses 5}

syncStatStrInternalAddresses  OBJECT-TYPE
    SYNTAX      OCTET STRING
    MAX-ACCESS  read-only
    STATUS      current
    DESCRIPTION
"
synchronization status line from file assp_sync.cfg for InternalAddresses
 0 - synchronization not configured
 1 - out of sync - running master mode
 2 - in sync - running  mastermode
 3 - in sync - running slave mode
 4 - in sync - running master mode (wait to reach state 2)
"
    ::= {InternalAddresses 6}

SepChar  OBJECT-TYPE
    SYNTAX      OCTET STRING
    MAX-ACCESS  read-write
    STATUS      current
    DESCRIPTION
"
RFC 3598 describes subaddressing with a Separation Character. A star ('*') is not allowed as Separation Character. Everything between Separation Character and @ is ignored (including Separation Character). For Example = '+' will allow user+subaddress@domain.com.
"
    REFERENCE "Separation Character for Subaddressing"
    DEFVAL { "+" }
    ::= {RecipientsLocalDomains 144}

syncStatSepChar  OBJECT-TYPE
    SYNTAX      OCTET STRING
    MAX-ACCESS  read-only
    STATUS      current
    DESCRIPTION
"
synchronization status for SepChar
-1 - SepChar could not be synchronized
 0 - synchronization not configured
 1 - out of sync - running master mode
 2 - in sync - running  mastermode
 3 - in sync - running slave mode
 4 - in sync - running master mode (wait to reach state 2)
"
    ::= {SepChar 5}

syncStatStrSepChar  OBJECT-TYPE
    SYNTAX      OCTET STRING
    MAX-ACCESS  read-only
    STATUS      current
    DESCRIPTION
"
synchronization status line from file assp_sync.cfg for SepChar
 0 - synchronization not configured
 1 - out of sync - running master mode
 2 - in sync - running  mastermode
 3 - in sync - running slave mode
 4 - in sync - running master mode (wait to reach state 2)
"
    ::= {SepChar 6}

EnableBangPath  OBJECT-TYPE
    SYNTAX      OCTET STRING
    MAX-ACCESS  read-write
    STATUS      current
    DESCRIPTION
"
If set, ASSP will support addresses like domainx!user and will convert them to user@domainx .
"
    REFERENCE "Support Bang Path"
    DEFVAL { "" }
    ::= {RecipientsLocalDomains 145}

syncStatEnableBangPath  OBJECT-TYPE
    SYNTAX      OCTET STRING
    MAX-ACCESS  read-only
    STATUS      current
    DESCRIPTION
"
synchronization status for EnableBangPath
-1 - EnableBangPath could not be synchronized
 0 - synchronization not configured
 1 - out of sync - running master mode
 2 - in sync - running  mastermode
 3 - in sync - running slave mode
 4 - in sync - running master mode (wait to reach state 2)
"
    ::= {EnableBangPath 5}

syncStatStrEnableBangPath  OBJECT-TYPE
    SYNTAX      OCTET STRING
    MAX-ACCESS  read-only
    STATUS      current
    DESCRIPTION
"
synchronization status line from file assp_sync.cfg for EnableBangPath
 0 - synchronization not configured
 1 - out of sync - running master mode
 2 - in sync - running  mastermode
 3 - in sync - running slave mode
 4 - in sync - running master mode (wait to reach state 2)
"
    ::= {EnableBangPath 6}

MaxVRFYErrors  OBJECT-TYPE
    SYNTAX      OCTET STRING
    MAX-ACCESS  read-write
    STATUS      current
    DESCRIPTION
"
The maximum number of failed 'RCPT TO' or 'VRFY' commands encountered before the connection is dropped. You can leave this field at 0, if you are using 'DoLDAP', 'LocalAddresses_Flat'! If configured, ASSP will drop the connection, if the count of '550 unknown user' errors, received from your 'smtpDestination'(MTA), reached this value!
"
    REFERENCE "Maximum recipient verification Errors"
    DEFVAL { "0" }
    ::= {RecipientsLocalDomains 146}

syncStatMaxVRFYErrors  OBJECT-TYPE
    SYNTAX      OCTET STRING
    MAX-ACCESS  read-only
    STATUS      current
    DESCRIPTION
"
synchronization status for MaxVRFYErrors
-1 - MaxVRFYErrors could not be synchronized
 0 - synchronization not configured
 1 - out of sync - running master mode
 2 - in sync - running  mastermode
 3 - in sync - running slave mode
 4 - in sync - running master mode (wait to reach state 2)
"
    ::= {MaxVRFYErrors 5}

syncStatStrMaxVRFYErrors  OBJECT-TYPE
    SYNTAX      OCTET STRING
    MAX-ACCESS  read-only
    STATUS      current
    DESCRIPTION
"
synchronization status line from file assp_sync.cfg for MaxVRFYErrors
 0 - synchronization not configured
 1 - out of sync - running master mode
 2 - in sync - running  mastermode
 3 - in sync - running slave mode
 4 - in sync - running master mode (wait to reach state 2)
"
    ::= {MaxVRFYErrors 6}

ReplaceRecpt  OBJECT-TYPE
    SYNTAX      OCTET STRING
    MAX-ACCESS  read-write
    STATUS      current
    DESCRIPTION
"
recommented if used: file:files/rcptreplrules.txt - default empty ! This enables recipient replacement. If you do not use file:, separate the rules with |. The replacement will be done before any ASSP check. Use this option carefully - for example: if you have enabled DKIM check, the DKIM check will fail, if the recipient of the mail was modified. For a more detailed description of the rules and options, read the file: files/rcptreplrules.txt!
"
    REFERENCE "Enable recipient replacement*"
    DEFVAL { "" }
    ::= {RecipientsLocalDomains 147}

syncStatReplaceRecpt  OBJECT-TYPE
    SYNTAX      OCTET STRING
    MAX-ACCESS  read-only
    STATUS      current
    DESCRIPTION
"
synchronization status for ReplaceRecpt
-1 - ReplaceRecpt could not be synchronized
 0 - synchronization not configured
 1 - out of sync - running master mode
 2 - in sync - running  mastermode
 3 - in sync - running slave mode
 4 - in sync - running master mode (wait to reach state 2)
"
    ::= {ReplaceRecpt 5}

syncStatStrReplaceRecpt  OBJECT-TYPE
    SYNTAX      OCTET STRING
    MAX-ACCESS  read-only
    STATUS      current
    DESCRIPTION
"
synchronization status line from file assp_sync.cfg for ReplaceRecpt
 0 - synchronization not configured
 1 - out of sync - running master mode
 2 - in sync - running  mastermode
 3 - in sync - running slave mode
 4 - in sync - running master mode (wait to reach state 2)
"
    ::= {ReplaceRecpt 6}

NoValidRecipient  OBJECT-TYPE
    SYNTAX      OCTET STRING
    MAX-ACCESS  read-write
    STATUS      current
    DESCRIPTION
"
SMTP reply for invalid Users. Default: '550 5.1.1 User unknown: EMAILADDRESS'  The literal EMAILADDRESS (case sensitive) is replaced by the fully qualified SMTP recipient (e.g., thisuser@yourcompany.com).
"
    REFERENCE "No-Valid-Local-User Reply"
    DEFVAL { "550 5.1.1 User unknown: EMAILADDRESS" }
    ::= {RecipientsLocalDomains 148}

syncStatNoValidRecipient  OBJECT-TYPE
    SYNTAX      OCTET STRING
    MAX-ACCESS  read-only
    STATUS      current
    DESCRIPTION
"
synchronization status for NoValidRecipient
-1 - NoValidRecipient could not be synchronized
 0 - synchronization not configured
 1 - out of sync - running master mode
 2 - in sync - running  mastermode
 3 - in sync - running slave mode
 4 - in sync - running master mode (wait to reach state 2)
"
    ::= {NoValidRecipient 5}

syncStatStrNoValidRecipient  OBJECT-TYPE
    SYNTAX      OCTET STRING
    MAX-ACCESS  read-only
    STATUS      current
    DESCRIPTION
"
synchronization status line from file assp_sync.cfg for NoValidRecipient
 0 - synchronization not configured
 1 - out of sync - running master mode
 2 - in sync - running  mastermode
 3 - in sync - running slave mode
 4 - in sync - running master mode (wait to reach state 2)
"
    ::= {NoValidRecipient 6}

DisableVRFY  OBJECT-TYPE
    SYNTAX      OCTET STRING
    MAX-ACCESS  read-write
    STATUS      current
    DESCRIPTION
"
If you have enabled VRFY and/or EXPN on your MTA to make assp able to verify addresses and you do not want external clients to use VRFY and EXPN - select this option.
"
    REFERENCE "Disable VRFY and EXPN for External Clients"
    DEFVAL { "" }
    ::= {RecipientsLocalDomains 860}

syncStatDisableVRFY  OBJECT-TYPE
    SYNTAX      OCTET STRING
    MAX-ACCESS  read-only
    STATUS      current
    DESCRIPTION
"
synchronization status for DisableVRFY
-1 - DisableVRFY could not be synchronized
 0 - synchronization not configured
 1 - out of sync - running master mode
 2 - in sync - running  mastermode
 3 - in sync - running slave mode
 4 - in sync - running master mode (wait to reach state 2)
"
    ::= {DisableVRFY 5}

syncStatStrDisableVRFY  OBJECT-TYPE
    SYNTAX      OCTET STRING
    MAX-ACCESS  read-only
    STATUS      current
    DESCRIPTION
"
synchronization status line from file assp_sync.cfg for DisableVRFY
 0 - synchronization not configured
 1 - out of sync - running master mode
 2 - in sync - running  mastermode
 3 - in sync - running slave mode
 4 - in sync - running master mode (wait to reach state 2)
"
    ::= {DisableVRFY 6}

DoVRFY  OBJECT-TYPE
    SYNTAX      OCTET STRING
    MAX-ACCESS  read-write
    STATUS      current
    DESCRIPTION
"
If activated and the format 'Domain=>MTA' is encountered in
 localDomains recipient addresses will be verified with SMTP-VRFY (if VRFY is not supported 'MAIL FROM:' and 'RCPT TO:' will be used).
 If you know that VRFY is not supported with a MTA, you may put the MTA into VRFYforceRCPTTO. Don't forget to configure LDAPFail (belongs also to VRFY) to your needs!
"
    REFERENCE "Verify Recipients with SMTP-VRFY"
    DEFVAL { "1" }
    ::= {RecipientsLocalDomains 885}

syncStatDoVRFY  OBJECT-TYPE
    SYNTAX      OCTET STRING
    MAX-ACCESS  read-only
    STATUS      current
    DESCRIPTION
"
synchronization status for DoVRFY
-1 - DoVRFY could not be synchronized
 0 - synchronization not configured
 1 - out of sync - running master mode
 2 - in sync - running  mastermode
 3 - in sync - running slave mode
 4 - in sync - running master mode (wait to reach state 2)
"
    ::= {DoVRFY 5}

syncStatStrDoVRFY  OBJECT-TYPE
    SYNTAX      OCTET STRING
    MAX-ACCESS  read-only
    STATUS      current
    DESCRIPTION
"
synchronization status line from file assp_sync.cfg for DoVRFY
 0 - synchronization not configured
 1 - out of sync - running master mode
 2 - in sync - running  mastermode
 3 - in sync - running slave mode
 4 - in sync - running master mode (wait to reach state 2)
"
    ::= {DoVRFY 6}

DoMaxDupRcpt  OBJECT-TYPE
    SYNTAX      OCTET STRING
    MAX-ACCESS  read-write
    STATUS      current
    DESCRIPTION
"
Block remote servers that uses the same recipient address more times, than the number defined in MaxDupRcpt in the RCPT TO: command. Scoring is done with mdrValencePB . This check is skipped for outgoing, noprocessing, whitelisted and spamlovers mails. If a message has to be delayed, this check will score before the delay if set to block or score - and score and/or block on the next server request.
"
    REFERENCE "Block Max Duplicate Recipients"
    DEFVAL { "3" }
    ::= {RecipientsLocalDomains 895}

syncStatDoMaxDupRcpt  OBJECT-TYPE
    SYNTAX      OCTET STRING
    MAX-ACCESS  read-only
    STATUS      current
    DESCRIPTION
"
synchronization status for DoMaxDupRcpt
-1 - DoMaxDupRcpt could not be synchronized
 0 - synchronization not configured
 1 - out of sync - running master mode
 2 - in sync - running  mastermode
 3 - in sync - running slave mode
 4 - in sync - running master mode (wait to reach state 2)
"
    ::= {DoMaxDupRcpt 5}

syncStatStrDoMaxDupRcpt  OBJECT-TYPE
    SYNTAX      OCTET STRING
    MAX-ACCESS  read-only
    STATUS      current
    DESCRIPTION
"
synchronization status line from file assp_sync.cfg for DoMaxDupRcpt
 0 - synchronization not configured
 1 - out of sync - running master mode
 2 - in sync - running  mastermode
 3 - in sync - running slave mode
 4 - in sync - running master mode (wait to reach state 2)
"
    ::= {DoMaxDupRcpt 6}

MaxDupRcpt  OBJECT-TYPE
    SYNTAX      OCTET STRING
    MAX-ACCESS  read-write
    STATUS      current
    DESCRIPTION
"
The maximum number of duplicate recipient addresses that are allowed in the sequence of the RCPT TO: commands!
  The number per mail is calculated by 'number of RCPT TO: commands  -  number of unique recipient addresses'.
  For example: if one address is used three times or two addresses are used each two times, will result in the same count - 2. Or if both is the case in one mail, the count will be 4.
"
    REFERENCE "Maximum Allowed Duplicate Recipient Addresses"
    DEFVAL { "0" }
    ::= {RecipientsLocalDomains 896}

syncStatMaxDupRcpt  OBJECT-TYPE
    SYNTAX      OCTET STRING
    MAX-ACCESS  read-only
    STATUS      current
    DESCRIPTION
"
synchronization status for MaxDupRcpt
-1 - MaxDupRcpt could not be synchronized
 0 - synchronization not configured
 1 - out of sync - running master mode
 2 - in sync - running  mastermode
 3 - in sync - running slave mode
 4 - in sync - running master mode (wait to reach state 2)
"
    ::= {MaxDupRcpt 5}

syncStatStrMaxDupRcpt  OBJECT-TYPE
    SYNTAX      OCTET STRING
    MAX-ACCESS  read-only
    STATUS      current
    DESCRIPTION
"
synchronization status line from file assp_sync.cfg for MaxDupRcpt
 0 - synchronization not configured
 1 - out of sync - running master mode
 2 - in sync - running  mastermode
 3 - in sync - running slave mode
 4 - in sync - running master mode (wait to reach state 2)
"
    ::= {MaxDupRcpt 6}

removeForeignBCC  OBJECT-TYPE
    SYNTAX      OCTET STRING
    MAX-ACCESS  read-write
    STATUS      current
    DESCRIPTION
"
Remove foreign BCC: header lines from the mail header. The remove is done before the DoHeaderAddrCheck is done!
"
    REFERENCE "remove Foreign BCC"
    DEFVAL { "" }
    ::= {RecipientsLocalDomains 978}

syncStatremoveForeignBCC  OBJECT-TYPE
    SYNTAX      OCTET STRING
    MAX-ACCESS  read-only
    STATUS      current
    DESCRIPTION
"
synchronization status for removeForeignBCC
-1 - removeForeignBCC could not be synchronized
 0 - synchronization not configured
 1 - out of sync - running master mode
 2 - in sync - running  mastermode
 3 - in sync - running slave mode
 4 - in sync - running master mode (wait to reach state 2)
"
    ::= {removeForeignBCC 5}

syncStatStrremoveForeignBCC  OBJECT-TYPE
    SYNTAX      OCTET STRING
    MAX-ACCESS  read-only
    STATUS      current
    DESCRIPTION
"
synchronization status line from file assp_sync.cfg for removeForeignBCC
 0 - synchronization not configured
 1 - out of sync - running master mode
 2 - in sync - running  mastermode
 3 - in sync - running slave mode
 4 - in sync - running master mode (wait to reach state 2)
"
    ::= {removeForeignBCC 6}

InternalAndWhiteAddresses  OBJECT-TYPE
    SYNTAX      OCTET STRING
    MAX-ACCESS  read-write
    STATUS      current
    DESCRIPTION
"
These local addresses accept mail only from local domains and whitelisted external senders. Accepts specific addresses (user@domain.com), user parts (user) or entire domains (@domain.com). Wildcards are supported (fribo*@domain.com).
"
    REFERENCE "Accept Mail from Local Domains and Whitelisted Senders only*"
    DEFVAL { "" }
    ::= {RecipientsLocalDomains 989}

syncStatInternalAndWhiteAddresses  OBJECT-TYPE
    SYNTAX      OCTET STRING
    MAX-ACCESS  read-only
    STATUS      current
    DESCRIPTION
"
synchronization status for InternalAndWhiteAddresses
-1 - InternalAndWhiteAddresses could not be synchronized
 0 - synchronization not configured
 1 - out of sync - running master mode
 2 - in sync - running  mastermode
 3 - in sync - running slave mode
 4 - in sync - running master mode (wait to reach state 2)
"
    ::= {InternalAndWhiteAddresses 5}

syncStatStrInternalAndWhiteAddresses  OBJECT-TYPE
    SYNTAX      OCTET STRING
    MAX-ACCESS  read-only
    STATUS      current
    DESCRIPTION
"
synchronization status line from file assp_sync.cfg for InternalAndWhiteAddresses
 0 - synchronization not configured
 1 - out of sync - running master mode
 2 - in sync - running  mastermode
 3 - in sync - running slave mode
 4 - in sync - running master mode (wait to reach state 2)
"
    ::= {InternalAndWhiteAddresses 6}

DoHeaderAddrCheck  OBJECT-TYPE
    SYNTAX      OCTET STRING
    MAX-ACCESS  read-write
    STATUS      current
    DESCRIPTION
"
If enabled TO: , CC: and BCC: header lines are checked the following way:
 1. a possible recipient replacement is done
 2. local email address validation is done -  if OK, the next address or headerline is processed
 3. spamtrapaddresses will be detected - scored with stValencePB - mail is blocked (noPenaltyMakeTraps is honored)
 4. a local but not valid TO/CC/BCC: address will be detected - scored with irValencePB 
 5. a RelayAttempt will be detected if a BCC address is not local - scored with rlValencePB - mail is blocked
 The check 3 and 4 honors whitelisting , noprocessing and noBlockingIPs
 Enable this check only, if assp is configured to validate local domains and email addresses!
 NOTICE: that removeForeignBCC take place before this check is done - step 5 will be never reached if removeForeignBCC is enabled!
"
    REFERENCE "Check TO,CC and BCC headers"
    DEFVAL { "" }
    ::= {RecipientsLocalDomains 1001}

syncStatDoHeaderAddrCheck  OBJECT-TYPE
    SYNTAX      OCTET STRING
    MAX-ACCESS  read-only
    STATUS      current
    DESCRIPTION
"
synchronization status for DoHeaderAddrCheck
-1 - DoHeaderAddrCheck could not be synchronized
 0 - synchronization not configured
 1 - out of sync - running master mode
 2 - in sync - running  mastermode
 3 - in sync - running slave mode
 4 - in sync - running master mode (wait to reach state 2)
"
    ::= {DoHeaderAddrCheck 5}

syncStatStrDoHeaderAddrCheck  OBJECT-TYPE
    SYNTAX      OCTET STRING
    MAX-ACCESS  read-only
    STATUS      current
    DESCRIPTION
"
synchronization status line from file assp_sync.cfg for DoHeaderAddrCheck
 0 - synchronization not configured
 1 - out of sync - running master mode
 2 - in sync - running  mastermode
 3 - in sync - running slave mode
 4 - in sync - running master mode (wait to reach state 2)
"
    ::= {DoHeaderAddrCheck 6}

ValidateHelo  OBJECT IDENTIFIER ::= {asspConfig 11}
useHeloBlacklist  OBJECT-TYPE
    SYNTAX      OCTET STRING
    MAX-ACCESS  read-write
    STATUS      current
    DESCRIPTION
"
Use the list of blacklisted-helo hosts built by rebuildspamdb.
"
    REFERENCE "Use the Helo Blacklist"
    DEFVAL { "3" }
    ::= {ValidateHelo 149}

syncStatuseHeloBlacklist  OBJECT-TYPE
    SYNTAX      OCTET STRING
    MAX-ACCESS  read-only
    STATUS      current
    DESCRIPTION
"
synchronization status for useHeloBlacklist
-1 - useHeloBlacklist could not be synchronized
 0 - synchronization not configured
 1 - out of sync - running master mode
 2 - in sync - running  mastermode
 3 - in sync - running slave mode
 4 - in sync - running master mode (wait to reach state 2)
"
    ::= {useHeloBlacklist 5}

syncStatStruseHeloBlacklist  OBJECT-TYPE
    SYNTAX      OCTET STRING
    MAX-ACCESS  read-only
    STATUS      current
    DESCRIPTION
"
synchronization status line from file assp_sync.cfg for useHeloBlacklist
 0 - synchronization not configured
 1 - out of sync - running master mode
 2 - in sync - running  mastermode
 3 - in sync - running slave mode
 4 - in sync - running master mode (wait to reach state 2)
"
    ::= {useHeloBlacklist 6}

DoIPinHelo  OBJECT-TYPE
    SYNTAX      OCTET STRING
    MAX-ACCESS  read-write
    STATUS      current
    DESCRIPTION
"
Score servers with IP number in Helo and check for mismatch with sending IP.
"
    REFERENCE "Do Score Suspicious Helos"
    DEFVAL { "3" }
    ::= {ValidateHelo 150}

syncStatDoIPinHelo  OBJECT-TYPE
    SYNTAX      OCTET STRING
    MAX-ACCESS  read-only
    STATUS      current
    DESCRIPTION
"
synchronization status for DoIPinHelo
-1 - DoIPinHelo could not be synchronized
 0 - synchronization not configured
 1 - out of sync - running master mode
 2 - in sync - running  mastermode
 3 - in sync - running slave mode
 4 - in sync - running master mode (wait to reach state 2)
"
    ::= {DoIPinHelo 5}

syncStatStrDoIPinHelo  OBJECT-TYPE
    SYNTAX      OCTET STRING
    MAX-ACCESS  read-only
    STATUS      current
    DESCRIPTION
"
synchronization status line from file assp_sync.cfg for DoIPinHelo
 0 - synchronization not configured
 1 - out of sync - running master mode
 2 - in sync - running  mastermode
 3 - in sync - running slave mode
 4 - in sync - running master mode (wait to reach state 2)
"
    ::= {DoIPinHelo 6}

ForceFakedLocalHelo  OBJECT-TYPE
    SYNTAX      OCTET STRING
    MAX-ACCESS  read-write
    STATUS      current
    DESCRIPTION
"
If set, ASSP will  check Forged Helos before DELAYING. Collecting, Testmode, CopySpam, Spam-Lover and privat/domain whitelist ( WhitelistPrivacyLevel ) is ignored.
"
    REFERENCE "Enforce Check of Forged Helos Before Delaying"
    DEFVAL { "1" }
    ::= {ValidateHelo 151}

syncStatForceFakedLocalHelo  OBJECT-TYPE
    SYNTAX      OCTET STRING
    MAX-ACCESS  read-only
    STATUS      current
    DESCRIPTION
"
synchronization status for ForceFakedLocalHelo
-1 - ForceFakedLocalHelo could not be synchronized
 0 - synchronization not configured
 1 - out of sync - running master mode
 2 - in sync - running  mastermode
 3 - in sync - running slave mode
 4 - in sync - running master mode (wait to reach state 2)
"
    ::= {ForceFakedLocalHelo 5}

syncStatStrForceFakedLocalHelo  OBJECT-TYPE
    SYNTAX      OCTET STRING
    MAX-ACCESS  read-only
    STATUS      current
    DESCRIPTION
"
synchronization status line from file assp_sync.cfg for ForceFakedLocalHelo
 0 - synchronization not configured
 1 - out of sync - running master mode
 2 - in sync - running  mastermode
 3 - in sync - running slave mode
 4 - in sync - running master mode (wait to reach state 2)
"
    ::= {ForceFakedLocalHelo 6}

DoFakedLocalHelo  OBJECT-TYPE
    SYNTAX      OCTET STRING
    MAX-ACCESS  read-write
    STATUS      current
    DESCRIPTION
"
Block remote servers that claim to come from our Local Domains/Local IP's/Local Host.
"
    REFERENCE "Block Forged Helos"
    DEFVAL { "1" }
    ::= {ValidateHelo 152}

syncStatDoFakedLocalHelo  OBJECT-TYPE
    SYNTAX      OCTET STRING
    MAX-ACCESS  read-only
    STATUS      current
    DESCRIPTION
"
synchronization status for DoFakedLocalHelo
-1 - DoFakedLocalHelo could not be synchronized
 0 - synchronization not configured
 1 - out of sync - running master mode
 2 - in sync - running  mastermode
 3 - in sync - running slave mode
 4 - in sync - running master mode (wait to reach state 2)
"
    ::= {DoFakedLocalHelo 5}

syncStatStrDoFakedLocalHelo  OBJECT-TYPE
    SYNTAX      OCTET STRING
    MAX-ACCESS  read-only
    STATUS      current
    DESCRIPTION
"
synchronization status line from file assp_sync.cfg for DoFakedLocalHelo
 0 - synchronization not configured
 1 - out of sync - running master mode
 2 - in sync - running  mastermode
 3 - in sync - running slave mode
 4 - in sync - running master mode (wait to reach state 2)
"
    ::= {DoFakedLocalHelo 6}

DoFakedUseLocalDomain  OBJECT-TYPE
    SYNTAX      OCTET STRING
    MAX-ACCESS  read-write
    STATUS      current
    DESCRIPTION
"
If set, DoFakedLocalHelo will  use localDomains.
"
    REFERENCE "Use Local Domain List for Blocking Forged Helos"
    DEFVAL { "1" }
    ::= {ValidateHelo 153}

syncStatDoFakedUseLocalDomain  OBJECT-TYPE
    SYNTAX      OCTET STRING
    MAX-ACCESS  read-only
    STATUS      current
    DESCRIPTION
"
synchronization status for DoFakedUseLocalDomain
-1 - DoFakedUseLocalDomain could not be synchronized
 0 - synchronization not configured
 1 - out of sync - running master mode
 2 - in sync - running  mastermode
 3 - in sync - running slave mode
 4 - in sync - running master mode (wait to reach state 2)
"
    ::= {DoFakedUseLocalDomain 5}

syncStatStrDoFakedUseLocalDomain  OBJECT-TYPE
    SYNTAX      OCTET STRING
    MAX-ACCESS  read-only
    STATUS      current
    DESCRIPTION
"
synchronization status line from file assp_sync.cfg for DoFakedUseLocalDomain
 0 - synchronization not configured
 1 - out of sync - running master mode
 2 - in sync - running  mastermode
 3 - in sync - running slave mode
 4 - in sync - running master mode (wait to reach state 2)
"
    ::= {DoFakedUseLocalDomain 6}

DoFakedWL  OBJECT-TYPE
    SYNTAX      OCTET STRING
    MAX-ACCESS  read-write
    STATUS      current
    DESCRIPTION
"
Disable 'Block Forged Helo's' for whitelisted addresses (not recommended).
"
    REFERENCE "Do Not Block Whitelisted"
    DEFVAL { "" }
    ::= {ValidateHelo 154}

syncStatDoFakedWL  OBJECT-TYPE
    SYNTAX      OCTET STRING
    MAX-ACCESS  read-only
    STATUS      current
    DESCRIPTION
"
synchronization status for DoFakedWL
-1 - DoFakedWL could not be synchronized
 0 - synchronization not configured
 1 - out of sync - running master mode
 2 - in sync - running  mastermode
 3 - in sync - running slave mode
 4 - in sync - running master mode (wait to reach state 2)
"
    ::= {DoFakedWL 5}

syncStatStrDoFakedWL  OBJECT-TYPE
    SYNTAX      OCTET STRING
    MAX-ACCESS  read-only
    STATUS      current
    DESCRIPTION
"
synchronization status line from file assp_sync.cfg for DoFakedWL
 0 - synchronization not configured
 1 - out of sync - running master mode
 2 - in sync - running  mastermode
 3 - in sync - running slave mode
 4 - in sync - running master mode (wait to reach state 2)
"
    ::= {DoFakedWL 6}

DoFakedNP  OBJECT-TYPE
    SYNTAX      OCTET STRING
    MAX-ACCESS  read-write
    STATUS      current
    DESCRIPTION
"
Disable 'Block Forged Helo's' for addresses identified as noprocessing (not recommended).
"
    REFERENCE "Do Not Block Noprocessing"
    DEFVAL { "" }
    ::= {ValidateHelo 155}

syncStatDoFakedNP  OBJECT-TYPE
    SYNTAX      OCTET STRING
    MAX-ACCESS  read-only
    STATUS      current
    DESCRIPTION
"
synchronization status for DoFakedNP
-1 - DoFakedNP could not be synchronized
 0 - synchronization not configured
 1 - out of sync - running master mode
 2 - in sync - running  mastermode
 3 - in sync - running slave mode
 4 - in sync - running master mode (wait to reach state 2)
"
    ::= {DoFakedNP 5}

syncStatStrDoFakedNP  OBJECT-TYPE
    SYNTAX      OCTET STRING
    MAX-ACCESS  read-only
    STATUS      current
    DESCRIPTION
"
synchronization status line from file assp_sync.cfg for DoFakedNP
 0 - synchronization not configured
 1 - out of sync - running master mode
 2 - in sync - running  mastermode
 3 - in sync - running slave mode
 4 - in sync - running master mode (wait to reach state 2)
"
    ::= {DoFakedNP 6}

myServerRe  OBJECT-TYPE
    SYNTAX      OCTET STRING
    MAX-ACCESS  read-write
    STATUS      current
    DESCRIPTION
"
Local Domains, IP's and Hostnames are often use to fake (forge) the Helo. Include all IP addresses and hostnames for your server here, localhost is already included. Include Local Domains of your choice here, if you deactivated the automatic use of the local domain list.  For example: 11.22.33.44|mx.YourDomains.com|here.org
"
    REFERENCE "Local Domains,IP's and Hostnames*"
    DEFVAL { "" }
    ::= {ValidateHelo 156}

noHelo  OBJECT-TYPE
    SYNTAX      OCTET STRING
    MAX-ACCESS  read-write
    STATUS      current
    DESCRIPTION
"
Enter IP addresses that you don't want to be HELO validated.
   For example: 127.0.0.1|192.168.
"
    REFERENCE "Don't Validate HELO for these IP's*"
    DEFVAL { "" }
    ::= {ValidateHelo 157}

syncStatnoHelo  OBJECT-TYPE
    SYNTAX      OCTET STRING
    MAX-ACCESS  read-only
    STATUS      current
    DESCRIPTION
"
synchronization status for noHelo
-1 - noHelo could not be synchronized
 0 - synchronization not configured
 1 - out of sync - running master mode
 2 - in sync - running  mastermode
 3 - in sync - running slave mode
 4 - in sync - running master mode (wait to reach state 2)
"
    ::= {noHelo 5}

syncStatStrnoHelo  OBJECT-TYPE
    SYNTAX      OCTET STRING
    MAX-ACCESS  read-only
    STATUS      current
    DESCRIPTION
"
synchronization status line from file assp_sync.cfg for noHelo
 0 - synchronization not configured
 1 - out of sync - running master mode
 2 - in sync - running  mastermode
 3 - in sync - running slave mode
 4 - in sync - running master mode (wait to reach state 2)
"
    ::= {noHelo 6}

heloBlacklistIgnore  OBJECT-TYPE
    SYNTAX      OCTET STRING
    MAX-ACCESS  read-write
    STATUS      current
    DESCRIPTION
"
HELO / EHLO greetings on this list will be excluded from the HELO checks. For example: host123.isp.com|host456.*.com
"
    REFERENCE "Don't block these HELO's*"
    DEFVAL { "" }
    ::= {ValidateHelo 158}

syncStatheloBlacklistIgnore  OBJECT-TYPE
    SYNTAX      OCTET STRING
    MAX-ACCESS  read-only
    STATUS      current
    DESCRIPTION
"
synchronization status for heloBlacklistIgnore
-1 - heloBlacklistIgnore could not be synchronized
 0 - synchronization not configured
 1 - out of sync - running master mode
 2 - in sync - running  mastermode
 3 - in sync - running slave mode
 4 - in sync - running master mode (wait to reach state 2)
"
    ::= {heloBlacklistIgnore 5}

syncStatStrheloBlacklistIgnore  OBJECT-TYPE
    SYNTAX      OCTET STRING
    MAX-ACCESS  read-only
    STATUS      current
    DESCRIPTION
"
synchronization status line from file assp_sync.cfg for heloBlacklistIgnore
 0 - synchronization not configured
 1 - out of sync - running master mode
 2 - in sync - running  mastermode
 3 - in sync - running slave mode
 4 - in sync - running master mode (wait to reach state 2)
"
    ::= {heloBlacklistIgnore 6}

ForceValidateHelo  OBJECT-TYPE
    SYNTAX      OCTET STRING
    MAX-ACCESS  read-write
    STATUS      current
    DESCRIPTION
"
If set, ASSP will  Validate/Invalidate the format of HELO before DELAYING. Collecting, Testmode, CopySpam, Spam-Lover and privat whitelist ( WhitelistPrivacyLevel ) is ignored.
"
    REFERENCE "Enforce Early Helo Checks"
    DEFVAL { "1" }
    ::= {ValidateHelo 159}

syncStatForceValidateHelo  OBJECT-TYPE
    SYNTAX      OCTET STRING
    MAX-ACCESS  read-only
    STATUS      current
    DESCRIPTION
"
synchronization status for ForceValidateHelo
-1 - ForceValidateHelo could not be synchronized
 0 - synchronization not configured
 1 - out of sync - running master mode
 2 - in sync - running  mastermode
 3 - in sync - running slave mode
 4 - in sync - running master mode (wait to reach state 2)
"
    ::= {ForceValidateHelo 5}

syncStatStrForceValidateHelo  OBJECT-TYPE
    SYNTAX      OCTET STRING
    MAX-ACCESS  read-only
    STATUS      current
    DESCRIPTION
"
synchronization status line from file assp_sync.cfg for ForceValidateHelo
 0 - synchronization not configured
 1 - out of sync - running master mode
 2 - in sync - running  mastermode
 3 - in sync - running slave mode
 4 - in sync - running master mode (wait to reach state 2)
"
    ::= {ForceValidateHelo 6}

DoValidFormatHelo  OBJECT-TYPE
    SYNTAX      OCTET STRING
    MAX-ACCESS  read-write
    STATUS      current
    DESCRIPTION
"
If activated, the HELO is checked against the expression below. If the Regular Expression matches, the HELO is validated as being ok. 
"
    REFERENCE "Validate Format of HELO"
    DEFVAL { "1" }
    ::= {ValidateHelo 160}

syncStatDoValidFormatHelo  OBJECT-TYPE
    SYNTAX      OCTET STRING
    MAX-ACCESS  read-only
    STATUS      current
    DESCRIPTION
"
synchronization status for DoValidFormatHelo
-1 - DoValidFormatHelo could not be synchronized
 0 - synchronization not configured
 1 - out of sync - running master mode
 2 - in sync - running  mastermode
 3 - in sync - running slave mode
 4 - in sync - running master mode (wait to reach state 2)
"
    ::= {DoValidFormatHelo 5}

syncStatStrDoValidFormatHelo  OBJECT-TYPE
    SYNTAX      OCTET STRING
    MAX-ACCESS  read-only
    STATUS      current
    DESCRIPTION
"
synchronization status line from file assp_sync.cfg for DoValidFormatHelo
 0 - synchronization not configured
 1 - out of sync - running master mode
 2 - in sync - running  mastermode
 3 - in sync - running slave mode
 4 - in sync - running master mode (wait to reach state 2)
"
    ::= {DoValidFormatHelo 6}

validFormatHeloRe  OBJECT-TYPE
    SYNTAX      OCTET STRING
    MAX-ACCESS  read-write
    STATUS      current
    DESCRIPTION
"
Validate Format HELO will check incoming HELOs according to rfc1123. For example: ^(?:\w[\w\.\-]*\.\w{2,6})$ or ^(?:(?:[a-z\d][a-z\d\-]*)?[a-z\d]\.)+[a-z]{2,6}$
"
    REFERENCE "Regular Expression to Validate Format of HELO*"
    DEFVAL { "file:files/validhelo.txt" }
    ::= {ValidateHelo 161}

syncStatvalidFormatHeloRe  OBJECT-TYPE
    SYNTAX      OCTET STRING
    MAX-ACCESS  read-only
    STATUS      current
    DESCRIPTION
"
synchronization status for validFormatHeloRe
-1 - validFormatHeloRe could not be synchronized
 0 - synchronization not configured
 1 - out of sync - running master mode
 2 - in sync - running  mastermode
 3 - in sync - running slave mode
 4 - in sync - running master mode (wait to reach state 2)
"
    ::= {validFormatHeloRe 5}

syncStatStrvalidFormatHeloRe  OBJECT-TYPE
    SYNTAX      OCTET STRING
    MAX-ACCESS  read-only
    STATUS      current
    DESCRIPTION
"
synchronization status line from file assp_sync.cfg for validFormatHeloRe
 0 - synchronization not configured
 1 - out of sync - running master mode
 2 - in sync - running  mastermode
 3 - in sync - running slave mode
 4 - in sync - running master mode (wait to reach state 2)
"
    ::= {validFormatHeloRe 6}

DoInvalidFormatHelo  OBJECT-TYPE
    SYNTAX      OCTET STRING
    MAX-ACCESS  read-write
    STATUS      current
    DESCRIPTION
"
If activated, the HELO is checked against the expression below. If the Regular Expression matches, the HELO is invalidated as being not ok.
"
    REFERENCE "Invalidate Format of HELO"
    DEFVAL { "1" }
    ::= {ValidateHelo 162}

syncStatDoInvalidFormatHelo  OBJECT-TYPE
    SYNTAX      OCTET STRING
    MAX-ACCESS  read-only
    STATUS      current
    DESCRIPTION
"
synchronization status for DoInvalidFormatHelo
-1 - DoInvalidFormatHelo could not be synchronized
 0 - synchronization not configured
 1 - out of sync - running master mode
 2 - in sync - running  mastermode
 3 - in sync - running slave mode
 4 - in sync - running master mode (wait to reach state 2)
"
    ::= {DoInvalidFormatHelo 5}

syncStatStrDoInvalidFormatHelo  OBJECT-TYPE
    SYNTAX      OCTET STRING
    MAX-ACCESS  read-only
    STATUS      current
    DESCRIPTION
"
synchronization status line from file assp_sync.cfg for DoInvalidFormatHelo
 0 - synchronization not configured
 1 - out of sync - running master mode
 2 - in sync - running  mastermode
 3 - in sync - running slave mode
 4 - in sync - running master mode (wait to reach state 2)
"
    ::= {DoInvalidFormatHelo 6}

invalidFormatHeloRe  OBJECT-TYPE
    SYNTAX      OCTET STRING
    MAX-ACCESS  read-write
    STATUS      current
    DESCRIPTION
"
Invalidate Format HELO will check incoming HELOs for this. 
 For example:  ^\d+\.\d+\.\d+\.\d+$|^[^\.]+\.?$,
"
    REFERENCE "Regular Expression to Invalidate Format of HELO**"
    DEFVAL { "file:files/invalidhelo.txt" }
    ::= {ValidateHelo 163}

syncStatinvalidFormatHeloRe  OBJECT-TYPE
    SYNTAX      OCTET STRING
    MAX-ACCESS  read-only
    STATUS      current
    DESCRIPTION
"
synchronization status for invalidFormatHeloRe
-1 - invalidFormatHeloRe could not be synchronized
 0 - synchronization not configured
 1 - out of sync - running master mode
 2 - in sync - running  mastermode
 3 - in sync - running slave mode
 4 - in sync - running master mode (wait to reach state 2)
"
    ::= {invalidFormatHeloRe 5}

syncStatStrinvalidFormatHeloRe  OBJECT-TYPE
    SYNTAX      OCTET STRING
    MAX-ACCESS  read-only
    STATUS      current
    DESCRIPTION
"
synchronization status line from file assp_sync.cfg for invalidFormatHeloRe
 0 - synchronization not configured
 1 - out of sync - running master mode
 2 - in sync - running  mastermode
 3 - in sync - running slave mode
 4 - in sync - running master mode (wait to reach state 2)
"
    ::= {invalidFormatHeloRe 6}

DoHeloWL  OBJECT-TYPE
    SYNTAX      OCTET STRING
    MAX-ACCESS  read-write
    STATUS      current
    DESCRIPTION
"
Do valid/invalid Helo for whitelisted addresses.
"
    REFERENCE "Do Valid/Invalid/Black Helo for Whitelisted"
    DEFVAL { "1" }
    ::= {ValidateHelo 164}

syncStatDoHeloWL  OBJECT-TYPE
    SYNTAX      OCTET STRING
    MAX-ACCESS  read-only
    STATUS      current
    DESCRIPTION
"
synchronization status for DoHeloWL
-1 - DoHeloWL could not be synchronized
 0 - synchronization not configured
 1 - out of sync - running master mode
 2 - in sync - running  mastermode
 3 - in sync - running slave mode
 4 - in sync - running master mode (wait to reach state 2)
"
    ::= {DoHeloWL 5}

syncStatStrDoHeloWL  OBJECT-TYPE
    SYNTAX      OCTET STRING
    MAX-ACCESS  read-only
    STATUS      current
    DESCRIPTION
"
synchronization status line from file assp_sync.cfg for DoHeloWL
 0 - synchronization not configured
 1 - out of sync - running master mode
 2 - in sync - running  mastermode
 3 - in sync - running slave mode
 4 - in sync - running master mode (wait to reach state 2)
"
    ::= {DoHeloWL 6}

DoHeloNP  OBJECT-TYPE
    SYNTAX      OCTET STRING
    MAX-ACCESS  read-write
    STATUS      current
    DESCRIPTION
"
Do valid/invalid Helo for noprocessing addresses.
  
  
"
    REFERENCE "Do Valid/Invalid/Black Helo for Noprocessing"
    DEFVAL { "1" }
    ::= {ValidateHelo 165}

syncStatDoHeloNP  OBJECT-TYPE
    SYNTAX      OCTET STRING
    MAX-ACCESS  read-only
    STATUS      current
    DESCRIPTION
"
synchronization status for DoHeloNP
-1 - DoHeloNP could not be synchronized
 0 - synchronization not configured
 1 - out of sync - running master mode
 2 - in sync - running  mastermode
 3 - in sync - running slave mode
 4 - in sync - running master mode (wait to reach state 2)
"
    ::= {DoHeloNP 5}

syncStatStrDoHeloNP  OBJECT-TYPE
    SYNTAX      OCTET STRING
    MAX-ACCESS  read-only
    STATUS      current
    DESCRIPTION
"
synchronization status line from file assp_sync.cfg for DoHeloNP
 0 - synchronization not configured
 1 - out of sync - running master mode
 2 - in sync - running  mastermode
 3 - in sync - running slave mode
 4 - in sync - running master mode (wait to reach state 2)
"
    ::= {DoHeloNP 6}

useHeloGoodlist  OBJECT-TYPE
    SYNTAX      OCTET STRING
    MAX-ACCESS  read-write
    STATUS      current
    DESCRIPTION
"
Use the list of known good helo hosts built by rebuildspamdb.
  bonus - the message/IP get a bonus of the weighted negative value of hlValencePB 
  whitelisted - the message is processed as whitelisted
  The good helos and weights are stored together with the helo blacklist.
"
    REFERENCE "Use the Helo Goodlist"
    DEFVAL { "1" }
    ::= {ValidateHelo 992}

syncStatuseHeloGoodlist  OBJECT-TYPE
    SYNTAX      OCTET STRING
    MAX-ACCESS  read-only
    STATUS      current
    DESCRIPTION
"
synchronization status for useHeloGoodlist
-1 - useHeloGoodlist could not be synchronized
 0 - synchronization not configured
 1 - out of sync - running master mode
 2 - in sync - running  mastermode
 3 - in sync - running slave mode
 4 - in sync - running master mode (wait to reach state 2)
"
    ::= {useHeloGoodlist 5}

syncStatStruseHeloGoodlist  OBJECT-TYPE
    SYNTAX      OCTET STRING
    MAX-ACCESS  read-only
    STATUS      current
    DESCRIPTION
"
synchronization status line from file assp_sync.cfg for useHeloGoodlist
 0 - synchronization not configured
 1 - out of sync - running master mode
 2 - in sync - running  mastermode
 3 - in sync - running slave mode
 4 - in sync - running master mode (wait to reach state 2)
"
    ::= {useHeloGoodlist 6}

ValidateSender  OBJECT IDENTIFIER ::= {asspConfig 12}
DoBlackDomain  OBJECT-TYPE
    SYNTAX      OCTET STRING
    MAX-ACCESS  read-write
    STATUS      current
    DESCRIPTION
"

"
    REFERENCE "Do Blacklisted Addresses and Domains"
    DEFVAL { "1" }
    ::= {ValidateSender 166}

syncStatDoBlackDomain  OBJECT-TYPE
    SYNTAX      OCTET STRING
    MAX-ACCESS  read-only
    STATUS      current
    DESCRIPTION
"
synchronization status for DoBlackDomain
-1 - DoBlackDomain could not be synchronized
 0 - synchronization not configured
 1 - out of sync - running master mode
 2 - in sync - running  mastermode
 3 - in sync - running slave mode
 4 - in sync - running master mode (wait to reach state 2)
"
    ::= {DoBlackDomain 5}

syncStatStrDoBlackDomain  OBJECT-TYPE
    SYNTAX      OCTET STRING
    MAX-ACCESS  read-only
    STATUS      current
    DESCRIPTION
"
synchronization status line from file assp_sync.cfg for DoBlackDomain
 0 - synchronization not configured
 1 - out of sync - running master mode
 2 - in sync - running  mastermode
 3 - in sync - running slave mode
 4 - in sync - running master mode (wait to reach state 2)
"
    ::= {DoBlackDomain 6}

DoBlackDomainWL  OBJECT-TYPE
    SYNTAX      OCTET STRING
    MAX-ACCESS  read-write
    STATUS      current
    DESCRIPTION
"
Do blacklisting addresses &amp; domains in messages which are marked whitelisted by whiteRe, whiteListedDomains, whiteListedIPs, whitelistdb, DoOrgWhiting or ValidateRWL .
"
    REFERENCE "Do Blacklisting Addresses and Domains for White"
    DEFVAL { "1" }
    ::= {ValidateSender 167}

syncStatDoBlackDomainWL  OBJECT-TYPE
    SYNTAX      OCTET STRING
    MAX-ACCESS  read-only
    STATUS      current
    DESCRIPTION
"
synchronization status for DoBlackDomainWL
-1 - DoBlackDomainWL could not be synchronized
 0 - synchronization not configured
 1 - out of sync - running master mode
 2 - in sync - running  mastermode
 3 - in sync - running slave mode
 4 - in sync - running master mode (wait to reach state 2)
"
    ::= {DoBlackDomainWL 5}

syncStatStrDoBlackDomainWL  OBJECT-TYPE
    SYNTAX      OCTET STRING
    MAX-ACCESS  read-only
    STATUS      current
    DESCRIPTION
"
synchronization status line from file assp_sync.cfg for DoBlackDomainWL
 0 - synchronization not configured
 1 - out of sync - running master mode
 2 - in sync - running  mastermode
 3 - in sync - running slave mode
 4 - in sync - running master mode (wait to reach state 2)
"
    ::= {DoBlackDomainWL 6}

DoBlackDomainNP  OBJECT-TYPE
    SYNTAX      OCTET STRING
    MAX-ACCESS  read-write
    STATUS      current
    DESCRIPTION
"
Do blacklisting addresses &amp; domains in messages which are marked noprocessing by npRe, noProcessingDomains, noProcessingIPs or noProcessing.
"
    REFERENCE "Do Blacklisting Addresses and Domains for NoProcessing"
    DEFVAL { "1" }
    ::= {ValidateSender 168}

syncStatDoBlackDomainNP  OBJECT-TYPE
    SYNTAX      OCTET STRING
    MAX-ACCESS  read-only
    STATUS      current
    DESCRIPTION
"
synchronization status for DoBlackDomainNP
-1 - DoBlackDomainNP could not be synchronized
 0 - synchronization not configured
 1 - out of sync - running master mode
 2 - in sync - running  mastermode
 3 - in sync - running slave mode
 4 - in sync - running master mode (wait to reach state 2)
"
    ::= {DoBlackDomainNP 5}

syncStatStrDoBlackDomainNP  OBJECT-TYPE
    SYNTAX      OCTET STRING
    MAX-ACCESS  read-only
    STATUS      current
    DESCRIPTION
"
synchronization status line from file assp_sync.cfg for DoBlackDomainNP
 0 - synchronization not configured
 1 - out of sync - running master mode
 2 - in sync - running  mastermode
 3 - in sync - running slave mode
 4 - in sync - running master mode (wait to reach state 2)
"
    ::= {DoBlackDomainNP 6}

blackListedDomains  OBJECT-TYPE
    SYNTAX      OCTET STRING
    MAX-ACCESS  read-write
    STATUS      current
    DESCRIPTION
"
Addresses  &amp; Domains from which you always want to reject mail, they only send you spam. Note this matches the end of the address, so if you don't want to match subdomains then include the @. Note that buy.com would also match spambuy.com but .buy.com won't match buy.com. abc@def.com will match abc@def.com but won't match bbc@def.com. Wildcards are supported. For example: cc|info|biz|seller@bayer.com|sell*@basf.com
  It is possible to make email addresses blacklisted only for a set of local domains and/or local users. Use wildcards (* and ?) to define domains.
  Use the following syntax to do this:
  *@anydomain=>*@any_local_domain - for domain to domain
  *@*.anydomain=>*@any_local_domain - for any sub-domain to domain
  user@anydomain=>*@*.any_local_domain - for user to any sub-domain
  It is possible to define more than one entry at the left and the right side of the definition (=&gt;), like:
  *@anydomain|*@other_domain=>*@any_local_domain|*@other_local_domain - always separate multiple entries by pipes
  It is also possible to use a GroupDefinition in any or both sides, like:
  [sendergroup]=>[recipientgroup]
  [sendergroup1]|[sendergroup2]|*@domain=>[recipientgroup1]|[recipientgroup2]|user@local_domain
  NOTICE - that the local email addresses and domains are not checked to be local once
"
    REFERENCE "Blacklisted Addresses and Domains*"
    DEFVAL { "file:files/blackdomains.txt" }
    ::= {ValidateSender 169}

syncStatblackListedDomains  OBJECT-TYPE
    SYNTAX      OCTET STRING
    MAX-ACCESS  read-only
    STATUS      current
    DESCRIPTION
"
synchronization status for blackListedDomains
-1 - blackListedDomains could not be synchronized
 0 - synchronization not configured
 1 - out of sync - running master mode
 2 - in sync - running  mastermode
 3 - in sync - running slave mode
 4 - in sync - running master mode (wait to reach state 2)
"
    ::= {blackListedDomains 5}

syncStatStrblackListedDomains  OBJECT-TYPE
    SYNTAX      OCTET STRING
    MAX-ACCESS  read-only
    STATUS      current
    DESCRIPTION
"
synchronization status line from file assp_sync.cfg for blackListedDomains
 0 - synchronization not configured
 1 - out of sync - running master mode
 2 - in sync - running  mastermode
 3 - in sync - running slave mode
 4 - in sync - running master mode (wait to reach state 2)
"
    ::= {blackListedDomains 6}

DoMsgID  OBJECT-TYPE
    SYNTAX      OCTET STRING
    MAX-ACCESS  read-write
    STATUS      current
    DESCRIPTION
"
Score messages with missing/suspicious/invalid Message-ID. Scoring is done by midmValencePB / midsValencePB / midiValencePB .
"
    REFERENCE "Check Message IDs"
    DEFVAL { "3" }
    ::= {ValidateSender 170}

syncStatDoMsgID  OBJECT-TYPE
    SYNTAX      OCTET STRING
    MAX-ACCESS  read-only
    STATUS      current
    DESCRIPTION
"
synchronization status for DoMsgID
-1 - DoMsgID could not be synchronized
 0 - synchronization not configured
 1 - out of sync - running master mode
 2 - in sync - running  mastermode
 3 - in sync - running slave mode
 4 - in sync - running master mode (wait to reach state 2)
"
    ::= {DoMsgID 5}

syncStatStrDoMsgID  OBJECT-TYPE
    SYNTAX      OCTET STRING
    MAX-ACCESS  read-only
    STATUS      current
    DESCRIPTION
"
synchronization status line from file assp_sync.cfg for DoMsgID
 0 - synchronization not configured
 1 - out of sync - running master mode
 2 - in sync - running  mastermode
 3 - in sync - running slave mode
 4 - in sync - running master mode (wait to reach state 2)
"
    ::= {DoMsgID 6}

noMsgID  OBJECT-TYPE
    SYNTAX      OCTET STRING
    MAX-ACCESS  read-write
    STATUS      current
    DESCRIPTION
"
Enter IP addresses that you don't want to be Message-ID validated, separated by pipes (|). For example: 127.0.0.1|192.168.
"
    REFERENCE "Don't Validate Message-IDs for these IPs*"
    DEFVAL { "127.0.0.|192.168.|10." }
    ::= {ValidateSender 171}

syncStatnoMsgID  OBJECT-TYPE
    SYNTAX      OCTET STRING
    MAX-ACCESS  read-only
    STATUS      current
    DESCRIPTION
"
synchronization status for noMsgID
-1 - noMsgID could not be synchronized
 0 - synchronization not configured
 1 - out of sync - running master mode
 2 - in sync - running  mastermode
 3 - in sync - running slave mode
 4 - in sync - running master mode (wait to reach state 2)
"
    ::= {noMsgID 5}

syncStatStrnoMsgID  OBJECT-TYPE
    SYNTAX      OCTET STRING
    MAX-ACCESS  read-only
    STATUS      current
    DESCRIPTION
"
synchronization status line from file assp_sync.cfg for noMsgID
 0 - synchronization not configured
 1 - out of sync - running master mode
 2 - in sync - running  mastermode
 3 - in sync - running slave mode
 4 - in sync - running master mode (wait to reach state 2)
"
    ::= {noMsgID 6}

validMsgIDRe  OBJECT-TYPE
    SYNTAX      OCTET STRING
    MAX-ACCESS  read-write
    STATUS      current
    DESCRIPTION
"
Check Message IDs will check incoming messages for valid Message-IDs. For example: ^.+\@.+\..+$  
"
    REFERENCE "Regular Expression to Validate Format of Message-ID*"
    DEFVAL { "^.+\@.+\..+$" }
    ::= {ValidateSender 172}

syncStatvalidMsgIDRe  OBJECT-TYPE
    SYNTAX      OCTET STRING
    MAX-ACCESS  read-only
    STATUS      current
    DESCRIPTION
"
synchronization status for validMsgIDRe
-1 - validMsgIDRe could not be synchronized
 0 - synchronization not configured
 1 - out of sync - running master mode
 2 - in sync - running  mastermode
 3 - in sync - running slave mode
 4 - in sync - running master mode (wait to reach state 2)
"
    ::= {validMsgIDRe 5}

syncStatStrvalidMsgIDRe  OBJECT-TYPE
    SYNTAX      OCTET STRING
    MAX-ACCESS  read-only
    STATUS      current
    DESCRIPTION
"
synchronization status line from file assp_sync.cfg for validMsgIDRe
 0 - synchronization not configured
 1 - out of sync - running master mode
 2 - in sync - running  mastermode
 3 - in sync - running slave mode
 4 - in sync - running master mode (wait to reach state 2)
"
    ::= {validMsgIDRe 6}

invalidMsgIDRe  OBJECT-TYPE
    SYNTAX      OCTET STRING
    MAX-ACCESS  read-write
    STATUS      current
    DESCRIPTION
"
Check Message IDs will check incoming messages for invalid Message-IDs.
"
    REFERENCE "Regular Expression to Invalidate Format of Message-ID**"
    DEFVAL { "" }
    ::= {ValidateSender 173}

syncStatinvalidMsgIDRe  OBJECT-TYPE
    SYNTAX      OCTET STRING
    MAX-ACCESS  read-only
    STATUS      current
    DESCRIPTION
"
synchronization status for invalidMsgIDRe
-1 - invalidMsgIDRe could not be synchronized
 0 - synchronization not configured
 1 - out of sync - running master mode
 2 - in sync - running  mastermode
 3 - in sync - running slave mode
 4 - in sync - running master mode (wait to reach state 2)
"
    ::= {invalidMsgIDRe 5}

syncStatStrinvalidMsgIDRe  OBJECT-TYPE
    SYNTAX      OCTET STRING
    MAX-ACCESS  read-only
    STATUS      current
    DESCRIPTION
"
synchronization status line from file assp_sync.cfg for invalidMsgIDRe
 0 - synchronization not configured
 1 - out of sync - running master mode
 2 - in sync - running  mastermode
 3 - in sync - running slave mode
 4 - in sync - running master mode (wait to reach state 2)
"
    ::= {invalidMsgIDRe 6}

DoNoValidLocalSender  OBJECT-TYPE
    SYNTAX      OCTET STRING
    MAX-ACCESS  read-write
    STATUS      current
    DESCRIPTION
"
If activated, each remote sender  with a local domain is checked against the Local Addresses File and/or LDAP. 
"
    REFERENCE "Validate Remote Sender with Local Domain Address"
    DEFVAL { "1" }
    ::= {ValidateSender 174}

syncStatDoNoValidLocalSender  OBJECT-TYPE
    SYNTAX      OCTET STRING
    MAX-ACCESS  read-only
    STATUS      current
    DESCRIPTION
"
synchronization status for DoNoValidLocalSender
-1 - DoNoValidLocalSender could not be synchronized
 0 - synchronization not configured
 1 - out of sync - running master mode
 2 - in sync - running  mastermode
 3 - in sync - running slave mode
 4 - in sync - running master mode (wait to reach state 2)
"
    ::= {DoNoValidLocalSender 5}

syncStatStrDoNoValidLocalSender  OBJECT-TYPE
    SYNTAX      OCTET STRING
    MAX-ACCESS  read-only
    STATUS      current
    DESCRIPTION
"
synchronization status line from file assp_sync.cfg for DoNoValidLocalSender
 0 - synchronization not configured
 1 - out of sync - running master mode
 2 - in sync - running  mastermode
 3 - in sync - running slave mode
 4 - in sync - running master mode (wait to reach state 2)
"
    ::= {DoNoValidLocalSender 6}

ForceNoValidLocalSender  OBJECT-TYPE
    SYNTAX      OCTET STRING
    MAX-ACCESS  read-write
    STATUS      current
    DESCRIPTION
"
If set, ASSP will check Remote Sender with Local Domain Address before Delaying a message. Collecting, Testmode, CopySpam, and Spam-Lover settings are ignored.
"
    REFERENCE "Early 'Remote Sender with Local Domain Address' Check"
    DEFVAL { "1" }
    ::= {ValidateSender 175}

syncStatForceNoValidLocalSender  OBJECT-TYPE
    SYNTAX      OCTET STRING
    MAX-ACCESS  read-only
    STATUS      current
    DESCRIPTION
"
synchronization status for ForceNoValidLocalSender
-1 - ForceNoValidLocalSender could not be synchronized
 0 - synchronization not configured
 1 - out of sync - running master mode
 2 - in sync - running  mastermode
 3 - in sync - running slave mode
 4 - in sync - running master mode (wait to reach state 2)
"
    ::= {ForceNoValidLocalSender 5}

syncStatStrForceNoValidLocalSender  OBJECT-TYPE
    SYNTAX      OCTET STRING
    MAX-ACCESS  read-only
    STATUS      current
    DESCRIPTION
"
synchronization status line from file assp_sync.cfg for ForceNoValidLocalSender
 0 - synchronization not configured
 1 - out of sync - running master mode
 2 - in sync - running  mastermode
 3 - in sync - running slave mode
 4 - in sync - running master mode (wait to reach state 2)
"
    ::= {ForceNoValidLocalSender 6}

DoNoSpoofing  OBJECT-TYPE
    SYNTAX      OCTET STRING
    MAX-ACCESS  read-write
    STATUS      current
    DESCRIPTION
"
If activated, each external sender address built with a domain in localDomains is regarded a spoofed address. An external sender is a sender from an IP not in acceptAllMail and not authenticated. 
"
    REFERENCE "Block Local Address from External Sender "
    DEFVAL { "3" }
    ::= {ValidateSender 176}

syncStatDoNoSpoofing  OBJECT-TYPE
    SYNTAX      OCTET STRING
    MAX-ACCESS  read-only
    STATUS      current
    DESCRIPTION
"
synchronization status for DoNoSpoofing
-1 - DoNoSpoofing could not be synchronized
 0 - synchronization not configured
 1 - out of sync - running master mode
 2 - in sync - running  mastermode
 3 - in sync - running slave mode
 4 - in sync - running master mode (wait to reach state 2)
"
    ::= {DoNoSpoofing 5}

syncStatStrDoNoSpoofing  OBJECT-TYPE
    SYNTAX      OCTET STRING
    MAX-ACCESS  read-only
    STATUS      current
    DESCRIPTION
"
synchronization status line from file assp_sync.cfg for DoNoSpoofing
 0 - synchronization not configured
 1 - out of sync - running master mode
 2 - in sync - running  mastermode
 3 - in sync - running slave mode
 4 - in sync - running master mode (wait to reach state 2)
"
    ::= {DoNoSpoofing 6}

noSpoofingCheckIP  OBJECT-TYPE
    SYNTAX      OCTET STRING
    MAX-ACCESS  read-write
    STATUS      current
    DESCRIPTION
"
Enter IP's that you don't want to be checked for spoofing. For example:145.145.145.145|145.146.
"
    REFERENCE "Don't do Spoofing Check for these IP's*"
    DEFVAL { "" }
    ::= {ValidateSender 177}

syncStatnoSpoofingCheckIP  OBJECT-TYPE
    SYNTAX      OCTET STRING
    MAX-ACCESS  read-only
    STATUS      current
    DESCRIPTION
"
synchronization status for noSpoofingCheckIP
-1 - noSpoofingCheckIP could not be synchronized
 0 - synchronization not configured
 1 - out of sync - running master mode
 2 - in sync - running  mastermode
 3 - in sync - running slave mode
 4 - in sync - running master mode (wait to reach state 2)
"
    ::= {noSpoofingCheckIP 5}

syncStatStrnoSpoofingCheckIP  OBJECT-TYPE
    SYNTAX      OCTET STRING
    MAX-ACCESS  read-only
    STATUS      current
    DESCRIPTION
"
synchronization status line from file assp_sync.cfg for noSpoofingCheckIP
 0 - synchronization not configured
 1 - out of sync - running master mode
 2 - in sync - running  mastermode
 3 - in sync - running slave mode
 4 - in sync - running master mode (wait to reach state 2)
"
    ::= {noSpoofingCheckIP 6}

noSpoofingCheckDomain  OBJECT-TYPE
    SYNTAX      OCTET STRING
    MAX-ACCESS  read-write
    STATUS      current
    DESCRIPTION
"
Accepts specific addresses (user@example.com), user parts (user) or entire domains (@example.com). Wildcards are supported (fribo*@example.com).
"
    REFERENCE "Don't do Spoofing Check for these Addresses/Domains*"
    DEFVAL { "" }
    ::= {ValidateSender 178}

syncStatnoSpoofingCheckDomain  OBJECT-TYPE
    SYNTAX      OCTET STRING
    MAX-ACCESS  read-only
    STATUS      current
    DESCRIPTION
"
synchronization status for noSpoofingCheckDomain
-1 - noSpoofingCheckDomain could not be synchronized
 0 - synchronization not configured
 1 - out of sync - running master mode
 2 - in sync - running  mastermode
 3 - in sync - running slave mode
 4 - in sync - running master mode (wait to reach state 2)
"
    ::= {noSpoofingCheckDomain 5}

syncStatStrnoSpoofingCheckDomain  OBJECT-TYPE
    SYNTAX      OCTET STRING
    MAX-ACCESS  read-only
    STATUS      current
    DESCRIPTION
"
synchronization status line from file assp_sync.cfg for noSpoofingCheckDomain
 0 - synchronization not configured
 1 - out of sync - running master mode
 2 - in sync - running  mastermode
 3 - in sync - running slave mode
 4 - in sync - running master mode (wait to reach state 2)
"
    ::= {noSpoofingCheckDomain 6}

DoReversed  OBJECT-TYPE
    SYNTAX      OCTET STRING
    MAX-ACCESS  read-write
    STATUS      current
    DESCRIPTION
"
If activated, each sender IP is checked for a PTR record. This requires an installed  module in PERL.
"
    REFERENCE "Reversed Lookup"
    DEFVAL { "3" }
    ::= {ValidateSender 180}

syncStatDoReversed  OBJECT-TYPE
    SYNTAX      OCTET STRING
    MAX-ACCESS  read-only
    STATUS      current
    DESCRIPTION
"
synchronization status for DoReversed
-1 - DoReversed could not be synchronized
 0 - synchronization not configured
 1 - out of sync - running master mode
 2 - in sync - running  mastermode
 3 - in sync - running slave mode
 4 - in sync - running master mode (wait to reach state 2)
"
    ::= {DoReversed 5}

syncStatStrDoReversed  OBJECT-TYPE
    SYNTAX      OCTET STRING
    MAX-ACCESS  read-only
    STATUS      current
    DESCRIPTION
"
synchronization status line from file assp_sync.cfg for DoReversed
 0 - synchronization not configured
 1 - out of sync - running master mode
 2 - in sync - running  mastermode
 3 - in sync - running slave mode
 4 - in sync - running master mode (wait to reach state 2)
"
    ::= {DoReversed 6}

DoReversedWL  OBJECT-TYPE
    SYNTAX      OCTET STRING
    MAX-ACCESS  read-write
    STATUS      current
    DESCRIPTION
"
Do reversed lookup for whitelisted addresses.
"
    REFERENCE "Do Reversed Lookup for Whitelisted"
    DEFVAL { "1" }
    ::= {ValidateSender 181}

syncStatDoReversedWL  OBJECT-TYPE
    SYNTAX      OCTET STRING
    MAX-ACCESS  read-only
    STATUS      current
    DESCRIPTION
"
synchronization status for DoReversedWL
-1 - DoReversedWL could not be synchronized
 0 - synchronization not configured
 1 - out of sync - running master mode
 2 - in sync - running  mastermode
 3 - in sync - running slave mode
 4 - in sync - running master mode (wait to reach state 2)
"
    ::= {DoReversedWL 5}

syncStatStrDoReversedWL  OBJECT-TYPE
    SYNTAX      OCTET STRING
    MAX-ACCESS  read-only
    STATUS      current
    DESCRIPTION
"
synchronization status line from file assp_sync.cfg for DoReversedWL
 0 - synchronization not configured
 1 - out of sync - running master mode
 2 - in sync - running  mastermode
 3 - in sync - running slave mode
 4 - in sync - running master mode (wait to reach state 2)
"
    ::= {DoReversedWL 6}

DoReversedNP  OBJECT-TYPE
    SYNTAX      OCTET STRING
    MAX-ACCESS  read-write
    STATUS      current
    DESCRIPTION
"
Do reversed lookup for noprocessing addresses.
"
    REFERENCE "Do Reversed Lookup for Noprocessing"
    DEFVAL { "1" }
    ::= {ValidateSender 182}

syncStatDoReversedNP  OBJECT-TYPE
    SYNTAX      OCTET STRING
    MAX-ACCESS  read-only
    STATUS      current
    DESCRIPTION
"
synchronization status for DoReversedNP
-1 - DoReversedNP could not be synchronized
 0 - synchronization not configured
 1 - out of sync - running master mode
 2 - in sync - running  mastermode
 3 - in sync - running slave mode
 4 - in sync - running master mode (wait to reach state 2)
"
    ::= {DoReversedNP 5}

syncStatStrDoReversedNP  OBJECT-TYPE
    SYNTAX      OCTET STRING
    MAX-ACCESS  read-only
    STATUS      current
    DESCRIPTION
"
synchronization status line from file assp_sync.cfg for DoReversedNP
 0 - synchronization not configured
 1 - out of sync - running master mode
 2 - in sync - running  mastermode
 3 - in sync - running slave mode
 4 - in sync - running master mode (wait to reach state 2)
"
    ::= {DoReversedNP 6}

DoInvalidPTR  OBJECT-TYPE
    SYNTAX      OCTET STRING
    MAX-ACCESS  read-write
    STATUS      current
    DESCRIPTION
"
If activated - and Reversed Lookup is activated -, the PTR-FQDN record is checked against the Regex. This requires an installed  module in PERL.
"
    REFERENCE "Reversed Lookup FQDN"
    DEFVAL { "3" }
    ::= {ValidateSender 183}

syncStatDoInvalidPTR  OBJECT-TYPE
    SYNTAX      OCTET STRING
    MAX-ACCESS  read-only
    STATUS      current
    DESCRIPTION
"
synchronization status for DoInvalidPTR
-1 - DoInvalidPTR could not be synchronized
 0 - synchronization not configured
 1 - out of sync - running master mode
 2 - in sync - running  mastermode
 3 - in sync - running slave mode
 4 - in sync - running master mode (wait to reach state 2)
"
    ::= {DoInvalidPTR 5}

syncStatStrDoInvalidPTR  OBJECT-TYPE
    SYNTAX      OCTET STRING
    MAX-ACCESS  read-only
    STATUS      current
    DESCRIPTION
"
synchronization status line from file assp_sync.cfg for DoInvalidPTR
 0 - synchronization not configured
 1 - out of sync - running master mode
 2 - in sync - running  mastermode
 3 - in sync - running slave mode
 4 - in sync - running master mode (wait to reach state 2)
"
    ::= {DoInvalidPTR 6}

invalidPTRRe  OBJECT-TYPE
    SYNTAX      OCTET STRING
    MAX-ACCESS  read-write
    STATUS      current
    DESCRIPTION
"
Validate Format PTR will check PTR records for this. 
  For example:  ^\d+\.\d+\.\d+\.\d+$|^[^\.]+\.?$ or file:files/invalidptr.txt
"
    REFERENCE "Regular Expression to Invalidate Format of PTR**"
    DEFVAL { "file:files/invalidptr.txt" }
    ::= {ValidateSender 184}

syncStatinvalidPTRRe  OBJECT-TYPE
    SYNTAX      OCTET STRING
    MAX-ACCESS  read-only
    STATUS      current
    DESCRIPTION
"
synchronization status for invalidPTRRe
-1 - invalidPTRRe could not be synchronized
 0 - synchronization not configured
 1 - out of sync - running master mode
 2 - in sync - running  mastermode
 3 - in sync - running slave mode
 4 - in sync - running master mode (wait to reach state 2)
"
    ::= {invalidPTRRe 5}

syncStatStrinvalidPTRRe  OBJECT-TYPE
    SYNTAX      OCTET STRING
    MAX-ACCESS  read-only
    STATUS      current
    DESCRIPTION
"
synchronization status line from file assp_sync.cfg for invalidPTRRe
 0 - synchronization not configured
 1 - out of sync - running master mode
 2 - in sync - running  mastermode
 3 - in sync - running slave mode
 4 - in sync - running master mode (wait to reach state 2)
"
    ::= {invalidPTRRe 6}

validPTRRe  OBJECT-TYPE
    SYNTAX      OCTET STRING
    MAX-ACCESS  read-write
    STATUS      current
    DESCRIPTION
"
Validate Format PTR will check PTR records for this. 
  For example:  static or file:files/validptr.txt
"
    REFERENCE "Regular Expression to Validate Format of PTR*"
    DEFVAL { "file:files/validptr.txt" }
    ::= {ValidateSender 185}

syncStatvalidPTRRe  OBJECT-TYPE
    SYNTAX      OCTET STRING
    MAX-ACCESS  read-only
    STATUS      current
    DESCRIPTION
"
synchronization status for validPTRRe
-1 - validPTRRe could not be synchronized
 0 - synchronization not configured
 1 - out of sync - running master mode
 2 - in sync - running  mastermode
 3 - in sync - running slave mode
 4 - in sync - running master mode (wait to reach state 2)
"
    ::= {validPTRRe 5}

syncStatStrvalidPTRRe  OBJECT-TYPE
    SYNTAX      OCTET STRING
    MAX-ACCESS  read-only
    STATUS      current
    DESCRIPTION
"
synchronization status line from file assp_sync.cfg for validPTRRe
 0 - synchronization not configured
 1 - out of sync - running master mode
 2 - in sync - running  mastermode
 3 - in sync - running slave mode
 4 - in sync - running master mode (wait to reach state 2)
"
    ::= {validPTRRe 6}

PTRCacheInterval  OBJECT-TYPE
    SYNTAX      OCTET STRING
    MAX-ACCESS  read-write
    STATUS      current
    DESCRIPTION
"
IP's in cache will be removed after this interval in days. 0 will disable the cache. 
"
    REFERENCE "Reversed Lookup Cache Refresh Interval"
    DEFVAL { "7" }
    ::= {ValidateSender 186}

syncStatPTRCacheInterval  OBJECT-TYPE
    SYNTAX      OCTET STRING
    MAX-ACCESS  read-only
    STATUS      current
    DESCRIPTION
"
synchronization status for PTRCacheInterval
-1 - PTRCacheInterval could not be synchronized
 0 - synchronization not configured
 1 - out of sync - running master mode
 2 - in sync - running  mastermode
 3 - in sync - running slave mode
 4 - in sync - running master mode (wait to reach state 2)
"
    ::= {PTRCacheInterval 5}

syncStatStrPTRCacheInterval  OBJECT-TYPE
    SYNTAX      OCTET STRING
    MAX-ACCESS  read-only
    STATUS      current
    DESCRIPTION
"
synchronization status line from file assp_sync.cfg for PTRCacheInterval
 0 - synchronization not configured
 1 - out of sync - running master mode
 2 - in sync - running  mastermode
 3 - in sync - running slave mode
 4 - in sync - running master mode (wait to reach state 2)
"
    ::= {PTRCacheInterval 6}

DoDomainCheck  OBJECT-TYPE
    SYNTAX      OCTET STRING
    MAX-ACCESS  read-write
    STATUS      current
    DESCRIPTION
"
If activated, the sender address and each address found in the following header lines (ReturnReceipt:, Return-Receipt-To:, Disposition-Notification-To:, Return-Path:, Reply-To:, Sender:, Errors-To:, List-...:) is checked for a valid MX or A record. Scoring is done for non existing MX record and non existing A record - a messages fails (block), if both records are not found.
"
    REFERENCE "Validate MX or A Record"
    DEFVAL { "3" }
    ::= {ValidateSender 187}

syncStatDoDomainCheck  OBJECT-TYPE
    SYNTAX      OCTET STRING
    MAX-ACCESS  read-only
    STATUS      current
    DESCRIPTION
"
synchronization status for DoDomainCheck
-1 - DoDomainCheck could not be synchronized
 0 - synchronization not configured
 1 - out of sync - running master mode
 2 - in sync - running  mastermode
 3 - in sync - running slave mode
 4 - in sync - running master mode (wait to reach state 2)
"
    ::= {DoDomainCheck 5}

syncStatStrDoDomainCheck  OBJECT-TYPE
    SYNTAX      OCTET STRING
    MAX-ACCESS  read-only
    STATUS      current
    DESCRIPTION
"
synchronization status line from file assp_sync.cfg for DoDomainCheck
 0 - synchronization not configured
 1 - out of sync - running master mode
 2 - in sync - running  mastermode
 3 - in sync - running slave mode
 4 - in sync - running master mode (wait to reach state 2)
"
    ::= {DoDomainCheck 6}

MXACacheInterval  OBJECT-TYPE
    SYNTAX      OCTET STRING
    MAX-ACCESS  read-write
    STATUS      current
    DESCRIPTION
"
IP's in cache will be removed after this interval in days. 0 will disable the cache.
"
    REFERENCE "Validate Domain MX Cache Refresh Interval"
    DEFVAL { "7" }
    ::= {ValidateSender 188}

syncStatMXACacheInterval  OBJECT-TYPE
    SYNTAX      OCTET STRING
    MAX-ACCESS  read-only
    STATUS      current
    DESCRIPTION
"
synchronization status for MXACacheInterval
-1 - MXACacheInterval could not be synchronized
 0 - synchronization not configured
 1 - out of sync - running master mode
 2 - in sync - running  mastermode
 3 - in sync - running slave mode
 4 - in sync - running master mode (wait to reach state 2)
"
    ::= {MXACacheInterval 5}

syncStatStrMXACacheInterval  OBJECT-TYPE
    SYNTAX      OCTET STRING
    MAX-ACCESS  read-only
    STATUS      current
    DESCRIPTION
"
synchronization status line from file assp_sync.cfg for MXACacheInterval
 0 - synchronization not configured
 1 - out of sync - running master mode
 2 - in sync - running  mastermode
 3 - in sync - running slave mode
 4 - in sync - running master mode (wait to reach state 2)
"
    ::= {MXACacheInterval 6}

DoNoFrom  OBJECT-TYPE
    SYNTAX      OCTET STRING
    MAX-ACCESS  read-write
    STATUS      current
    DESCRIPTION
"
Scoring is set with fromValencePB.
"
    REFERENCE "Check For Existing From Header "
    DEFVAL { "3" }
    ::= {ValidateSender 189}

syncStatDoNoFrom  OBJECT-TYPE
    SYNTAX      OCTET STRING
    MAX-ACCESS  read-only
    STATUS      current
    DESCRIPTION
"
synchronization status for DoNoFrom
-1 - DoNoFrom could not be synchronized
 0 - synchronization not configured
 1 - out of sync - running master mode
 2 - in sync - running  mastermode
 3 - in sync - running slave mode
 4 - in sync - running master mode (wait to reach state 2)
"
    ::= {DoNoFrom 5}

syncStatStrDoNoFrom  OBJECT-TYPE
    SYNTAX      OCTET STRING
    MAX-ACCESS  read-only
    STATUS      current
    DESCRIPTION
"
synchronization status line from file assp_sync.cfg for DoNoFrom
 0 - synchronization not configured
 1 - out of sync - running master mode
 2 - in sync - running  mastermode
 3 - in sync - running slave mode
 4 - in sync - running master mode (wait to reach state 2)
"
    ::= {DoNoFrom 6}

DoNoFromWL  OBJECT-TYPE
    SYNTAX      OCTET STRING
    MAX-ACCESS  read-write
    STATUS      current
    DESCRIPTION
"
Check for existing From Header for whitelisted addresses.
"
    REFERENCE "Do DoNoFrom for Whitelisted"
    DEFVAL { "1" }
    ::= {ValidateSender 190}

syncStatDoNoFromWL  OBJECT-TYPE
    SYNTAX      OCTET STRING
    MAX-ACCESS  read-only
    STATUS      current
    DESCRIPTION
"
synchronization status for DoNoFromWL
-1 - DoNoFromWL could not be synchronized
 0 - synchronization not configured
 1 - out of sync - running master mode
 2 - in sync - running  mastermode
 3 - in sync - running slave mode
 4 - in sync - running master mode (wait to reach state 2)
"
    ::= {DoNoFromWL 5}

syncStatStrDoNoFromWL  OBJECT-TYPE
    SYNTAX      OCTET STRING
    MAX-ACCESS  read-only
    STATUS      current
    DESCRIPTION
"
synchronization status line from file assp_sync.cfg for DoNoFromWL
 0 - synchronization not configured
 1 - out of sync - running master mode
 2 - in sync - running  mastermode
 3 - in sync - running slave mode
 4 - in sync - running master mode (wait to reach state 2)
"
    ::= {DoNoFromWL 6}

DoNoFromNP  OBJECT-TYPE
    SYNTAX      OCTET STRING
    MAX-ACCESS  read-write
    STATUS      current
    DESCRIPTION
"
Check for existing From Header for noprocessing addresses.
"
    REFERENCE "Do DoNoFrom for NoProcessing"
    DEFVAL { "1" }
    ::= {ValidateSender 191}

syncStatDoNoFromNP  OBJECT-TYPE
    SYNTAX      OCTET STRING
    MAX-ACCESS  read-only
    STATUS      current
    DESCRIPTION
"
synchronization status for DoNoFromNP
-1 - DoNoFromNP could not be synchronized
 0 - synchronization not configured
 1 - out of sync - running master mode
 2 - in sync - running  mastermode
 3 - in sync - running slave mode
 4 - in sync - running master mode (wait to reach state 2)
"
    ::= {DoNoFromNP 5}

syncStatStrDoNoFromNP  OBJECT-TYPE
    SYNTAX      OCTET STRING
    MAX-ACCESS  read-only
    STATUS      current
    DESCRIPTION
"
synchronization status line from file assp_sync.cfg for DoNoFromNP
 0 - synchronization not configured
 1 - out of sync - running master mode
 2 - in sync - running  mastermode
 3 - in sync - running slave mode
 4 - in sync - running master mode (wait to reach state 2)
"
    ::= {DoNoFromNP 6}

DoDKIM  OBJECT-TYPE
    SYNTAX      OCTET STRING
    MAX-ACCESS  read-write
    STATUS      current
    DESCRIPTION
"
If activated, DomainKeys Identified Mails are checked for the right signature and contents. All DKIM parameters belongs also to the old DomainKey specification. This requires an installed  module in PERL. In addition DKIM is used to process Domain-based Message Authentication, Reporting &amp; Conformance - described in  (DMARC requires also ValidateSPF to be enabled).
"
    REFERENCE "Validate DomainKeys Identified Mail "
    DEFVAL { "3" }
    ::= {ValidateSender 192}

syncStatDoDKIM  OBJECT-TYPE
    SYNTAX      OCTET STRING
    MAX-ACCESS  read-only
    STATUS      current
    DESCRIPTION
"
synchronization status for DoDKIM
-1 - DoDKIM could not be synchronized
 0 - synchronization not configured
 1 - out of sync - running master mode
 2 - in sync - running  mastermode
 3 - in sync - running slave mode
 4 - in sync - running master mode (wait to reach state 2)
"
    ::= {DoDKIM 5}

syncStatStrDoDKIM  OBJECT-TYPE
    SYNTAX      OCTET STRING
    MAX-ACCESS  read-only
    STATUS      current
    DESCRIPTION
"
synchronization status line from file assp_sync.cfg for DoDKIM
 0 - synchronization not configured
 1 - out of sync - running master mode
 2 - in sync - running  mastermode
 3 - in sync - running slave mode
 4 - in sync - running master mode (wait to reach state 2)
"
    ::= {DoDKIM 6}

DoStrictDKIM  OBJECT-TYPE
    SYNTAX      OCTET STRING
    MAX-ACCESS  read-write
    STATUS      current
    DESCRIPTION
"
The DKIM test will fail, if the mail was modified by a mailhop. In this case the from address, the from domain, the to domain, the DKIM-signature by itself and the prefix of the digest-verification are valid, only the lower digest value differs! This may happen, if a mailhop has modified any other headerfield like X-...! If unchecked a mail will only pass, if the author policy and sender policy are accept or neutral!
"
    REFERENCE "Validate DomainKeys Identified Mail strictly"
    DEFVAL { "0" }
    ::= {ValidateSender 193}

syncStatDoStrictDKIM  OBJECT-TYPE
    SYNTAX      OCTET STRING
    MAX-ACCESS  read-only
    STATUS      current
    DESCRIPTION
"
synchronization status for DoStrictDKIM
-1 - DoStrictDKIM could not be synchronized
 0 - synchronization not configured
 1 - out of sync - running master mode
 2 - in sync - running  mastermode
 3 - in sync - running slave mode
 4 - in sync - running master mode (wait to reach state 2)
"
    ::= {DoStrictDKIM 5}

syncStatStrDoStrictDKIM  OBJECT-TYPE
    SYNTAX      OCTET STRING
    MAX-ACCESS  read-only
    STATUS      current
    DESCRIPTION
"
synchronization status line from file assp_sync.cfg for DoStrictDKIM
 0 - synchronization not configured
 1 - out of sync - running master mode
 2 - in sync - running  mastermode
 3 - in sync - running slave mode
 4 - in sync - running master mode (wait to reach state 2)
"
    ::= {DoStrictDKIM 6}

noDKIMAddresses  OBJECT-TYPE
    SYNTAX      OCTET STRING
    MAX-ACCESS  read-write
    STATUS      current
    DESCRIPTION
"
Mail from any of these addresses will not be tagged and checked for DKIM. Accepts specific addresses (user@domain.com), user parts (user) or entire domains (@domain.com).
"
    REFERENCE "Do not any DKIM Check for this Addresses *"
    DEFVAL { "" }
    ::= {ValidateSender 194}

syncStatnoDKIMAddresses  OBJECT-TYPE
    SYNTAX      OCTET STRING
    MAX-ACCESS  read-only
    STATUS      current
    DESCRIPTION
"
synchronization status for noDKIMAddresses
-1 - noDKIMAddresses could not be synchronized
 0 - synchronization not configured
 1 - out of sync - running master mode
 2 - in sync - running  mastermode
 3 - in sync - running slave mode
 4 - in sync - running master mode (wait to reach state 2)
"
    ::= {noDKIMAddresses 5}

syncStatStrnoDKIMAddresses  OBJECT-TYPE
    SYNTAX      OCTET STRING
    MAX-ACCESS  read-only
    STATUS      current
    DESCRIPTION
"
synchronization status line from file assp_sync.cfg for noDKIMAddresses
 0 - synchronization not configured
 1 - out of sync - running master mode
 2 - in sync - running  mastermode
 3 - in sync - running slave mode
 4 - in sync - running master mode (wait to reach state 2)
"
    ::= {noDKIMAddresses 6}

noDKIMIP  OBJECT-TYPE
    SYNTAX      OCTET STRING
    MAX-ACCESS  read-write
    STATUS      current
    DESCRIPTION
"
Enter IP's that you want to exclude from DKIM check, separated by pipes (|).
"
    REFERENCE "Exclude these IP's from any DKIM Check*"
    DEFVAL { "" }
    ::= {ValidateSender 195}

syncStatnoDKIMIP  OBJECT-TYPE
    SYNTAX      OCTET STRING
    MAX-ACCESS  read-only
    STATUS      current
    DESCRIPTION
"
synchronization status for noDKIMIP
-1 - noDKIMIP could not be synchronized
 0 - synchronization not configured
 1 - out of sync - running master mode
 2 - in sync - running  mastermode
 3 - in sync - running slave mode
 4 - in sync - running master mode (wait to reach state 2)
"
    ::= {noDKIMIP 5}

syncStatStrnoDKIMIP  OBJECT-TYPE
    SYNTAX      OCTET STRING
    MAX-ACCESS  read-only
    STATUS      current
    DESCRIPTION
"
synchronization status line from file assp_sync.cfg for noDKIMIP
 0 - synchronization not configured
 1 - out of sync - running master mode
 2 - in sync - running  mastermode
 3 - in sync - running slave mode
 4 - in sync - running master mode (wait to reach state 2)
"
    ::= {noDKIMIP 6}

DKIMCacheInterval  OBJECT-TYPE
    SYNTAX      OCTET STRING
    MAX-ACCESS  read-write
    STATUS      current
    DESCRIPTION
"
domains's in cache will be removed after this interval in days. 0 will disable the cache.
  If activated a DKIM-pre-check will be done. If ASSP finds a DKIM-Signature in the mail header, it checks the DNS records of the sending domain for valid DKIM configurations and writes a record in to the DKIM-pre-check-cache, if it finds such configuration.
  If ASSP does not find a DKIM-Signature in the mail header, it also checks the DNS records of the sending domain for valid DKIM configurations. If it find such a configuration, the mail is considered spam, because it should have a DKIM-Signature.
  The next mail from a domain that is found in this cache, must have a DKIM-Signature to pass the DKIM-pre-check. How ever, some DNS records are wrong or inaccurate and will cause ASSP to block mails because of this - register such domains and/or IP's in noDKIMAddresses and/or noDKIMIP .
  
"
    REFERENCE "Validate DKIM-Pre-Check-Cache Refresh Interval"
    DEFVAL { "7" }
    ::= {ValidateSender 196}

syncStatDKIMCacheInterval  OBJECT-TYPE
    SYNTAX      OCTET STRING
    MAX-ACCESS  read-only
    STATUS      current
    DESCRIPTION
"
synchronization status for DKIMCacheInterval
-1 - DKIMCacheInterval could not be synchronized
 0 - synchronization not configured
 1 - out of sync - running master mode
 2 - in sync - running  mastermode
 3 - in sync - running slave mode
 4 - in sync - running master mode (wait to reach state 2)
"
    ::= {DKIMCacheInterval 5}

syncStatStrDKIMCacheInterval  OBJECT-TYPE
    SYNTAX      OCTET STRING
    MAX-ACCESS  read-only
    STATUS      current
    DESCRIPTION
"
synchronization status line from file assp_sync.cfg for DKIMCacheInterval
 0 - synchronization not configured
 1 - out of sync - running master mode
 2 - in sync - running  mastermode
 3 - in sync - running slave mode
 4 - in sync - running master mode (wait to reach state 2)
"
    ::= {DKIMCacheInterval 6}

AddDKIMHeader  OBJECT-TYPE
    SYNTAX      OCTET STRING
    MAX-ACCESS  read-write
    STATUS      current
    DESCRIPTION
"
Add X-Assp-DKIM header.
"
    REFERENCE "Add X-Assp-DKIM Header"
    DEFVAL { "1" }
    ::= {ValidateSender 197}

syncStatAddDKIMHeader  OBJECT-TYPE
    SYNTAX      OCTET STRING
    MAX-ACCESS  read-only
    STATUS      current
    DESCRIPTION
"
synchronization status for AddDKIMHeader
-1 - AddDKIMHeader could not be synchronized
 0 - synchronization not configured
 1 - out of sync - running master mode
 2 - in sync - running  mastermode
 3 - in sync - running slave mode
 4 - in sync - running master mode (wait to reach state 2)
"
    ::= {AddDKIMHeader 5}

syncStatStrAddDKIMHeader  OBJECT-TYPE
    SYNTAX      OCTET STRING
    MAX-ACCESS  read-only
    STATUS      current
    DESCRIPTION
"
synchronization status line from file assp_sync.cfg for AddDKIMHeader
 0 - synchronization not configured
 1 - out of sync - running master mode
 2 - in sync - running  mastermode
 3 - in sync - running slave mode
 4 - in sync - running master mode (wait to reach state 2)
"
    ::= {AddDKIMHeader 6}

SenderInvalidError  OBJECT-TYPE
    SYNTAX      OCTET STRING
    MAX-ACCESS  read-write
    STATUS      current
    DESCRIPTION
"
SMTP error message to reject invalid senders. The literal REASON is replaced by (missing MX, missing PTR, invalid Helo, invalid user) depending on the check.
  
  
"
    REFERENCE "Sender Validation Error"
    DEFVAL { "554 5.7.1 REASON ." }
    ::= {ValidateSender 198}

syncStatSenderInvalidError  OBJECT-TYPE
    SYNTAX      OCTET STRING
    MAX-ACCESS  read-only
    STATUS      current
    DESCRIPTION
"
synchronization status for SenderInvalidError
-1 - SenderInvalidError could not be synchronized
 0 - synchronization not configured
 1 - out of sync - running master mode
 2 - in sync - running  mastermode
 3 - in sync - running slave mode
 4 - in sync - running master mode (wait to reach state 2)
"
    ::= {SenderInvalidError 5}

syncStatStrSenderInvalidError  OBJECT-TYPE
    SYNTAX      OCTET STRING
    MAX-ACCESS  read-only
    STATUS      current
    DESCRIPTION
"
synchronization status line from file assp_sync.cfg for SenderInvalidError
 0 - synchronization not configured
 1 - out of sync - running master mode
 2 - in sync - running  mastermode
 3 - in sync - running slave mode
 4 - in sync - running master mode (wait to reach state 2)
"
    ::= {SenderInvalidError 6}

removeDispositionNotification  OBJECT-TYPE
    SYNTAX      OCTET STRING
    MAX-ACCESS  read-write
    STATUS      current
    DESCRIPTION
"
If set, all headers : 'ReturnReceipt: , Return-Receipt-To: and Disposition-Notification-To:' will be removed from not whitelisted and not noprocessing incoming mails. Select this to prevent unwanted whitelisting of spammers that request a Disposition Notification. An other way to prevent autowhitelisting because of an autoresponds is to use redRe .
"
    REFERENCE "Remove Disposition Notification Headers"
    DEFVAL { "" }
    ::= {ValidateSender 897}

syncStatremoveDispositionNotification  OBJECT-TYPE
    SYNTAX      OCTET STRING
    MAX-ACCESS  read-only
    STATUS      current
    DESCRIPTION
"
synchronization status for removeDispositionNotification
-1 - removeDispositionNotification could not be synchronized
 0 - synchronization not configured
 1 - out of sync - running master mode
 2 - in sync - running  mastermode
 3 - in sync - running slave mode
 4 - in sync - running master mode (wait to reach state 2)
"
    ::= {removeDispositionNotification 5}

syncStatStrremoveDispositionNotification  OBJECT-TYPE
    SYNTAX      OCTET STRING
    MAX-ACCESS  read-only
    STATUS      current
    DESCRIPTION
"
synchronization status line from file assp_sync.cfg for removeDispositionNotification
 0 - synchronization not configured
 1 - out of sync - running master mode
 2 - in sync - running  mastermode
 3 - in sync - running slave mode
 4 - in sync - running master mode (wait to reach state 2)
"
    ::= {removeDispositionNotification 6}

DoNoSpoofing4From  OBJECT-TYPE
    SYNTAX      OCTET STRING
    MAX-ACCESS  read-write
    STATUS      current
    DESCRIPTION
"
Do the NoSpoofing check also for header 'from:' addresses.
"
    REFERENCE "Do NoSpoofing for from:"
    DEFVAL { "" }
    ::= {ValidateSender 985}

syncStatDoNoSpoofing4From  OBJECT-TYPE
    SYNTAX      OCTET STRING
    MAX-ACCESS  read-only
    STATUS      current
    DESCRIPTION
"
synchronization status for DoNoSpoofing4From
-1 - DoNoSpoofing4From could not be synchronized
 0 - synchronization not configured
 1 - out of sync - running master mode
 2 - in sync - running  mastermode
 3 - in sync - running slave mode
 4 - in sync - running master mode (wait to reach state 2)
"
    ::= {DoNoSpoofing4From 5}

syncStatStrDoNoSpoofing4From  OBJECT-TYPE
    SYNTAX      OCTET STRING
    MAX-ACCESS  read-only
    STATUS      current
    DESCRIPTION
"
synchronization status line from file assp_sync.cfg for DoNoSpoofing4From
 0 - synchronization not configured
 1 - out of sync - running master mode
 2 - in sync - running  mastermode
 3 - in sync - running slave mode
 4 - in sync - running master mode (wait to reach state 2)
"
    ::= {DoNoSpoofing4From 6}

onlySpoofingCheckIP  OBJECT-TYPE
    SYNTAX      OCTET STRING
    MAX-ACCESS  read-write
    STATUS      current
    DESCRIPTION
"
Enter IP's that you want to be checked for spoofing. If this is set, ONLY these IP's will be checked. For example:145.145.145.145|145.146.
"
    REFERENCE "Do Spoofing Check ONLY for these IP's*"
    DEFVAL { "" }
    ::= {ValidateSender 990}

syncStatonlySpoofingCheckIP  OBJECT-TYPE
    SYNTAX      OCTET STRING
    MAX-ACCESS  read-only
    STATUS      current
    DESCRIPTION
"
synchronization status for onlySpoofingCheckIP
-1 - onlySpoofingCheckIP could not be synchronized
 0 - synchronization not configured
 1 - out of sync - running master mode
 2 - in sync - running  mastermode
 3 - in sync - running slave mode
 4 - in sync - running master mode (wait to reach state 2)
"
    ::= {onlySpoofingCheckIP 5}

syncStatStronlySpoofingCheckIP  OBJECT-TYPE
    SYNTAX      OCTET STRING
    MAX-ACCESS  read-only
    STATUS      current
    DESCRIPTION
"
synchronization status line from file assp_sync.cfg for onlySpoofingCheckIP
 0 - synchronization not configured
 1 - out of sync - running master mode
 2 - in sync - running  mastermode
 3 - in sync - running slave mode
 4 - in sync - running master mode (wait to reach state 2)
"
    ::= {onlySpoofingCheckIP 6}

onlySpoofingCheckDomain  OBJECT-TYPE
    SYNTAX      OCTET STRING
    MAX-ACCESS  read-write
    STATUS      current
    DESCRIPTION
"
Accepts specific addresses (user@example.com), user parts (user) or entire domains (@example.com). Wildcards are supported (fribo*@example.com). If set, ONLY these addresses/domains will be checked for spoofing.
"
    REFERENCE "Do Spoofing Check ONLY for these Addresses/Domains*"
    DEFVAL { "" }
    ::= {ValidateSender 991}

syncStatonlySpoofingCheckDomain  OBJECT-TYPE
    SYNTAX      OCTET STRING
    MAX-ACCESS  read-only
    STATUS      current
    DESCRIPTION
"
synchronization status for onlySpoofingCheckDomain
-1 - onlySpoofingCheckDomain could not be synchronized
 0 - synchronization not configured
 1 - out of sync - running master mode
 2 - in sync - running  mastermode
 3 - in sync - running slave mode
 4 - in sync - running master mode (wait to reach state 2)
"
    ::= {onlySpoofingCheckDomain 5}

syncStatStronlySpoofingCheckDomain  OBJECT-TYPE
    SYNTAX      OCTET STRING
    MAX-ACCESS  read-only
    STATUS      current
    DESCRIPTION
"
synchronization status line from file assp_sync.cfg for onlySpoofingCheckDomain
 0 - synchronization not configured
 1 - out of sync - running master mode
 2 - in sync - running  mastermode
 3 - in sync - running slave mode
 4 - in sync - running master mode (wait to reach state 2)
"
    ::= {onlySpoofingCheckDomain 6}

IPBlocking  OBJECT IDENTIFIER ::= {asspConfig 13}
DoDenySMTP  OBJECT-TYPE
    SYNTAX      OCTET STRING
    MAX-ACCESS  read-write
    STATUS      current
    DESCRIPTION
"
If activated, the IP is checked against (denySMTPConnectionsFrom) Deny Connections from these IP's.
"
    REFERENCE "Do Deny Connections from these IP's"
    DEFVAL { "1" }
    ::= {IPBlocking 199}

syncStatDoDenySMTP  OBJECT-TYPE
    SYNTAX      OCTET STRING
    MAX-ACCESS  read-only
    STATUS      current
    DESCRIPTION
"
synchronization status for DoDenySMTP
-1 - DoDenySMTP could not be synchronized
 0 - synchronization not configured
 1 - out of sync - running master mode
 2 - in sync - running  mastermode
 3 - in sync - running slave mode
 4 - in sync - running master mode (wait to reach state 2)
"
    ::= {DoDenySMTP 5}

syncStatStrDoDenySMTP  OBJECT-TYPE
    SYNTAX      OCTET STRING
    MAX-ACCESS  read-only
    STATUS      current
    DESCRIPTION
"
synchronization status line from file assp_sync.cfg for DoDenySMTP
 0 - synchronization not configured
 1 - out of sync - running master mode
 2 - in sync - running  mastermode
 3 - in sync - running slave mode
 4 - in sync - running master mode (wait to reach state 2)
"
    ::= {DoDenySMTP 6}

denySMTPConnectionsFrom  OBJECT-TYPE
    SYNTAX      OCTET STRING
    MAX-ACCESS  read-write
    STATUS      current
    DESCRIPTION
"
Manualy maintained list of IP's which should be blocked. IP's in noPB, noDelay, acceptAllMail, ispip, whiteListedIPs, noProcessingIPs, whitebox will pass. For example: file:files/blockip.txt.
  To define IP's only for specific email addresses or domains (recipients) you must use the file:... option
  An entry (line) may look as follows:
  145.146.0.0/16=>*@local.domain|user@mydomain|user2@*.mydomain # comment
  It is possible to define a predefined group on any or both sides of the '=>' separator, like:
  [ipgroup]=>[usergroup]|user@mydomain
  NOTICE: the following combination of two entries, will lead in to a user/domain based matching - the global entry will be ignored!
  145.146.0.0/16 # comment
  145.146.0.0/16=>*@local.domain|user@mydomain|user2@*.mydomain # comment
  If multiple user/domain based entries are defined for the same IP, only the last one will be used!
"
    REFERENCE "Deny Connections from these IP's*"
    DEFVAL { "" }
    ::= {IPBlocking 200}

syncStatdenySMTPConnectionsFrom  OBJECT-TYPE
    SYNTAX      OCTET STRING
    MAX-ACCESS  read-only
    STATUS      current
    DESCRIPTION
"
synchronization status for denySMTPConnectionsFrom
-1 - denySMTPConnectionsFrom could not be synchronized
 0 - synchronization not configured
 1 - out of sync - running master mode
 2 - in sync - running  mastermode
 3 - in sync - running slave mode
 4 - in sync - running master mode (wait to reach state 2)
"
    ::= {denySMTPConnectionsFrom 5}

syncStatStrdenySMTPConnectionsFrom  OBJECT-TYPE
    SYNTAX      OCTET STRING
    MAX-ACCESS  read-only
    STATUS      current
    DESCRIPTION
"
synchronization status line from file assp_sync.cfg for denySMTPConnectionsFrom
 0 - synchronization not configured
 1 - out of sync - running master mode
 2 - in sync - running  mastermode
 3 - in sync - running slave mode
 4 - in sync - running master mode (wait to reach state 2)
"
    ::= {denySMTPConnectionsFrom 6}

noBlockingIPs  OBJECT-TYPE
    SYNTAX      OCTET STRING
    MAX-ACCESS  read-write
    STATUS      current
    DESCRIPTION
"
Manualy maintained list of IP's which should not be blocked.  For example: 145.145.145.145|145.146.
  To define IP's only for specific email addresses or domains (recipients) you must use the file:... option
  An entry (line) may look as follows:
  145.146.0.0/16=>*@local.domain|user@mydomain|user2@*.mydomain # comment
  It is possible to define a predefined group on any or both sides of the '=>' separator, like:
  [ipgroup]=>[usergroup]|user@mydomain
  NOTICE: the following combination of two entries, will lead in to a user/domain based matching - the global entry will be ignored!
  145.146.0.0/16 # comment
  145.146.0.0/16=>*@local.domain|user@mydomain|user2@*.mydomain # comment
  If multiple user/domain based entries are defined for the same IP, only the last one will be used!
"
    REFERENCE "Do not block Connections from these IP's*"
    DEFVAL { "" }
    ::= {IPBlocking 201}

syncStatnoBlockingIPs  OBJECT-TYPE
    SYNTAX      OCTET STRING
    MAX-ACCESS  read-only
    STATUS      current
    DESCRIPTION
"
synchronization status for noBlockingIPs
-1 - noBlockingIPs could not be synchronized
 0 - synchronization not configured
 1 - out of sync - running master mode
 2 - in sync - running  mastermode
 3 - in sync - running slave mode
 4 - in sync - running master mode (wait to reach state 2)
"
    ::= {noBlockingIPs 5}

syncStatStrnoBlockingIPs  OBJECT-TYPE
    SYNTAX      OCTET STRING
    MAX-ACCESS  read-only
    STATUS      current
    DESCRIPTION
"
synchronization status line from file assp_sync.cfg for noBlockingIPs
 0 - synchronization not configured
 1 - out of sync - running master mode
 2 - in sync - running  mastermode
 3 - in sync - running slave mode
 4 - in sync - running master mode (wait to reach state 2)
"
    ::= {noBlockingIPs 6}

DoDenySMTPstrict  OBJECT-TYPE
    SYNTAX      OCTET STRING
    MAX-ACCESS  read-write
    STATUS      current
    DESCRIPTION
"
If activated, the IP is checked against ('denySMTPConnectionsFromAlways') Deny Connections from these IP's Strictly.
"
    REFERENCE "Do Deny Connections from these IP's Strictly"
    DEFVAL { "1" }
    ::= {IPBlocking 202}

syncStatDoDenySMTPstrict  OBJECT-TYPE
    SYNTAX      OCTET STRING
    MAX-ACCESS  read-only
    STATUS      current
    DESCRIPTION
"
synchronization status for DoDenySMTPstrict
-1 - DoDenySMTPstrict could not be synchronized
 0 - synchronization not configured
 1 - out of sync - running master mode
 2 - in sync - running  mastermode
 3 - in sync - running slave mode
 4 - in sync - running master mode (wait to reach state 2)
"
    ::= {DoDenySMTPstrict 5}

syncStatStrDoDenySMTPstrict  OBJECT-TYPE
    SYNTAX      OCTET STRING
    MAX-ACCESS  read-only
    STATUS      current
    DESCRIPTION
"
synchronization status line from file assp_sync.cfg for DoDenySMTPstrict
 0 - synchronization not configured
 1 - out of sync - running master mode
 2 - in sync - running  mastermode
 3 - in sync - running slave mode
 4 - in sync - running master mode (wait to reach state 2)
"
    ::= {DoDenySMTPstrict 6}

denySMTPConnectionsFromAlways  OBJECT-TYPE
    SYNTAX      OCTET STRING
    MAX-ACCESS  read-write
    STATUS      current
    DESCRIPTION
"
Manualy maintained list of IP's which should strictly be blocked after address verification and before body and header is downloaded. Contrary to denySMTPConnectionsFrom IP's in noDelay, acceptAllMail, ispip, whiteListedIPs, noProcessingIPs, whitebox will not pass if listed here.
"
    REFERENCE "Deny Connections from these IP's Strictly*"
    DEFVAL { "file:files/denyalways.txt" }
    ::= {IPBlocking 203}

syncStatdenySMTPConnectionsFromAlways  OBJECT-TYPE
    SYNTAX      OCTET STRING
    MAX-ACCESS  read-only
    STATUS      current
    DESCRIPTION
"
synchronization status for denySMTPConnectionsFromAlways
-1 - denySMTPConnectionsFromAlways could not be synchronized
 0 - synchronization not configured
 1 - out of sync - running master mode
 2 - in sync - running  mastermode
 3 - in sync - running slave mode
 4 - in sync - running master mode (wait to reach state 2)
"
    ::= {denySMTPConnectionsFromAlways 5}

syncStatStrdenySMTPConnectionsFromAlways  OBJECT-TYPE
    SYNTAX      OCTET STRING
    MAX-ACCESS  read-only
    STATUS      current
    DESCRIPTION
"
synchronization status line from file assp_sync.cfg for denySMTPConnectionsFromAlways
 0 - synchronization not configured
 1 - out of sync - running master mode
 2 - in sync - running  mastermode
 3 - in sync - running slave mode
 4 - in sync - running master mode (wait to reach state 2)
"
    ::= {denySMTPConnectionsFromAlways 6}

DoDropList  OBJECT-TYPE
    SYNTAX      OCTET STRING
    MAX-ACCESS  read-write
    STATUS      current
    DESCRIPTION
"
If activated, the IP is checked against the Droplist in addition to 'denySMTPConnectionsFromAlways' and/or 'denySMTPConnectionsFrom'. The droplist is downloaded if a new one is available and contains the Spamhaus DROP List. See 'http://www.spamhaus.org/drop/drop.lasso'.
"
    REFERENCE "Do also Deny Connections from these IP's"
    DEFVAL { "0" }
    ::= {IPBlocking 204}

syncStatDoDropList  OBJECT-TYPE
    SYNTAX      OCTET STRING
    MAX-ACCESS  read-only
    STATUS      current
    DESCRIPTION
"
synchronization status for DoDropList
-1 - DoDropList could not be synchronized
 0 - synchronization not configured
 1 - out of sync - running master mode
 2 - in sync - running  mastermode
 3 - in sync - running slave mode
 4 - in sync - running master mode (wait to reach state 2)
"
    ::= {DoDropList 5}

syncStatStrDoDropList  OBJECT-TYPE
    SYNTAX      OCTET STRING
    MAX-ACCESS  read-only
    STATUS      current
    DESCRIPTION
"
synchronization status line from file assp_sync.cfg for DoDropList
 0 - synchronization not configured
 1 - out of sync - running master mode
 2 - in sync - running  mastermode
 3 - in sync - running slave mode
 4 - in sync - running master mode (wait to reach state 2)
"
    ::= {DoDropList 6}

denySMTPstrictEarly  OBJECT-TYPE
    SYNTAX      OCTET STRING
    MAX-ACCESS  read-write
    STATUS      current
    DESCRIPTION
"
IP's in denySMTPConnectionsFromAlways will be denied right away.
"
    REFERENCE "Do Strictly Deny Connections Early"
    DEFVAL { "" }
    ::= {IPBlocking 205}

syncStatdenySMTPstrictEarly  OBJECT-TYPE
    SYNTAX      OCTET STRING
    MAX-ACCESS  read-only
    STATUS      current
    DESCRIPTION
"
synchronization status for denySMTPstrictEarly
-1 - denySMTPstrictEarly could not be synchronized
 0 - synchronization not configured
 1 - out of sync - running master mode
 2 - in sync - running  mastermode
 3 - in sync - running slave mode
 4 - in sync - running master mode (wait to reach state 2)
"
    ::= {denySMTPstrictEarly 5}

syncStatStrdenySMTPstrictEarly  OBJECT-TYPE
    SYNTAX      OCTET STRING
    MAX-ACCESS  read-only
    STATUS      current
    DESCRIPTION
"
synchronization status line from file assp_sync.cfg for denySMTPstrictEarly
 0 - synchronization not configured
 1 - out of sync - running master mode
 2 - in sync - running  mastermode
 3 - in sync - running slave mode
 4 - in sync - running master mode (wait to reach state 2)
"
    ::= {denySMTPstrictEarly 6}

DoFrequencyIP  OBJECT-TYPE
    SYNTAX      OCTET STRING
    MAX-ACCESS  read-write
    STATUS      current
    DESCRIPTION
"

"
    REFERENCE "Check Frequency - Maximum Connections Per IP"
    DEFVAL { "0" }
    ::= {IPBlocking 206}

syncStatDoFrequencyIP  OBJECT-TYPE
    SYNTAX      OCTET STRING
    MAX-ACCESS  read-only
    STATUS      current
    DESCRIPTION
"
synchronization status for DoFrequencyIP
-1 - DoFrequencyIP could not be synchronized
 0 - synchronization not configured
 1 - out of sync - running master mode
 2 - in sync - running  mastermode
 3 - in sync - running slave mode
 4 - in sync - running master mode (wait to reach state 2)
"
    ::= {DoFrequencyIP 5}

syncStatStrDoFrequencyIP  OBJECT-TYPE
    SYNTAX      OCTET STRING
    MAX-ACCESS  read-only
    STATUS      current
    DESCRIPTION
"
synchronization status line from file assp_sync.cfg for DoFrequencyIP
 0 - synchronization not configured
 1 - out of sync - running master mode
 2 - in sync - running  mastermode
 3 - in sync - running slave mode
 4 - in sync - running master mode (wait to reach state 2)
"
    ::= {DoFrequencyIP 6}

maxSMTPipConnects  OBJECT-TYPE
    SYNTAX      OCTET STRING
    MAX-ACCESS  read-write
    STATUS      current
    DESCRIPTION
"
The maximum number of SMTP connections an IP Address can make during the . If a server makes more than this many connections to ASSP within the (maxSMTPipDuration) IP Address Frequency Duration it will be banned from future connections until the (maxSMTPipExpiration) IP Address Frequency Expiration is reached. This can be used to prevent server overloading and DoS attacks. 10 connections are typically enough. If left blank or 0, there is no limit imposed by ASSP. IP's in noPB, noDelay, acceptAllMail, ispip, whiteListedIPs, noProcessingIPs, PB-whitebox are excluded from SMTP session limiting, whitelisted and noprocessing addresses are honored
"
    REFERENCE "Maximum Frequency of Connections Per IP "
    DEFVAL { "10" }
    ::= {IPBlocking 207}

syncStatmaxSMTPipConnects  OBJECT-TYPE
    SYNTAX      OCTET STRING
    MAX-ACCESS  read-only
    STATUS      current
    DESCRIPTION
"
synchronization status for maxSMTPipConnects
-1 - maxSMTPipConnects could not be synchronized
 0 - synchronization not configured
 1 - out of sync - running master mode
 2 - in sync - running  mastermode
 3 - in sync - running slave mode
 4 - in sync - running master mode (wait to reach state 2)
"
    ::= {maxSMTPipConnects 5}

syncStatStrmaxSMTPipConnects  OBJECT-TYPE
    SYNTAX      OCTET STRING
    MAX-ACCESS  read-only
    STATUS      current
    DESCRIPTION
"
synchronization status line from file assp_sync.cfg for maxSMTPipConnects
 0 - synchronization not configured
 1 - out of sync - running master mode
 2 - in sync - running  mastermode
 3 - in sync - running slave mode
 4 - in sync - running master mode (wait to reach state 2)
"
    ::= {maxSMTPipConnects 6}

maxSMTPipDuration  OBJECT-TYPE
    SYNTAX      OCTET STRING
    MAX-ACCESS  read-write
    STATUS      current
    DESCRIPTION
"
The window (in seconds) during which the (maxSMTPipConnects) IP Frequency (see above for more details) will be scrutinized for each IP. The default is 90 seconds.
"
    REFERENCE "Maximum Frequency of Connections Per IP Duration"
    DEFVAL { "90" }
    ::= {IPBlocking 208}

syncStatmaxSMTPipDuration  OBJECT-TYPE
    SYNTAX      OCTET STRING
    MAX-ACCESS  read-only
    STATUS      current
    DESCRIPTION
"
synchronization status for maxSMTPipDuration
-1 - maxSMTPipDuration could not be synchronized
 0 - synchronization not configured
 1 - out of sync - running master mode
 2 - in sync - running  mastermode
 3 - in sync - running slave mode
 4 - in sync - running master mode (wait to reach state 2)
"
    ::= {maxSMTPipDuration 5}

syncStatStrmaxSMTPipDuration  OBJECT-TYPE
    SYNTAX      OCTET STRING
    MAX-ACCESS  read-only
    STATUS      current
    DESCRIPTION
"
synchronization status line from file assp_sync.cfg for maxSMTPipDuration
 0 - synchronization not configured
 1 - out of sync - running master mode
 2 - in sync - running  mastermode
 3 - in sync - running slave mode
 4 - in sync - running master mode (wait to reach state 2)
"
    ::= {maxSMTPipDuration 6}

maxSMTPipExpiration  OBJECT-TYPE
    SYNTAX      OCTET STRING
    MAX-ACCESS  read-write
    STATUS      current
    DESCRIPTION
"
The number of seconds that must pass before an IP address blocked by the (maxSMTPipConnects) IP Address Frequency setting is allowed to connect again. The default is 7200 (seconds) .
"
    REFERENCE "Expiration of Maximum Frequency"
    DEFVAL { "7200" }
    ::= {IPBlocking 209}

syncStatmaxSMTPipExpiration  OBJECT-TYPE
    SYNTAX      OCTET STRING
    MAX-ACCESS  read-only
    STATUS      current
    DESCRIPTION
"
synchronization status for maxSMTPipExpiration
-1 - maxSMTPipExpiration could not be synchronized
 0 - synchronization not configured
 1 - out of sync - running master mode
 2 - in sync - running  mastermode
 3 - in sync - running slave mode
 4 - in sync - running master mode (wait to reach state 2)
"
    ::= {maxSMTPipExpiration 5}

syncStatStrmaxSMTPipExpiration  OBJECT-TYPE
    SYNTAX      OCTET STRING
    MAX-ACCESS  read-only
    STATUS      current
    DESCRIPTION
"
synchronization status line from file assp_sync.cfg for maxSMTPipExpiration
 0 - synchronization not configured
 1 - out of sync - running master mode
 2 - in sync - running  mastermode
 3 - in sync - running slave mode
 4 - in sync - running master mode (wait to reach state 2)
"
    ::= {maxSMTPipExpiration 6}

DoDomainIP  OBJECT-TYPE
    SYNTAX      OCTET STRING
    MAX-ACCESS  read-write
    STATUS      current
    DESCRIPTION
"
This check is skipped if the IP and domain have passed the SPF-check. If ValidateSPF is enabled and an IP/Domain reaches the maxSMTPdomainIP limit, the MaintThread starts a background SPF check to prevent blocking good mails in future.
"
    REFERENCE "Check Number of IP's Per Domain"
    DEFVAL { "0" }
    ::= {IPBlocking 210}

syncStatDoDomainIP  OBJECT-TYPE
    SYNTAX      OCTET STRING
    MAX-ACCESS  read-only
    STATUS      current
    DESCRIPTION
"
synchronization status for DoDomainIP
-1 - DoDomainIP could not be synchronized
 0 - synchronization not configured
 1 - out of sync - running master mode
 2 - in sync - running  mastermode
 3 - in sync - running slave mode
 4 - in sync - running master mode (wait to reach state 2)
"
    ::= {DoDomainIP 5}

syncStatStrDoDomainIP  OBJECT-TYPE
    SYNTAX      OCTET STRING
    MAX-ACCESS  read-only
    STATUS      current
    DESCRIPTION
"
synchronization status line from file assp_sync.cfg for DoDomainIP
 0 - synchronization not configured
 1 - out of sync - running master mode
 2 - in sync - running  mastermode
 3 - in sync - running slave mode
 4 - in sync - running master mode (wait to reach state 2)
"
    ::= {DoDomainIP 6}

maxSMTPdomainIP  OBJECT-TYPE
    SYNTAX      OCTET STRING
    MAX-ACCESS  read-write
    STATUS      current
    DESCRIPTION
"
The number of IP(subnet) switches a domain may have during the (maxSMTPdomainIPExpiration) Limit Different IP's Per Domain Expiration. If a domain switches more often than this it will be banned from future connections until the Expiration is reached. This can be used to prevent server overloading and DoS attacks. 10 connections are typically enough. If left blank or 0, there is no limit imposed by ASSP. IP's in noPB, noDelay, acceptAllMail, ispip, whiteListedIPs, noProcessingIPs, PB-whitebox are excluded, whitelisted and noprocessing addresses are honored.
"
    REFERENCE "Limit Number of IP's  Per Domain"
    DEFVAL { "10" }
    ::= {IPBlocking 211}

syncStatmaxSMTPdomainIP  OBJECT-TYPE
    SYNTAX      OCTET STRING
    MAX-ACCESS  read-only
    STATUS      current
    DESCRIPTION
"
synchronization status for maxSMTPdomainIP
-1 - maxSMTPdomainIP could not be synchronized
 0 - synchronization not configured
 1 - out of sync - running master mode
 2 - in sync - running  mastermode
 3 - in sync - running slave mode
 4 - in sync - running master mode (wait to reach state 2)
"
    ::= {maxSMTPdomainIP 5}

syncStatStrmaxSMTPdomainIP  OBJECT-TYPE
    SYNTAX      OCTET STRING
    MAX-ACCESS  read-only
    STATUS      current
    DESCRIPTION
"
synchronization status line from file assp_sync.cfg for maxSMTPdomainIP
 0 - synchronization not configured
 1 - out of sync - running master mode
 2 - in sync - running  mastermode
 3 - in sync - running slave mode
 4 - in sync - running master mode (wait to reach state 2)
"
    ::= {maxSMTPdomainIP 6}

maxSMTPdomainIPExpiration  OBJECT-TYPE
    SYNTAX      OCTET STRING
    MAX-ACCESS  read-write
    STATUS      current
    DESCRIPTION
"
The number of seconds that must pass before a domain blocked by the (maxSMTPdomainIP) Limit Subnet IP's Per Domain setting (see above for more details) is allowed to connect again. The default is 7200 (seconds).
"
    REFERENCE "Expiration of Limit Number"
    DEFVAL { "7200" }
    ::= {IPBlocking 212}

syncStatmaxSMTPdomainIPExpiration  OBJECT-TYPE
    SYNTAX      OCTET STRING
    MAX-ACCESS  read-only
    STATUS      current
    DESCRIPTION
"
synchronization status for maxSMTPdomainIPExpiration
-1 - maxSMTPdomainIPExpiration could not be synchronized
 0 - synchronization not configured
 1 - out of sync - running master mode
 2 - in sync - running  mastermode
 3 - in sync - running slave mode
 4 - in sync - running master mode (wait to reach state 2)
"
    ::= {maxSMTPdomainIPExpiration 5}

syncStatStrmaxSMTPdomainIPExpiration  OBJECT-TYPE
    SYNTAX      OCTET STRING
    MAX-ACCESS  read-only
    STATUS      current
    DESCRIPTION
"
synchronization status line from file assp_sync.cfg for maxSMTPdomainIPExpiration
 0 - synchronization not configured
 1 - out of sync - running master mode
 2 - in sync - running  mastermode
 3 - in sync - running slave mode
 4 - in sync - running master mode (wait to reach state 2)
"
    ::= {maxSMTPdomainIPExpiration 6}

maxSMTPdomainIPWL  OBJECT-TYPE
    SYNTAX      OCTET STRING
    MAX-ACCESS  read-write
    STATUS      current
    DESCRIPTION
"
This prevents specific domains from limiting. For example: yahoo.com|hotmail.*.com|gmail.com
  
  
"
    REFERENCE "Do Not Limit Different IP's For These Domains*"
    DEFVAL { "gmx.de|t-online.de|yahoo.com|hotmail.com|gmail.com" }
    ::= {IPBlocking 213}

syncStatmaxSMTPdomainIPWL  OBJECT-TYPE
    SYNTAX      OCTET STRING
    MAX-ACCESS  read-only
    STATUS      current
    DESCRIPTION
"
synchronization status for maxSMTPdomainIPWL
-1 - maxSMTPdomainIPWL could not be synchronized
 0 - synchronization not configured
 1 - out of sync - running master mode
 2 - in sync - running  mastermode
 3 - in sync - running slave mode
 4 - in sync - running master mode (wait to reach state 2)
"
    ::= {maxSMTPdomainIPWL 5}

syncStatStrmaxSMTPdomainIPWL  OBJECT-TYPE
    SYNTAX      OCTET STRING
    MAX-ACCESS  read-only
    STATUS      current
    DESCRIPTION
"
synchronization status line from file assp_sync.cfg for maxSMTPdomainIPWL
 0 - synchronization not configured
 1 - out of sync - running master mode
 2 - in sync - running  mastermode
 3 - in sync - running slave mode
 4 - in sync - running master mode (wait to reach state 2)
"
    ::= {maxSMTPdomainIPWL 6}

DelayIP  OBJECT-TYPE
    SYNTAX      OCTET STRING
    MAX-ACCESS  read-write
    STATUS      current
    DESCRIPTION
"
Enable simple delaying for IP's in black penaltybox with totalscore above this value. An value of zero or empty disables this feature.
"
    REFERENCE "Simple IP Greylisting"
    DEFVAL { "" }
    ::= {IPBlocking 932}

syncStatDelayIP  OBJECT-TYPE
    SYNTAX      OCTET STRING
    MAX-ACCESS  read-only
    STATUS      current
    DESCRIPTION
"
synchronization status for DelayIP
-1 - DelayIP could not be synchronized
 0 - synchronization not configured
 1 - out of sync - running master mode
 2 - in sync - running  mastermode
 3 - in sync - running slave mode
 4 - in sync - running master mode (wait to reach state 2)
"
    ::= {DelayIP 5}

syncStatStrDelayIP  OBJECT-TYPE
    SYNTAX      OCTET STRING
    MAX-ACCESS  read-only
    STATUS      current
    DESCRIPTION
"
synchronization status line from file assp_sync.cfg for DelayIP
 0 - synchronization not configured
 1 - out of sync - running master mode
 2 - in sync - running  mastermode
 3 - in sync - running slave mode
 4 - in sync - running master mode (wait to reach state 2)
"
    ::= {DelayIP 6}

DelayIPTime  OBJECT-TYPE
    SYNTAX      OCTET STRING
    MAX-ACCESS  read-write
    STATUS      current
    DESCRIPTION
"
Enter the number of minutes for which delivery, related with IP address of the sending host, is refused with a temporary failure. Default is 5 minutes.
"
    REFERENCE "Simple IP Greylisting Embargo Time"
    DEFVAL { "5" }
    ::= {IPBlocking 933}

syncStatDelayIPTime  OBJECT-TYPE
    SYNTAX      OCTET STRING
    MAX-ACCESS  read-only
    STATUS      current
    DESCRIPTION
"
synchronization status for DelayIPTime
-1 - DelayIPTime could not be synchronized
 0 - synchronization not configured
 1 - out of sync - running master mode
 2 - in sync - running  mastermode
 3 - in sync - running slave mode
 4 - in sync - running master mode (wait to reach state 2)
"
    ::= {DelayIPTime 5}

syncStatStrDelayIPTime  OBJECT-TYPE
    SYNTAX      OCTET STRING
    MAX-ACCESS  read-only
    STATUS      current
    DESCRIPTION
"
synchronization status line from file assp_sync.cfg for DelayIPTime
 0 - synchronization not configured
 1 - out of sync - running master mode
 2 - in sync - running  mastermode
 3 - in sync - running slave mode
 4 - in sync - running master mode (wait to reach state 2)
"
    ::= {DelayIPTime 6}

enhancedOriginIPDetect  OBJECT-TYPE
    SYNTAX      OCTET STRING
    MAX-ACCESS  read-write
    STATUS      current
    DESCRIPTION
"
If selected, ASSP will analyze the mail headers 'RECEIVED:' lines for IP's on the mail routing way to detect spam bots, that uses open relay or highjacked mail servers for mail delivery.
  Local and private IP's, and IP's listed in ispip, acceptAllMail, whiteListedIPs, noProcessingIPs, noDelay and noPB will be ingnored.
  The detected IP's will be additionally checked for IP-Blocking, DNSBL and IP-Frequency - the same way like the connected IP. These IP's are also additionally used for the maximum mail size calculation in MaxRealSizeAdr and MaxRealSizeExternalAdr.
"
    REFERENCE "Do an Enhanced Origin IP Address Detection in the Mail Header"
    DEFVAL { "1" }
    ::= {IPBlocking 959}

syncStatenhancedOriginIPDetect  OBJECT-TYPE
    SYNTAX      OCTET STRING
    MAX-ACCESS  read-only
    STATUS      current
    DESCRIPTION
"
synchronization status for enhancedOriginIPDetect
-1 - enhancedOriginIPDetect could not be synchronized
 0 - synchronization not configured
 1 - out of sync - running master mode
 2 - in sync - running  mastermode
 3 - in sync - running slave mode
 4 - in sync - running master mode (wait to reach state 2)
"
    ::= {enhancedOriginIPDetect 5}

syncStatStrenhancedOriginIPDetect  OBJECT-TYPE
    SYNTAX      OCTET STRING
    MAX-ACCESS  read-only
    STATUS      current
    DESCRIPTION
"
synchronization status line from file assp_sync.cfg for enhancedOriginIPDetect
 0 - synchronization not configured
 1 - out of sync - running master mode
 2 - in sync - running  mastermode
 3 - in sync - running slave mode
 4 - in sync - running master mode (wait to reach state 2)
"
    ::= {enhancedOriginIPDetect 6}

SenderBaseWhois  OBJECT IDENTIFIER ::= {asspConfig 14}
sbTestMode  OBJECT-TYPE
    SYNTAX      OCTET STRING
    MAX-ACCESS  read-write
    STATUS      current
    DESCRIPTION
"

"
    REFERENCE "SenderBase Testmode"
    DEFVAL { "" }
    ::= {SenderBaseWhois 214}

syncStatsbTestMode  OBJECT-TYPE
    SYNTAX      OCTET STRING
    MAX-ACCESS  read-only
    STATUS      current
    DESCRIPTION
"
synchronization status for sbTestMode
-1 - sbTestMode could not be synchronized
 0 - synchronization not configured
 1 - out of sync - running master mode
 2 - in sync - running  mastermode
 3 - in sync - running slave mode
 4 - in sync - running master mode (wait to reach state 2)
"
    ::= {sbTestMode 5}

syncStatStrsbTestMode  OBJECT-TYPE
    SYNTAX      OCTET STRING
    MAX-ACCESS  read-only
    STATUS      current
    DESCRIPTION
"
synchronization status line from file assp_sync.cfg for sbTestMode
 0 - synchronization not configured
 1 - out of sync - running master mode
 2 - in sync - running  mastermode
 3 - in sync - running slave mode
 4 - in sync - running master mode (wait to reach state 2)
"
    ::= {sbTestMode 6}

DoOrgWhiting  OBJECT-TYPE
    SYNTAX      OCTET STRING
    MAX-ACCESS  read-write
    STATUS      current
    DESCRIPTION
"
If activated, each sending IP address has its assigned organization looked up. Scoring is set with sworgValencePB.
"
    REFERENCE "Do Organization Whiting"
    DEFVAL { "1" }
    ::= {SenderBaseWhois 215}

syncStatDoOrgWhiting  OBJECT-TYPE
    SYNTAX      OCTET STRING
    MAX-ACCESS  read-only
    STATUS      current
    DESCRIPTION
"
synchronization status for DoOrgWhiting
-1 - DoOrgWhiting could not be synchronized
 0 - synchronization not configured
 1 - out of sync - running master mode
 2 - in sync - running  mastermode
 3 - in sync - running slave mode
 4 - in sync - running master mode (wait to reach state 2)
"
    ::= {DoOrgWhiting 5}

syncStatStrDoOrgWhiting  OBJECT-TYPE
    SYNTAX      OCTET STRING
    MAX-ACCESS  read-only
    STATUS      current
    DESCRIPTION
"
synchronization status line from file assp_sync.cfg for DoOrgWhiting
 0 - synchronization not configured
 1 - out of sync - running master mode
 2 - in sync - running  mastermode
 3 - in sync - running slave mode
 4 - in sync - running master mode (wait to reach state 2)
"
    ::= {DoOrgWhiting 6}

whiteSenderBase  OBJECT-TYPE
    SYNTAX      OCTET STRING
    MAX-ACCESS  read-write
    STATUS      current
    DESCRIPTION
"
If the organization or domain  in the  IP description matches this Perl regular expression the message will be considered non-spam. For example file:files/whiteorg.txt
"
    REFERENCE "Whitelisted Organizations and Domains in SenderBase**"
    DEFVAL { "file:files/whiteorg.txt" }
    ::= {SenderBaseWhois 216}

syncStatwhiteSenderBase  OBJECT-TYPE
    SYNTAX      OCTET STRING
    MAX-ACCESS  read-only
    STATUS      current
    DESCRIPTION
"
synchronization status for whiteSenderBase
-1 - whiteSenderBase could not be synchronized
 0 - synchronization not configured
 1 - out of sync - running master mode
 2 - in sync - running  mastermode
 3 - in sync - running slave mode
 4 - in sync - running master mode (wait to reach state 2)
"
    ::= {whiteSenderBase 5}

syncStatStrwhiteSenderBase  OBJECT-TYPE
    SYNTAX      OCTET STRING
    MAX-ACCESS  read-only
    STATUS      current
    DESCRIPTION
"
synchronization status line from file assp_sync.cfg for whiteSenderBase
 0 - synchronization not configured
 1 - out of sync - running master mode
 2 - in sync - running  mastermode
 3 - in sync - running slave mode
 4 - in sync - running master mode (wait to reach state 2)
"
    ::= {whiteSenderBase 6}

DoOrgBlocking  OBJECT-TYPE
    SYNTAX      OCTET STRING
    MAX-ACCESS  read-write
    STATUS      current
    DESCRIPTION
"
If activated, each sending IP address has its assigned organization looked up. Scoring is set with sborgValencePB, Testmode is set with sbTestMode.
"
    REFERENCE "Do Organization Blocking"
    DEFVAL { "2" }
    ::= {SenderBaseWhois 217}

syncStatDoOrgBlocking  OBJECT-TYPE
    SYNTAX      OCTET STRING
    MAX-ACCESS  read-only
    STATUS      current
    DESCRIPTION
"
synchronization status for DoOrgBlocking
-1 - DoOrgBlocking could not be synchronized
 0 - synchronization not configured
 1 - out of sync - running master mode
 2 - in sync - running  mastermode
 3 - in sync - running slave mode
 4 - in sync - running master mode (wait to reach state 2)
"
    ::= {DoOrgBlocking 5}

syncStatStrDoOrgBlocking  OBJECT-TYPE
    SYNTAX      OCTET STRING
    MAX-ACCESS  read-only
    STATUS      current
    DESCRIPTION
"
synchronization status line from file assp_sync.cfg for DoOrgBlocking
 0 - synchronization not configured
 1 - out of sync - running master mode
 2 - in sync - running  mastermode
 3 - in sync - running slave mode
 4 - in sync - running master mode (wait to reach state 2)
"
    ::= {DoOrgBlocking 6}

blackSenderBase  OBJECT-TYPE
    SYNTAX      OCTET STRING
    MAX-ACCESS  read-write
    STATUS      current
    DESCRIPTION
"
If the organization or domain in the  IP description matches this Perl regular expression the message will be considered spam.
"
    REFERENCE "Blacklisted Organizations and Domains in SenderBase**"
    DEFVAL { "" }
    ::= {SenderBaseWhois 218}

syncStatblackSenderBase  OBJECT-TYPE
    SYNTAX      OCTET STRING
    MAX-ACCESS  read-only
    STATUS      current
    DESCRIPTION
"
synchronization status for blackSenderBase
-1 - blackSenderBase could not be synchronized
 0 - synchronization not configured
 1 - out of sync - running master mode
 2 - in sync - running  mastermode
 3 - in sync - running slave mode
 4 - in sync - running master mode (wait to reach state 2)
"
    ::= {blackSenderBase 5}

syncStatStrblackSenderBase  OBJECT-TYPE
    SYNTAX      OCTET STRING
    MAX-ACCESS  read-only
    STATUS      current
    DESCRIPTION
"
synchronization status line from file assp_sync.cfg for blackSenderBase
 0 - synchronization not configured
 1 - out of sync - running master mode
 2 - in sync - running  mastermode
 3 - in sync - running slave mode
 4 - in sync - running master mode (wait to reach state 2)
"
    ::= {blackSenderBase 6}

DoCountryBlocking  OBJECT-TYPE
    SYNTAX      OCTET STRING
    MAX-ACCESS  read-write
    STATUS      current
    DESCRIPTION
"
If activated, each sending IP address has its assigned country looked up.
"
    REFERENCE "Do Country Blocking"
    DEFVAL { "2" }
    ::= {SenderBaseWhois 219}

syncStatDoCountryBlocking  OBJECT-TYPE
    SYNTAX      OCTET STRING
    MAX-ACCESS  read-only
    STATUS      current
    DESCRIPTION
"
synchronization status for DoCountryBlocking
-1 - DoCountryBlocking could not be synchronized
 0 - synchronization not configured
 1 - out of sync - running master mode
 2 - in sync - running  mastermode
 3 - in sync - running slave mode
 4 - in sync - running master mode (wait to reach state 2)
"
    ::= {DoCountryBlocking 5}

syncStatStrDoCountryBlocking  OBJECT-TYPE
    SYNTAX      OCTET STRING
    MAX-ACCESS  read-only
    STATUS      current
    DESCRIPTION
"
synchronization status line from file assp_sync.cfg for DoCountryBlocking
 0 - synchronization not configured
 1 - out of sync - running master mode
 2 - in sync - running  mastermode
 3 - in sync - running slave mode
 4 - in sync - running master mode (wait to reach state 2)
"
    ::= {DoCountryBlocking 6}

CountryCodeBlockedRe  OBJECT-TYPE
    SYNTAX      OCTET STRING
    MAX-ACCESS  read-write
    STATUS      current
    DESCRIPTION
"
Messages from IP's based in these countries will be blocked. For example: CN|KR|RU|JP|TR|TH|PL|LT|CL|RO|UA|GR|HU|SA|IN|IE|PT|MD|PE|CZ|TW|BR|CL. 'all' will block all foreign countrycodes which are not in 'Suspicious Country Codes' or 'Ignore Country Codes'. See: . 
"
    REFERENCE "Blocked Country Codes**"
    DEFVAL { "CN|KR|RU|JP|TR|TH|PL|LT|CL|RO|UA|GR|HU|SA|IN|GB|IE|PT|MD|PE|CZ|TW|BR|CL" }
    ::= {SenderBaseWhois 220}

syncStatCountryCodeBlockedRe  OBJECT-TYPE
    SYNTAX      OCTET STRING
    MAX-ACCESS  read-only
    STATUS      current
    DESCRIPTION
"
synchronization status for CountryCodeBlockedRe
-1 - CountryCodeBlockedRe could not be synchronized
 0 - synchronization not configured
 1 - out of sync - running master mode
 2 - in sync - running  mastermode
 3 - in sync - running slave mode
 4 - in sync - running master mode (wait to reach state 2)
"
    ::= {CountryCodeBlockedRe 5}

syncStatStrCountryCodeBlockedRe  OBJECT-TYPE
    SYNTAX      OCTET STRING
    MAX-ACCESS  read-only
    STATUS      current
    DESCRIPTION
"
synchronization status line from file assp_sync.cfg for CountryCodeBlockedRe
 0 - synchronization not configured
 1 - out of sync - running master mode
 2 - in sync - running  mastermode
 3 - in sync - running slave mode
 4 - in sync - running master mode (wait to reach state 2)
"
    ::= {CountryCodeBlockedRe 6}

DoSenderBase  OBJECT-TYPE
    SYNTAX      OCTET STRING
    MAX-ACCESS  read-write
    STATUS      current
    DESCRIPTION
"
If activated, each sending IP address has its assigned country looked up.
"
    REFERENCE "Do Country Code Scoring"
    DEFVAL { "3" }
    ::= {SenderBaseWhois 221}

syncStatDoSenderBase  OBJECT-TYPE
    SYNTAX      OCTET STRING
    MAX-ACCESS  read-only
    STATUS      current
    DESCRIPTION
"
synchronization status for DoSenderBase
-1 - DoSenderBase could not be synchronized
 0 - synchronization not configured
 1 - out of sync - running master mode
 2 - in sync - running  mastermode
 3 - in sync - running slave mode
 4 - in sync - running master mode (wait to reach state 2)
"
    ::= {DoSenderBase 5}

syncStatStrDoSenderBase  OBJECT-TYPE
    SYNTAX      OCTET STRING
    MAX-ACCESS  read-only
    STATUS      current
    DESCRIPTION
"
synchronization status line from file assp_sync.cfg for DoSenderBase
 0 - synchronization not configured
 1 - out of sync - running master mode
 2 - in sync - running  mastermode
 3 - in sync - running slave mode
 4 - in sync - running master mode (wait to reach state 2)
"
    ::= {DoSenderBase 6}

NoCountryCodeRe  OBJECT-TYPE
    SYNTAX      OCTET STRING
    MAX-ACCESS  read-write
    STATUS      current
    DESCRIPTION
"
Messages from IP's based in these countries will be ignored. For example: US|CA|DE
"
    REFERENCE "Ignore Countries*"
    DEFVAL { "US|CA|DE" }
    ::= {SenderBaseWhois 222}

syncStatNoCountryCodeRe  OBJECT-TYPE
    SYNTAX      OCTET STRING
    MAX-ACCESS  read-only
    STATUS      current
    DESCRIPTION
"
synchronization status for NoCountryCodeRe
-1 - NoCountryCodeRe could not be synchronized
 0 - synchronization not configured
 1 - out of sync - running master mode
 2 - in sync - running  mastermode
 3 - in sync - running slave mode
 4 - in sync - running master mode (wait to reach state 2)
"
    ::= {NoCountryCodeRe 5}

syncStatStrNoCountryCodeRe  OBJECT-TYPE
    SYNTAX      OCTET STRING
    MAX-ACCESS  read-only
    STATUS      current
    DESCRIPTION
"
synchronization status line from file assp_sync.cfg for NoCountryCodeRe
 0 - synchronization not configured
 1 - out of sync - running master mode
 2 - in sync - running  mastermode
 3 - in sync - running slave mode
 4 - in sync - running master mode (wait to reach state 2)
"
    ::= {NoCountryCodeRe 6}

CountryCodeRe  OBJECT-TYPE
    SYNTAX      OCTET STRING
    MAX-ACCESS  read-write
    STATUS      current
    DESCRIPTION
"
Messages from IP's based in these countries will increase the MessageScore. For example: CN|KR|RU|JP|TR|TH|PL|LT|CL|RO|UA|GR|HU|SA|IN|IE|PT|MD|PE|CZ|TW|BR|CL|ID|PH
"
    REFERENCE "Suspicious Country Codes**"
    DEFVAL { "CN|KR|RU|JP|TR|TH|PL|LT|CL|RO|UA|GR|HU|SA|IN|IE|PT|MD|PE|CZ|TW|BR|CL|ID|PH" }
    ::= {SenderBaseWhois 223}

syncStatCountryCodeRe  OBJECT-TYPE
    SYNTAX      OCTET STRING
    MAX-ACCESS  read-only
    STATUS      current
    DESCRIPTION
"
synchronization status for CountryCodeRe
-1 - CountryCodeRe could not be synchronized
 0 - synchronization not configured
 1 - out of sync - running master mode
 2 - in sync - running  mastermode
 3 - in sync - running slave mode
 4 - in sync - running master mode (wait to reach state 2)
"
    ::= {CountryCodeRe 5}

syncStatStrCountryCodeRe  OBJECT-TYPE
    SYNTAX      OCTET STRING
    MAX-ACCESS  read-only
    STATUS      current
    DESCRIPTION
"
synchronization status line from file assp_sync.cfg for CountryCodeRe
 0 - synchronization not configured
 1 - out of sync - running master mode
 2 - in sync - running  mastermode
 3 - in sync - running slave mode
 4 - in sync - running master mode (wait to reach state 2)
"
    ::= {CountryCodeRe 6}

MyCountryCodeRe  OBJECT-TYPE
    SYNTAX      OCTET STRING
    MAX-ACCESS  read-write
    STATUS      current
    DESCRIPTION
"
Put here your own country code(s) (for example: US). Messages from IP's based in these countries will decrease, messages from other countries will increase the MessageScore.
"
    REFERENCE "Home Country Codes**"
    DEFVAL { "" }
    ::= {SenderBaseWhois 224}

syncStatMyCountryCodeRe  OBJECT-TYPE
    SYNTAX      OCTET STRING
    MAX-ACCESS  read-only
    STATUS      current
    DESCRIPTION
"
synchronization status for MyCountryCodeRe
-1 - MyCountryCodeRe could not be synchronized
 0 - synchronization not configured
 1 - out of sync - running master mode
 2 - in sync - running  mastermode
 3 - in sync - running slave mode
 4 - in sync - running master mode (wait to reach state 2)
"
    ::= {MyCountryCodeRe 5}

syncStatStrMyCountryCodeRe  OBJECT-TYPE
    SYNTAX      OCTET STRING
    MAX-ACCESS  read-only
    STATUS      current
    DESCRIPTION
"
synchronization status line from file assp_sync.cfg for MyCountryCodeRe
 0 - synchronization not configured
 1 - out of sync - running master mode
 2 - in sync - running  mastermode
 3 - in sync - running slave mode
 4 - in sync - running master mode (wait to reach state 2)
"
    ::= {MyCountryCodeRe 6}

ScoreForeignCountries  OBJECT-TYPE
    SYNTAX      OCTET STRING
    MAX-ACCESS  read-write
    STATUS      current
    DESCRIPTION
"
Messages from foreign countries will increase the total messageScore using sbfccValencePB.
"
    REFERENCE "Score Foreign Countries"
    DEFVAL { "1" }
    ::= {SenderBaseWhois 225}

syncStatScoreForeignCountries  OBJECT-TYPE
    SYNTAX      OCTET STRING
    MAX-ACCESS  read-only
    STATUS      current
    DESCRIPTION
"
synchronization status for ScoreForeignCountries
-1 - ScoreForeignCountries could not be synchronized
 0 - synchronization not configured
 1 - out of sync - running master mode
 2 - in sync - running  mastermode
 3 - in sync - running slave mode
 4 - in sync - running master mode (wait to reach state 2)
"
    ::= {ScoreForeignCountries 5}

syncStatStrScoreForeignCountries  OBJECT-TYPE
    SYNTAX      OCTET STRING
    MAX-ACCESS  read-only
    STATUS      current
    DESCRIPTION
"
synchronization status line from file assp_sync.cfg for ScoreForeignCountries
 0 - synchronization not configured
 1 - out of sync - running master mode
 2 - in sync - running  mastermode
 3 - in sync - running slave mode
 4 - in sync - running master mode (wait to reach state 2)
"
    ::= {ScoreForeignCountries 6}

SBCacheExp  OBJECT-TYPE
    SYNTAX      OCTET STRING
    MAX-ACCESS  read-write
    STATUS      current
    DESCRIPTION
"
IP's in cache will be removed after this interval in days. 0 will disable the cache.  
"
    REFERENCE "Country Cache Refresh Interval"
    DEFVAL { "3" }
    ::= {SenderBaseWhois 226}

syncStatSBCacheExp  OBJECT-TYPE
    SYNTAX      OCTET STRING
    MAX-ACCESS  read-only
    STATUS      current
    DESCRIPTION
"
synchronization status for SBCacheExp
-1 - SBCacheExp could not be synchronized
 0 - synchronization not configured
 1 - out of sync - running master mode
 2 - in sync - running  mastermode
 3 - in sync - running slave mode
 4 - in sync - running master mode (wait to reach state 2)
"
    ::= {SBCacheExp 5}

syncStatStrSBCacheExp  OBJECT-TYPE
    SYNTAX      OCTET STRING
    MAX-ACCESS  read-only
    STATUS      current
    DESCRIPTION
"
synchronization status line from file assp_sync.cfg for SBCacheExp
 0 - synchronization not configured
 1 - out of sync - running master mode
 2 - in sync - running  mastermode
 3 - in sync - running slave mode
 4 - in sync - running master mode (wait to reach state 2)
"
    ::= {SBCacheExp 6}

enableWhois  OBJECT-TYPE
    SYNTAX      OCTET STRING
    MAX-ACCESS  read-write
    STATUS      current
    DESCRIPTION
"

  If enabled, WHOIS queries to Whois-servers
	'ARIN' => 'whois.arin.net' - (which will possible redirect to)
	'RIPE' => 'whois.ripe.net'
	'APNIC' => 'whois.apnic.net'
	'KRNIC' => 'whois.krnic.net'
	'LACNIC' => 'whois.lacnic.net'
	'AFRINIC' => 'whois.afrinic.net'
  will be done instead/after/before (WHOIS only/SenderBase first/WHOIS first) the Senderbase queries to CISCO's Ironport servers to get informations about an IP address. ARIN will be the first queried WHOIS server.
  For the two '...first' options, the alternative second check is done, if the first check fails or assp has got no result for the county code.
  This is useful, if your DNS-servers don't get answers for senderbase queries or senderbase queries are too slow.
  In most cases WHOIS queries are much more faster than senderbase queries!
  NOTICE: you must open the WHOIS-port (43) for TCP on your firewall for outgoing traffic from assp (if not already done)!
"
    REFERENCE "Use Whois Queries instead or after or before of SenderBase Queries"
    DEFVAL { "0" }
    ::= {SenderBaseWhois 1027}

syncStatenableWhois  OBJECT-TYPE
    SYNTAX      OCTET STRING
    MAX-ACCESS  read-only
    STATUS      current
    DESCRIPTION
"
synchronization status for enableWhois
-1 - enableWhois could not be synchronized
 0 - synchronization not configured
 1 - out of sync - running master mode
 2 - in sync - running  mastermode
 3 - in sync - running slave mode
 4 - in sync - running master mode (wait to reach state 2)
"
    ::= {enableWhois 5}

syncStatStrenableWhois  OBJECT-TYPE
    SYNTAX      OCTET STRING
    MAX-ACCESS  read-only
    STATUS      current
    DESCRIPTION
"
synchronization status line from file assp_sync.cfg for enableWhois
 0 - synchronization not configured
 1 - out of sync - running master mode
 2 - in sync - running  mastermode
 3 - in sync - running slave mode
 4 - in sync - running master mode (wait to reach state 2)
"
    ::= {enableWhois 6}

PenaltyBox  OBJECT IDENTIFIER ::= {asspConfig 15}
DoPenalty  OBJECT-TYPE
    SYNTAX      OCTET STRING
    MAX-ACCESS  read-write
    STATUS      current
    DESCRIPTION
"
The PenaltyBox is a  temporary position of low esteem awarded for a perceived misdeed. It scores IP's based on some events ( baValencePB see  penalty scores )and writes them into  a BlackBox. If the score per specified time interval surpasses the threshold the message is rejected (and the IP is marked for blocking). They continue to get scored  up to the Extreme Threshold.
 These top performers can get a special treatment PenaltyExtreme when DoPenaltyExtreme is enabled. The WhiteBox stores IP's which should not be put into the BlackBox. The WhiteBox is always enabled. If an address is in the whitelist or whitedomain, the IP goes into the WhiteBox. The WhiteBox is one of the sources  Delaying/Greylisting uses to determine when delaying should not be done. Entries in Don't do penalties for these IP's or ISP/Secondary MX Servers will prevent from penalties. Select 'monitor/messageScoring' to fill WhiteBox and BlackBox. 'monitor/messageScoring' is also the right choice if you do not want to block IP's but rather score a message in 'Message Scoring Mode'. 
"
    REFERENCE "Do PenaltyBox - IP History"
    DEFVAL { "2" }
    ::= {PenaltyBox 227}

syncStatDoPenalty  OBJECT-TYPE
    SYNTAX      OCTET STRING
    MAX-ACCESS  read-only
    STATUS      current
    DESCRIPTION
"
synchronization status for DoPenalty
-1 - DoPenalty could not be synchronized
 0 - synchronization not configured
 1 - out of sync - running master mode
 2 - in sync - running  mastermode
 3 - in sync - running slave mode
 4 - in sync - running master mode (wait to reach state 2)
"
    ::= {DoPenalty 5}

syncStatStrDoPenalty  OBJECT-TYPE
    SYNTAX      OCTET STRING
    MAX-ACCESS  read-only
    STATUS      current
    DESCRIPTION
"
synchronization status line from file assp_sync.cfg for DoPenalty
 0 - synchronization not configured
 1 - out of sync - running master mode
 2 - in sync - running  mastermode
 3 - in sync - running slave mode
 4 - in sync - running master mode (wait to reach state 2)
"
    ::= {DoPenalty 6}

DoPenaltyMessage  OBJECT-TYPE
    SYNTAX      OCTET STRING
    MAX-ACCESS  read-write
    STATUS      current
    DESCRIPTION
"
If this feature is selected, the total score for all checks during a message is used to determine if the email is Spam. If the combined score is greater than the Low MessageLimit (PenaltyMessageLow) and less than or equal the High MessageLimit (PenaltyMessageLimit) the message will not be blocked but tagged. If the combined score is greater than the High MessageLimit (PenaltyMessageLimit), the message will be blocked.
"
    REFERENCE "Message Scoring Mode "
    DEFVAL { "1" }
    ::= {PenaltyBox 228}

syncStatDoPenaltyMessage  OBJECT-TYPE
    SYNTAX      OCTET STRING
    MAX-ACCESS  read-only
    STATUS      current
    DESCRIPTION
"
synchronization status for DoPenaltyMessage
-1 - DoPenaltyMessage could not be synchronized
 0 - synchronization not configured
 1 - out of sync - running master mode
 2 - in sync - running  mastermode
 3 - in sync - running slave mode
 4 - in sync - running master mode (wait to reach state 2)
"
    ::= {DoPenaltyMessage 5}

syncStatStrDoPenaltyMessage  OBJECT-TYPE
    SYNTAX      OCTET STRING
    MAX-ACCESS  read-only
    STATUS      current
    DESCRIPTION
"
synchronization status line from file assp_sync.cfg for DoPenaltyMessage
 0 - synchronization not configured
 1 - out of sync - running master mode
 2 - in sync - running  mastermode
 3 - in sync - running slave mode
 4 - in sync - running master mode (wait to reach state 2)
"
    ::= {DoPenaltyMessage 6}

MsgScoreOnEnd  OBJECT-TYPE
    SYNTAX      OCTET STRING
    MAX-ACCESS  read-write
    STATUS      current
    DESCRIPTION
"
ASSP will wait using the 'DoPenaltyMessage' action, until all configured possible checks are finished. Use this, to force calculating a complete message score over all values, including all bonus values.
"
    REFERENCE "Message Scoring on End"
    DEFVAL { "" }
    ::= {PenaltyBox 229}

syncStatMsgScoreOnEnd  OBJECT-TYPE
    SYNTAX      OCTET STRING
    MAX-ACCESS  read-only
    STATUS      current
    DESCRIPTION
"
synchronization status for MsgScoreOnEnd
-1 - MsgScoreOnEnd could not be synchronized
 0 - synchronization not configured
 1 - out of sync - running master mode
 2 - in sync - running  mastermode
 3 - in sync - running slave mode
 4 - in sync - running master mode (wait to reach state 2)
"
    ::= {MsgScoreOnEnd 5}

syncStatStrMsgScoreOnEnd  OBJECT-TYPE
    SYNTAX      OCTET STRING
    MAX-ACCESS  read-only
    STATUS      current
    DESCRIPTION
"
synchronization status line from file assp_sync.cfg for MsgScoreOnEnd
 0 - synchronization not configured
 1 - out of sync - running master mode
 2 - in sync - running  mastermode
 3 - in sync - running slave mode
 4 - in sync - running master mode (wait to reach state 2)
"
    ::= {MsgScoreOnEnd 6}

PenaltyMessageLow  OBJECT-TYPE
    SYNTAX      OCTET STRING
    MAX-ACCESS  read-write
    STATUS      current
    DESCRIPTION
"
MessageMode will not block messages whose score exceeds this threshold during the message but will tag them.  For example: 40
"
    REFERENCE "Low MessageLimit"
    DEFVAL { "40" }
    ::= {PenaltyBox 230}

syncStatPenaltyMessageLow  OBJECT-TYPE
    SYNTAX      OCTET STRING
    MAX-ACCESS  read-only
    STATUS      current
    DESCRIPTION
"
synchronization status for PenaltyMessageLow
-1 - PenaltyMessageLow could not be synchronized
 0 - synchronization not configured
 1 - out of sync - running master mode
 2 - in sync - running  mastermode
 3 - in sync - running slave mode
 4 - in sync - running master mode (wait to reach state 2)
"
    ::= {PenaltyMessageLow 5}

syncStatStrPenaltyMessageLow  OBJECT-TYPE
    SYNTAX      OCTET STRING
    MAX-ACCESS  read-only
    STATUS      current
    DESCRIPTION
"
synchronization status line from file assp_sync.cfg for PenaltyMessageLow
 0 - synchronization not configured
 1 - out of sync - running master mode
 2 - in sync - running  mastermode
 3 - in sync - running slave mode
 4 - in sync - running master mode (wait to reach state 2)
"
    ::= {PenaltyMessageLow 6}

PenaltyMessageLimit  OBJECT-TYPE
    SYNTAX      OCTET STRING
    MAX-ACCESS  read-write
    STATUS      current
    DESCRIPTION
"
MessageMode will block messages whose score exceeds this threshold during the message.  For example: 50
"
    REFERENCE "High MessageLimit"
    DEFVAL { "50" }
    ::= {PenaltyBox 231}

syncStatPenaltyMessageLimit  OBJECT-TYPE
    SYNTAX      OCTET STRING
    MAX-ACCESS  read-only
    STATUS      current
    DESCRIPTION
"
synchronization status for PenaltyMessageLimit
-1 - PenaltyMessageLimit could not be synchronized
 0 - synchronization not configured
 1 - out of sync - running master mode
 2 - in sync - running  mastermode
 3 - in sync - running slave mode
 4 - in sync - running master mode (wait to reach state 2)
"
    ::= {PenaltyMessageLimit 5}

syncStatStrPenaltyMessageLimit  OBJECT-TYPE
    SYNTAX      OCTET STRING
    MAX-ACCESS  read-only
    STATUS      current
    DESCRIPTION
"
synchronization status line from file assp_sync.cfg for PenaltyMessageLimit
 0 - synchronization not configured
 1 - out of sync - running master mode
 2 - in sync - running  mastermode
 3 - in sync - running slave mode
 4 - in sync - running master mode (wait to reach state 2)
"
    ::= {PenaltyMessageLimit 6}

AddScoringHeader  OBJECT-TYPE
    SYNTAX      OCTET STRING
    MAX-ACCESS  read-write
    STATUS      current
    DESCRIPTION
"
Adds a line to the email header 'X-Assp-XXX-Score: ', where XXX may be IP, Message or both.
"
    REFERENCE "Add IP/Message Scoring Header"
    DEFVAL { "1" }
    ::= {PenaltyBox 232}

syncStatAddScoringHeader  OBJECT-TYPE
    SYNTAX      OCTET STRING
    MAX-ACCESS  read-only
    STATUS      current
    DESCRIPTION
"
synchronization status for AddScoringHeader
-1 - AddScoringHeader could not be synchronized
 0 - synchronization not configured
 1 - out of sync - running master mode
 2 - in sync - running  mastermode
 3 - in sync - running slave mode
 4 - in sync - running master mode (wait to reach state 2)
"
    ::= {AddScoringHeader 5}

syncStatStrAddScoringHeader  OBJECT-TYPE
    SYNTAX      OCTET STRING
    MAX-ACCESS  read-only
    STATUS      current
    DESCRIPTION
"
synchronization status line from file assp_sync.cfg for AddScoringHeader
 0 - synchronization not configured
 1 - out of sync - running master mode
 2 - in sync - running  mastermode
 3 - in sync - running slave mode
 4 - in sync - running master mode (wait to reach state 2)
"
    ::= {AddScoringHeader 6}

pbdb  OBJECT-TYPE
    SYNTAX      OCTET STRING
    MAX-ACCESS  read-write
    STATUS      current
    DESCRIPTION
"
The directory/file with the penaltybox database files. For removal of entries from BlackBox use noPB .
 For removal of entries from WhiteBox use noPBwhite. For whitelisting IP's use whiteListedIPs or noProcessingIPs . For blacklisting use denySMTPConnectionsFrom and denySMTPConnectionsFromAlways .Write only 'DB:' to use a database table instead of a local file. 
 
"
    REFERENCE "PenaltyBox Database"
    DEFVAL { "pb/pbdb" }
    ::= {PenaltyBox 233}

noPB  OBJECT-TYPE
    SYNTAX      OCTET STRING
    MAX-ACCESS  read-write
    STATUS      current
    DESCRIPTION
"
Enter IP's that you don't want to be penalized. These IP's will also be automatically removed from PB-BlackBox. For example: 127.0.0.1|172.16.
"
    REFERENCE "Don't do Profiling for these IP's*"
    DEFVAL { "" }
    ::= {PenaltyBox 234}

syncStatnoPB  OBJECT-TYPE
    SYNTAX      OCTET STRING
    MAX-ACCESS  read-only
    STATUS      current
    DESCRIPTION
"
synchronization status for noPB
-1 - noPB could not be synchronized
 0 - synchronization not configured
 1 - out of sync - running master mode
 2 - in sync - running  mastermode
 3 - in sync - running slave mode
 4 - in sync - running master mode (wait to reach state 2)
"
    ::= {noPB 5}

syncStatStrnoPB  OBJECT-TYPE
    SYNTAX      OCTET STRING
    MAX-ACCESS  read-only
    STATUS      current
    DESCRIPTION
"
synchronization status line from file assp_sync.cfg for noPB
 0 - synchronization not configured
 1 - out of sync - running master mode
 2 - in sync - running  mastermode
 3 - in sync - running slave mode
 4 - in sync - running master mode (wait to reach state 2)
"
    ::= {noPB 6}

noPBwhite  OBJECT-TYPE
    SYNTAX      OCTET STRING
    MAX-ACCESS  read-write
    STATUS      current
    DESCRIPTION
"
Enter IP's that you want to be penalized. These IP's will also be automatically removed from PB-WhiteBox.
"
    REFERENCE "Don't do WhiteBox for these IP's*"
    DEFVAL { "" }
    ::= {PenaltyBox 235}

syncStatnoPBwhite  OBJECT-TYPE
    SYNTAX      OCTET STRING
    MAX-ACCESS  read-only
    STATUS      current
    DESCRIPTION
"
synchronization status for noPBwhite
-1 - noPBwhite could not be synchronized
 0 - synchronization not configured
 1 - out of sync - running master mode
 2 - in sync - running  mastermode
 3 - in sync - running slave mode
 4 - in sync - running master mode (wait to reach state 2)
"
    ::= {noPBwhite 5}

syncStatStrnoPBwhite  OBJECT-TYPE
    SYNTAX      OCTET STRING
    MAX-ACCESS  read-only
    STATUS      current
    DESCRIPTION
"
synchronization status line from file assp_sync.cfg for noPBwhite
 0 - synchronization not configured
 1 - out of sync - running master mode
 2 - in sync - running  mastermode
 3 - in sync - running slave mode
 4 - in sync - running master mode (wait to reach state 2)
"
    ::= {noPBwhite 6}

WhiteExpiration  OBJECT-TYPE
    SYNTAX      OCTET STRING
    MAX-ACCESS  read-write
    STATUS      current
    DESCRIPTION
"
The WhiteBox is always activated. The WhiteBox is similar to the  Whitelist  - but it is not a whitelist: content-related checks like Bayesian, URIBL, Bomb  will be done, IP-related checks will be skipped. WhiteBox entries will expire after this specified number of days. For example: 30
"
    REFERENCE "Expiration Time for WhiteBox Entries"
    DEFVAL { "30" }
    ::= {PenaltyBox 236}

syncStatWhiteExpiration  OBJECT-TYPE
    SYNTAX      OCTET STRING
    MAX-ACCESS  read-only
    STATUS      current
    DESCRIPTION
"
synchronization status for WhiteExpiration
-1 - WhiteExpiration could not be synchronized
 0 - synchronization not configured
 1 - out of sync - running master mode
 2 - in sync - running  mastermode
 3 - in sync - running slave mode
 4 - in sync - running master mode (wait to reach state 2)
"
    ::= {WhiteExpiration 5}

syncStatStrWhiteExpiration  OBJECT-TYPE
    SYNTAX      OCTET STRING
    MAX-ACCESS  read-only
    STATUS      current
    DESCRIPTION
"
synchronization status line from file assp_sync.cfg for WhiteExpiration
 0 - synchronization not configured
 1 - out of sync - running master mode
 2 - in sync - running  mastermode
 3 - in sync - running slave mode
 4 - in sync - running master mode (wait to reach state 2)
"
    ::= {WhiteExpiration 6}

DoDamping  OBJECT-TYPE
    SYNTAX      OCTET STRING
    MAX-ACCESS  read-write
    STATUS      current
    DESCRIPTION
"
If DoPenalty and DoPenaltyMessage are set not to disabled and DoDamping is not set to 0, ASSP will slowdown the spammers traffic speed proportional to the current message score - because slowing down their speed will reduce spam everywhere.
  The delay in seconds per receive/read cycle is calculated by the division [messagescore / DoDamping] . A recommended value is 5 default is 0. In this case the delay for a message score of 50 would be 10 seconds.
  Do not use this option, if you have a highly frequented system, because the spammers connections will stay possibly a long time on your system, and you system could possibly reach the sessions limit ( maxSMTPSessions ).
  Damping is never done for: noprocessing, whitelisted, nodelay, ISP, redlisted, noPB, outgoing/releayed and contentonly addresses, IP's, messages.
  Damping may not be done for forced checks, relay attemps, messages reaching maxerrors, spamtrapaddresses and if any block condition is found - because ASSP will no more read from those connections and closes such connections immediately - but ASSP will try to keep the connection open for the calculated time, before it closes the connection.
  Using this option or using a too low value (long delay) could possibly prevent ASSP from receiving spam messages, for example for spamlovers or sendAllSpam . Some Servers could give up sending data, because of too long delays.
"
    REFERENCE "Do Damping on Messagescore [0...99]"
    DEFVAL { "0" }
    ::= {PenaltyBox 237}

syncStatDoDamping  OBJECT-TYPE
    SYNTAX      OCTET STRING
    MAX-ACCESS  read-only
    STATUS      current
    DESCRIPTION
"
synchronization status for DoDamping
-1 - DoDamping could not be synchronized
 0 - synchronization not configured
 1 - out of sync - running master mode
 2 - in sync - running  mastermode
 3 - in sync - running slave mode
 4 - in sync - running master mode (wait to reach state 2)
"
    ::= {DoDamping 5}

syncStatStrDoDamping  OBJECT-TYPE
    SYNTAX      OCTET STRING
    MAX-ACCESS  read-only
    STATUS      current
    DESCRIPTION
"
synchronization status line from file assp_sync.cfg for DoDamping
 0 - synchronization not configured
 1 - out of sync - running master mode
 2 - in sync - running  mastermode
 3 - in sync - running slave mode
 4 - in sync - running master mode (wait to reach state 2)
"
    ::= {DoDamping 6}

maxDampingTime  OBJECT-TYPE
    SYNTAX      OCTET STRING
    MAX-ACCESS  read-write
    STATUS      current
    DESCRIPTION
"
The maximum time in second, that is used for one damping cycle if DoDamping is not set to 0, even if the calculated value caused by DoDamping is higher. For example: 30
"
    REFERENCE "Max time Used for Damping"
    DEFVAL { "30" }
    ::= {PenaltyBox 238}

syncStatmaxDampingTime  OBJECT-TYPE
    SYNTAX      OCTET STRING
    MAX-ACCESS  read-only
    STATUS      current
    DESCRIPTION
"
synchronization status for maxDampingTime
-1 - maxDampingTime could not be synchronized
 0 - synchronization not configured
 1 - out of sync - running master mode
 2 - in sync - running  mastermode
 3 - in sync - running slave mode
 4 - in sync - running master mode (wait to reach state 2)
"
    ::= {maxDampingTime 5}

syncStatStrmaxDampingTime  OBJECT-TYPE
    SYNTAX      OCTET STRING
    MAX-ACCESS  read-only
    STATUS      current
    DESCRIPTION
"
synchronization status line from file assp_sync.cfg for maxDampingTime
 0 - synchronization not configured
 1 - out of sync - running master mode
 2 - in sync - running  mastermode
 3 - in sync - running slave mode
 4 - in sync - running master mode (wait to reach state 2)
"
    ::= {maxDampingTime 6}

spamtrapaddresses  OBJECT-TYPE
    SYNTAX      OCTET STRING
    MAX-ACCESS  read-write
    STATUS      current
    DESCRIPTION
"
Mail to any of these addresses will be blocked and the scoring value is added. Whitelist and noPenaltyMakeTraps will be ignored. Nothing will be stored in the Spam Collection, if these addresses are not checked for validity. TO: and CC: addresses will be also checked - BCC: addresses only, if 'removeForeignBCC' is not set. Accepts specific addresses (user@domain.com), user parts (user) or entire domains (@domain.com).
"
    REFERENCE "PenaltyBox Trap Addresses *"
    DEFVAL { "put|your@penaltytrap.com|addresses|@here.org" }
    ::= {PenaltyBox 239}

syncStatspamtrapaddresses  OBJECT-TYPE
    SYNTAX      OCTET STRING
    MAX-ACCESS  read-only
    STATUS      current
    DESCRIPTION
"
synchronization status for spamtrapaddresses
-1 - spamtrapaddresses could not be synchronized
 0 - synchronization not configured
 1 - out of sync - running master mode
 2 - in sync - running  mastermode
 3 - in sync - running slave mode
 4 - in sync - running master mode (wait to reach state 2)
"
    ::= {spamtrapaddresses 5}

syncStatStrspamtrapaddresses  OBJECT-TYPE
    SYNTAX      OCTET STRING
    MAX-ACCESS  read-only
    STATUS      current
    DESCRIPTION
"
synchronization status line from file assp_sync.cfg for spamtrapaddresses
 0 - synchronization not configured
 1 - out of sync - running master mode
 2 - in sync - running  mastermode
 3 - in sync - running slave mode
 4 - in sync - running master mode (wait to reach state 2)
"
    ::= {spamtrapaddresses 6}

PenaltyTrapPolite  OBJECT-TYPE
    SYNTAX      OCTET STRING
    MAX-ACCESS  read-write
    STATUS      current
    DESCRIPTION
"
SMTP reply for invalid Users. Default: '550 5.1.1 User unknown: EMAILADDRESS'  The literal EMAILADDRESS (case sensitive) is replaced by the fully qualified SMTP recipient (e.g., thisuser@example.com).
"
    REFERENCE "PenaltyTrap Reply"
    DEFVAL { "550 5.1.1 User unknown: EMAILADDRESS" }
    ::= {PenaltyBox 240}

syncStatPenaltyTrapPolite  OBJECT-TYPE
    SYNTAX      OCTET STRING
    MAX-ACCESS  read-only
    STATUS      current
    DESCRIPTION
"
synchronization status for PenaltyTrapPolite
-1 - PenaltyTrapPolite could not be synchronized
 0 - synchronization not configured
 1 - out of sync - running master mode
 2 - in sync - running  mastermode
 3 - in sync - running slave mode
 4 - in sync - running master mode (wait to reach state 2)
"
    ::= {PenaltyTrapPolite 5}

syncStatStrPenaltyTrapPolite  OBJECT-TYPE
    SYNTAX      OCTET STRING
    MAX-ACCESS  read-only
    STATUS      current
    DESCRIPTION
"
synchronization status line from file assp_sync.cfg for PenaltyTrapPolite
 0 - synchronization not configured
 1 - out of sync - running master mode
 2 - in sync - running  mastermode
 3 - in sync - running slave mode
 4 - in sync - running master mode (wait to reach state 2)
"
    ::= {PenaltyTrapPolite 6}

DoPenaltyMakeTraps  OBJECT-TYPE
    SYNTAX      OCTET STRING
    MAX-ACCESS  read-write
    STATUS      current
    DESCRIPTION
"
If set to 'make traps, only collect them', the frequency of Invalid Addresses is stored, no other action taken. If set to 'do not make them but block' or 'make traps and block them', addresses in heavy use will act like spamtrapaddresses (PenaltyBox Trap Addresses). If UseTrapToCollect is also set they will work like spamaddresses and collect the mails.
"
    REFERENCE "Do Heavy Used Invalid Addresses as PenaltyBox Trap Addresses"
    DEFVAL { "2" }
    ::= {PenaltyBox 241}

syncStatDoPenaltyMakeTraps  OBJECT-TYPE
    SYNTAX      OCTET STRING
    MAX-ACCESS  read-only
    STATUS      current
    DESCRIPTION
"
synchronization status for DoPenaltyMakeTraps
-1 - DoPenaltyMakeTraps could not be synchronized
 0 - synchronization not configured
 1 - out of sync - running master mode
 2 - in sync - running  mastermode
 3 - in sync - running slave mode
 4 - in sync - running master mode (wait to reach state 2)
"
    ::= {DoPenaltyMakeTraps 5}

syncStatStrDoPenaltyMakeTraps  OBJECT-TYPE
    SYNTAX      OCTET STRING
    MAX-ACCESS  read-only
    STATUS      current
    DESCRIPTION
"
synchronization status line from file assp_sync.cfg for DoPenaltyMakeTraps
 0 - synchronization not configured
 1 - out of sync - running master mode
 2 - in sync - running  mastermode
 3 - in sync - running slave mode
 4 - in sync - running master mode (wait to reach state 2)
"
    ::= {DoPenaltyMakeTraps 6}

PenaltyMakeTraps  OBJECT-TYPE
    SYNTAX      OCTET STRING
    MAX-ACCESS  read-write
    STATUS      current
    DESCRIPTION
"
Minimum number of times an address must appear before it will be used as Trap. For example 10.
"
    REFERENCE "Invalid Addresses Limit"
    DEFVAL { "10" }
    ::= {PenaltyBox 242}

syncStatPenaltyMakeTraps  OBJECT-TYPE
    SYNTAX      OCTET STRING
    MAX-ACCESS  read-only
    STATUS      current
    DESCRIPTION
"
synchronization status for PenaltyMakeTraps
-1 - PenaltyMakeTraps could not be synchronized
 0 - synchronization not configured
 1 - out of sync - running master mode
 2 - in sync - running  mastermode
 3 - in sync - running slave mode
 4 - in sync - running master mode (wait to reach state 2)
"
    ::= {PenaltyMakeTraps 5}

syncStatStrPenaltyMakeTraps  OBJECT-TYPE
    SYNTAX      OCTET STRING
    MAX-ACCESS  read-only
    STATUS      current
    DESCRIPTION
"
synchronization status line from file assp_sync.cfg for PenaltyMakeTraps
 0 - synchronization not configured
 1 - out of sync - running master mode
 2 - in sync - running  mastermode
 3 - in sync - running slave mode
 4 - in sync - running master mode (wait to reach state 2)
"
    ::= {PenaltyMakeTraps 6}

noPenaltyMakeTraps  OBJECT-TYPE
    SYNTAX      OCTET STRING
    MAX-ACCESS  read-write
    STATUS      current
    DESCRIPTION
"
Addresses which should not be used for traps. This list is also opponent to spamtrapaddresses . Accepts specific addresses (user@domain.com), user parts (user) or entire domains (@domain.com).  Wildcards are supported (fribo*@domain.com).
"
    REFERENCE "Exceptionlist for Traps*"
    DEFVAL { "" }
    ::= {PenaltyBox 243}

syncStatnoPenaltyMakeTraps  OBJECT-TYPE
    SYNTAX      OCTET STRING
    MAX-ACCESS  read-only
    STATUS      current
    DESCRIPTION
"
synchronization status for noPenaltyMakeTraps
-1 - noPenaltyMakeTraps could not be synchronized
 0 - synchronization not configured
 1 - out of sync - running master mode
 2 - in sync - running  mastermode
 3 - in sync - running slave mode
 4 - in sync - running master mode (wait to reach state 2)
"
    ::= {noPenaltyMakeTraps 5}

syncStatStrnoPenaltyMakeTraps  OBJECT-TYPE
    SYNTAX      OCTET STRING
    MAX-ACCESS  read-only
    STATUS      current
    DESCRIPTION
"
synchronization status line from file assp_sync.cfg for noPenaltyMakeTraps
 0 - synchronization not configured
 1 - out of sync - running master mode
 2 - in sync - running  mastermode
 3 - in sync - running slave mode
 4 - in sync - running master mode (wait to reach state 2)
"
    ::= {noPenaltyMakeTraps 6}

PBTrapInterval  OBJECT-TYPE
    SYNTAX      OCTET STRING
    MAX-ACCESS  read-write
    STATUS      current
    DESCRIPTION
"
Addresses will be removed after this interval in days. For example 3. 
"
    REFERENCE "Invalid Addresses Refresh Interval"
    DEFVAL { "3" }
    ::= {PenaltyBox 244}

syncStatPBTrapInterval  OBJECT-TYPE
    SYNTAX      OCTET STRING
    MAX-ACCESS  read-only
    STATUS      current
    DESCRIPTION
"
synchronization status for PBTrapInterval
-1 - PBTrapInterval could not be synchronized
 0 - synchronization not configured
 1 - out of sync - running master mode
 2 - in sync - running  mastermode
 3 - in sync - running slave mode
 4 - in sync - running master mode (wait to reach state 2)
"
    ::= {PBTrapInterval 5}

syncStatStrPBTrapInterval  OBJECT-TYPE
    SYNTAX      OCTET STRING
    MAX-ACCESS  read-only
    STATUS      current
    DESCRIPTION
"
synchronization status line from file assp_sync.cfg for PBTrapInterval
 0 - synchronization not configured
 1 - out of sync - running master mode
 2 - in sync - running  mastermode
 3 - in sync - running slave mode
 4 - in sync - running master mode (wait to reach state 2)
"
    ::= {PBTrapInterval 6}

PenaltyUseNetblocks  OBJECT-TYPE
    SYNTAX      OCTET STRING
    MAX-ACCESS  read-write
    STATUS      current
    DESCRIPTION
"
Perform the IP address checks of the sending host based on the /24 subnet  rather than on the specific IP.
"
    REFERENCE "Use IP Netblocks"
    DEFVAL { "1" }
    ::= {PenaltyBox 245}

syncStatPenaltyUseNetblocks  OBJECT-TYPE
    SYNTAX      OCTET STRING
    MAX-ACCESS  read-only
    STATUS      current
    DESCRIPTION
"
synchronization status for PenaltyUseNetblocks
-1 - PenaltyUseNetblocks could not be synchronized
 0 - synchronization not configured
 1 - out of sync - running master mode
 2 - in sync - running  mastermode
 3 - in sync - running slave mode
 4 - in sync - running master mode (wait to reach state 2)
"
    ::= {PenaltyUseNetblocks 5}

syncStatStrPenaltyUseNetblocks  OBJECT-TYPE
    SYNTAX      OCTET STRING
    MAX-ACCESS  read-only
    STATUS      current
    DESCRIPTION
"
synchronization status line from file assp_sync.cfg for PenaltyUseNetblocks
 0 - synchronization not configured
 1 - out of sync - running master mode
 2 - in sync - running  mastermode
 3 - in sync - running slave mode
 4 - in sync - running master mode (wait to reach state 2)
"
    ::= {PenaltyUseNetblocks 6}

PenaltyError  OBJECT-TYPE
    SYNTAX      OCTET STRING
    MAX-ACCESS  read-write
    STATUS      current
    DESCRIPTION
"
If set SMTP reply for Penalty Deny. eg: '554 5.7.1 Error, send your mail to postmaster@LOCALDOMAIN to ensure delivery'. The literal LOCALDOMAIN will be replaced by the recipient domain. For example:554 5.7.1 Mail appears to be unsolicited -- send error reports to postmaster@LOCALDOMAIN.
"
    REFERENCE "Penalty Reply"
    DEFVAL { "" }
    ::= {PenaltyBox 246}

syncStatPenaltyError  OBJECT-TYPE
    SYNTAX      OCTET STRING
    MAX-ACCESS  read-only
    STATUS      current
    DESCRIPTION
"
synchronization status for PenaltyError
-1 - PenaltyError could not be synchronized
 0 - synchronization not configured
 1 - out of sync - running master mode
 2 - in sync - running  mastermode
 3 - in sync - running slave mode
 4 - in sync - running master mode (wait to reach state 2)
"
    ::= {PenaltyError 5}

syncStatStrPenaltyError  OBJECT-TYPE
    SYNTAX      OCTET STRING
    MAX-ACCESS  read-only
    STATUS      current
    DESCRIPTION
"
synchronization status line from file assp_sync.cfg for PenaltyError
 0 - synchronization not configured
 1 - out of sync - running master mode
 2 - in sync - running  mastermode
 3 - in sync - running slave mode
 4 - in sync - running master mode (wait to reach state 2)
"
    ::= {PenaltyError 6}

PenaltyDuration  OBJECT-TYPE
    SYNTAX      OCTET STRING
    MAX-ACCESS  read-write
    STATUS      current
    DESCRIPTION
"
IP's will be kept in the BlackBox if their score exceeds the Penalty Limit during this interval (minutes).
"
    REFERENCE "Penalty Interval"
    DEFVAL { "60" }
    ::= {PenaltyBox 247}

syncStatPenaltyDuration  OBJECT-TYPE
    SYNTAX      OCTET STRING
    MAX-ACCESS  read-only
    STATUS      current
    DESCRIPTION
"
synchronization status for PenaltyDuration
-1 - PenaltyDuration could not be synchronized
 0 - synchronization not configured
 1 - out of sync - running master mode
 2 - in sync - running  mastermode
 3 - in sync - running slave mode
 4 - in sync - running master mode (wait to reach state 2)
"
    ::= {PenaltyDuration 5}

syncStatStrPenaltyDuration  OBJECT-TYPE
    SYNTAX      OCTET STRING
    MAX-ACCESS  read-only
    STATUS      current
    DESCRIPTION
"
synchronization status line from file assp_sync.cfg for PenaltyDuration
 0 - synchronization not configured
 1 - out of sync - running master mode
 2 - in sync - running  mastermode
 3 - in sync - running slave mode
 4 - in sync - running master mode (wait to reach state 2)
"
    ::= {PenaltyDuration 6}

PenaltyLimit  OBJECT-TYPE
    SYNTAX      OCTET STRING
    MAX-ACCESS  read-write
    STATUS      current
    DESCRIPTION
"
PB will block IP's whose score exceeds this threshold during the Penalty Interval. Successful ASSP checks will increase the internal score per IP. For example: 50
"
    REFERENCE "Penalty Limit"
    DEFVAL { "50" }
    ::= {PenaltyBox 248}

syncStatPenaltyLimit  OBJECT-TYPE
    SYNTAX      OCTET STRING
    MAX-ACCESS  read-only
    STATUS      current
    DESCRIPTION
"
synchronization status for PenaltyLimit
-1 - PenaltyLimit could not be synchronized
 0 - synchronization not configured
 1 - out of sync - running master mode
 2 - in sync - running  mastermode
 3 - in sync - running slave mode
 4 - in sync - running master mode (wait to reach state 2)
"
    ::= {PenaltyLimit 5}

syncStatStrPenaltyLimit  OBJECT-TYPE
    SYNTAX      OCTET STRING
    MAX-ACCESS  read-only
    STATUS      current
    DESCRIPTION
"
synchronization status line from file assp_sync.cfg for PenaltyLimit
 0 - synchronization not configured
 1 - out of sync - running master mode
 2 - in sync - running  mastermode
 3 - in sync - running slave mode
 4 - in sync - running master mode (wait to reach state 2)
"
    ::= {PenaltyLimit 6}

PenaltyExpiration  OBJECT-TYPE
    SYNTAX      OCTET STRING
    MAX-ACCESS  read-write
    STATUS      current
    DESCRIPTION
"
Penalties will expire after this number of minutes. If set to Zero the Penalty BlackBox will be deleted and started from scratch.
"
    REFERENCE "Expiration Time"
    DEFVAL { "360" }
    ::= {PenaltyBox 249}

syncStatPenaltyExpiration  OBJECT-TYPE
    SYNTAX      OCTET STRING
    MAX-ACCESS  read-only
    STATUS      current
    DESCRIPTION
"
synchronization status for PenaltyExpiration
-1 - PenaltyExpiration could not be synchronized
 0 - synchronization not configured
 1 - out of sync - running master mode
 2 - in sync - running  mastermode
 3 - in sync - running slave mode
 4 - in sync - running master mode (wait to reach state 2)
"
    ::= {PenaltyExpiration 5}

syncStatStrPenaltyExpiration  OBJECT-TYPE
    SYNTAX      OCTET STRING
    MAX-ACCESS  read-only
    STATUS      current
    DESCRIPTION
"
synchronization status line from file assp_sync.cfg for PenaltyExpiration
 0 - synchronization not configured
 1 - out of sync - running master mode
 2 - in sync - running  mastermode
 3 - in sync - running slave mode
 4 - in sync - running master mode (wait to reach state 2)
"
    ::= {PenaltyExpiration 6}

CleanPBInterval  OBJECT-TYPE
    SYNTAX      OCTET STRING
    MAX-ACCESS  read-write
    STATUS      current
    DESCRIPTION
"
Delete outdated entries from blackbox and whitebox databases every this many hours.
  Defaults to 3 hours.
"
    REFERENCE "Clean Up PB Databases <sup>s</sup>"
    DEFVAL { "3" }
    ::= {PenaltyBox 250}

syncStatCleanPBInterval  OBJECT-TYPE
    SYNTAX      OCTET STRING
    MAX-ACCESS  read-only
    STATUS      current
    DESCRIPTION
"
synchronization status for CleanPBInterval
-1 - CleanPBInterval could not be synchronized
 0 - synchronization not configured
 1 - out of sync - running master mode
 2 - in sync - running  mastermode
 3 - in sync - running slave mode
 4 - in sync - running master mode (wait to reach state 2)
"
    ::= {CleanPBInterval 5}

syncStatStrCleanPBInterval  OBJECT-TYPE
    SYNTAX      OCTET STRING
    MAX-ACCESS  read-only
    STATUS      current
    DESCRIPTION
"
synchronization status line from file assp_sync.cfg for CleanPBInterval
 0 - synchronization not configured
 1 - out of sync - running master mode
 2 - in sync - running  mastermode
 3 - in sync - running slave mode
 4 - in sync - running master mode (wait to reach state 2)
"
    ::= {CleanPBInterval 6}

DoPenaltyExtreme  OBJECT-TYPE
    SYNTAX      OCTET STRING
    MAX-ACCESS  read-write
    STATUS      current
    DESCRIPTION
"
If set PBextreme will block IP's whose score meet or exceed Extreme Scoring Threshold. DoPenaltyExtreme blocks after the header is done, based on the IP's score from previous and current SMTP session
"
    REFERENCE "PenaltyBox Extreme IP Profiling"
    DEFVAL { "0" }
    ::= {PenaltyBox 251}

syncStatDoPenaltyExtreme  OBJECT-TYPE
    SYNTAX      OCTET STRING
    MAX-ACCESS  read-only
    STATUS      current
    DESCRIPTION
"
synchronization status for DoPenaltyExtreme
-1 - DoPenaltyExtreme could not be synchronized
 0 - synchronization not configured
 1 - out of sync - running master mode
 2 - in sync - running  mastermode
 3 - in sync - running slave mode
 4 - in sync - running master mode (wait to reach state 2)
"
    ::= {DoPenaltyExtreme 5}

syncStatStrDoPenaltyExtreme  OBJECT-TYPE
    SYNTAX      OCTET STRING
    MAX-ACCESS  read-only
    STATUS      current
    DESCRIPTION
"
synchronization status line from file assp_sync.cfg for DoPenaltyExtreme
 0 - synchronization not configured
 1 - out of sync - running master mode
 2 - in sync - running  mastermode
 3 - in sync - running slave mode
 4 - in sync - running master mode (wait to reach state 2)
"
    ::= {DoPenaltyExtreme 6}

DoPenaltyExtremeSMTP  OBJECT-TYPE
    SYNTAX      OCTET STRING
    MAX-ACCESS  read-write
    STATUS      current
    DESCRIPTION
"
If set PBextreme will block IP's whose score meet or exceed Extreme Scoring Threshold before DELAYING, based on the IP's score from previous SMTP sessions. This can be set independently from DoPenaltyExtreme above. Whitelist, Collecting, Testmode, CopySpam, Spam-Lover is ignored.
"
    REFERENCE "Enforce Early PenaltyBox Extreme IP Profiling"
    DEFVAL { "0" }
    ::= {PenaltyBox 252}

syncStatDoPenaltyExtremeSMTP  OBJECT-TYPE
    SYNTAX      OCTET STRING
    MAX-ACCESS  read-only
    STATUS      current
    DESCRIPTION
"
synchronization status for DoPenaltyExtremeSMTP
-1 - DoPenaltyExtremeSMTP could not be synchronized
 0 - synchronization not configured
 1 - out of sync - running master mode
 2 - in sync - running  mastermode
 3 - in sync - running slave mode
 4 - in sync - running master mode (wait to reach state 2)
"
    ::= {DoPenaltyExtremeSMTP 5}

syncStatStrDoPenaltyExtremeSMTP  OBJECT-TYPE
    SYNTAX      OCTET STRING
    MAX-ACCESS  read-only
    STATUS      current
    DESCRIPTION
"
synchronization status line from file assp_sync.cfg for DoPenaltyExtremeSMTP
 0 - synchronization not configured
 1 - out of sync - running master mode
 2 - in sync - running  mastermode
 3 - in sync - running slave mode
 4 - in sync - running master mode (wait to reach state 2)
"
    ::= {DoPenaltyExtremeSMTP 6}

PenaltyExtreme  OBJECT-TYPE
    SYNTAX      OCTET STRING
    MAX-ACCESS  read-write
    STATUS      current
    DESCRIPTION
"
PBextreme will use this to determine candidates for special treatment. For example: 150.
"
    REFERENCE "Extreme Scoring Threshold"
    DEFVAL { "150" }
    ::= {PenaltyBox 253}

syncStatPenaltyExtreme  OBJECT-TYPE
    SYNTAX      OCTET STRING
    MAX-ACCESS  read-only
    STATUS      current
    DESCRIPTION
"
synchronization status for PenaltyExtreme
-1 - PenaltyExtreme could not be synchronized
 0 - synchronization not configured
 1 - out of sync - running master mode
 2 - in sync - running  mastermode
 3 - in sync - running slave mode
 4 - in sync - running master mode (wait to reach state 2)
"
    ::= {PenaltyExtreme 5}

syncStatStrPenaltyExtreme  OBJECT-TYPE
    SYNTAX      OCTET STRING
    MAX-ACCESS  read-only
    STATUS      current
    DESCRIPTION
"
synchronization status line from file assp_sync.cfg for PenaltyExtreme
 0 - synchronization not configured
 1 - out of sync - running master mode
 2 - in sync - running  mastermode
 3 - in sync - running slave mode
 4 - in sync - running master mode (wait to reach state 2)
"
    ::= {PenaltyExtreme 6}

ExtremeWL  OBJECT-TYPE
    SYNTAX      OCTET STRING
    MAX-ACCESS  read-write
    STATUS      current
    DESCRIPTION
"
Enable extreme penalties for whitelisted addresses.
"
    REFERENCE "Penalize Whitelisted"
    DEFVAL { "" }
    ::= {PenaltyBox 254}

syncStatExtremeWL  OBJECT-TYPE
    SYNTAX      OCTET STRING
    MAX-ACCESS  read-only
    STATUS      current
    DESCRIPTION
"
synchronization status for ExtremeWL
-1 - ExtremeWL could not be synchronized
 0 - synchronization not configured
 1 - out of sync - running master mode
 2 - in sync - running  mastermode
 3 - in sync - running slave mode
 4 - in sync - running master mode (wait to reach state 2)
"
    ::= {ExtremeWL 5}

syncStatStrExtremeWL  OBJECT-TYPE
    SYNTAX      OCTET STRING
    MAX-ACCESS  read-only
    STATUS      current
    DESCRIPTION
"
synchronization status line from file assp_sync.cfg for ExtremeWL
 0 - synchronization not configured
 1 - out of sync - running master mode
 2 - in sync - running  mastermode
 3 - in sync - running slave mode
 4 - in sync - running master mode (wait to reach state 2)
"
    ::= {ExtremeWL 6}

ExtremeNP  OBJECT-TYPE
    SYNTAX      OCTET STRING
    MAX-ACCESS  read-write
    STATUS      current
    DESCRIPTION
"
Enable extreme penalties for addresses on the noProcessing list.
"
    REFERENCE "Penalize NonProcessing"
    DEFVAL { "" }
    ::= {PenaltyBox 255}

syncStatExtremeNP  OBJECT-TYPE
    SYNTAX      OCTET STRING
    MAX-ACCESS  read-only
    STATUS      current
    DESCRIPTION
"
synchronization status for ExtremeNP
-1 - ExtremeNP could not be synchronized
 0 - synchronization not configured
 1 - out of sync - running master mode
 2 - in sync - running  mastermode
 3 - in sync - running slave mode
 4 - in sync - running master mode (wait to reach state 2)
"
    ::= {ExtremeNP 5}

syncStatStrExtremeNP  OBJECT-TYPE
    SYNTAX      OCTET STRING
    MAX-ACCESS  read-only
    STATUS      current
    DESCRIPTION
"
synchronization status line from file assp_sync.cfg for ExtremeNP
 0 - synchronization not configured
 1 - out of sync - running master mode
 2 - in sync - running  mastermode
 3 - in sync - running slave mode
 4 - in sync - running master mode (wait to reach state 2)
"
    ::= {ExtremeNP 6}

ExtremeExpiration  OBJECT-TYPE
    SYNTAX      OCTET STRING
    MAX-ACCESS  read-write
    STATUS      current
    DESCRIPTION
"
Extreme penalties will expire after this number of days. For example: 7
"
    REFERENCE "Expiration Time for Extreme Penalties"
    DEFVAL { "7" }
    ::= {PenaltyBox 256}

syncStatExtremeExpiration  OBJECT-TYPE
    SYNTAX      OCTET STRING
    MAX-ACCESS  read-only
    STATUS      current
    DESCRIPTION
"
synchronization status for ExtremeExpiration
-1 - ExtremeExpiration could not be synchronized
 0 - synchronization not configured
 1 - out of sync - running master mode
 2 - in sync - running  mastermode
 3 - in sync - running slave mode
 4 - in sync - running master mode (wait to reach state 2)
"
    ::= {ExtremeExpiration 5}

syncStatStrExtremeExpiration  OBJECT-TYPE
    SYNTAX      OCTET STRING
    MAX-ACCESS  read-only
    STATUS      current
    DESCRIPTION
"
synchronization status line from file assp_sync.cfg for ExtremeExpiration
 0 - synchronization not configured
 1 - out of sync - running master mode
 2 - in sync - running  mastermode
 3 - in sync - running slave mode
 4 - in sync - running master mode (wait to reach state 2)
"
    ::= {ExtremeExpiration 6}

DoExtremeExport  OBJECT-TYPE
    SYNTAX      OCTET STRING
    MAX-ACCESS  read-write
    STATUS      current
    DESCRIPTION
"

"
    REFERENCE "Do Export Penalty BlackBox Extreme"
    DEFVAL { "" }
    ::= {PenaltyBox 257}

syncStatDoExtremeExport  OBJECT-TYPE
    SYNTAX      OCTET STRING
    MAX-ACCESS  read-only
    STATUS      current
    DESCRIPTION
"
synchronization status for DoExtremeExport
-1 - DoExtremeExport could not be synchronized
 0 - synchronization not configured
 1 - out of sync - running master mode
 2 - in sync - running  mastermode
 3 - in sync - running slave mode
 4 - in sync - running master mode (wait to reach state 2)
"
    ::= {DoExtremeExport 5}

syncStatStrDoExtremeExport  OBJECT-TYPE
    SYNTAX      OCTET STRING
    MAX-ACCESS  read-only
    STATUS      current
    DESCRIPTION
"
synchronization status line from file assp_sync.cfg for DoExtremeExport
 0 - synchronization not configured
 1 - out of sync - running master mode
 2 - in sync - running  mastermode
 3 - in sync - running slave mode
 4 - in sync - running master mode (wait to reach state 2)
"
    ::= {DoExtremeExport 6}

DoExtremeExportAppend  OBJECT-TYPE
    SYNTAX      OCTET STRING
    MAX-ACCESS  read-write
    STATUS      current
    DESCRIPTION
"
Do not overwrite the export file but append to it.
"
    REFERENCE "Append Export File"
    DEFVAL { "" }
    ::= {PenaltyBox 258}

syncStatDoExtremeExportAppend  OBJECT-TYPE
    SYNTAX      OCTET STRING
    MAX-ACCESS  read-only
    STATUS      current
    DESCRIPTION
"
synchronization status for DoExtremeExportAppend
-1 - DoExtremeExportAppend could not be synchronized
 0 - synchronization not configured
 1 - out of sync - running master mode
 2 - in sync - running  mastermode
 3 - in sync - running slave mode
 4 - in sync - running master mode (wait to reach state 2)
"
    ::= {DoExtremeExportAppend 5}

syncStatStrDoExtremeExportAppend  OBJECT-TYPE
    SYNTAX      OCTET STRING
    MAX-ACCESS  read-only
    STATUS      current
    DESCRIPTION
"
synchronization status line from file assp_sync.cfg for DoExtremeExportAppend
 0 - synchronization not configured
 1 - out of sync - running master mode
 2 - in sync - running  mastermode
 3 - in sync - running slave mode
 4 - in sync - running master mode (wait to reach state 2)
"
    ::= {DoExtremeExportAppend 6}

exportInterval  OBJECT-TYPE
    SYNTAX      OCTET STRING
    MAX-ACCESS  read-write
    STATUS      current
    DESCRIPTION
"
 Exported Penalty Black Box Extreme File every this hours.
  Defaults to 6 hours.
"
    REFERENCE "Export BlackBox Extreme File Interval <sup>s</sup>"
    DEFVAL { "6" }
    ::= {PenaltyBox 259}

syncStatexportInterval  OBJECT-TYPE
    SYNTAX      OCTET STRING
    MAX-ACCESS  read-only
    STATUS      current
    DESCRIPTION
"
synchronization status for exportInterval
-1 - exportInterval could not be synchronized
 0 - synchronization not configured
 1 - out of sync - running master mode
 2 - in sync - running  mastermode
 3 - in sync - running slave mode
 4 - in sync - running master mode (wait to reach state 2)
"
    ::= {exportInterval 5}

syncStatStrexportInterval  OBJECT-TYPE
    SYNTAX      OCTET STRING
    MAX-ACCESS  read-only
    STATUS      current
    DESCRIPTION
"
synchronization status line from file assp_sync.cfg for exportInterval
 0 - synchronization not configured
 1 - out of sync - running master mode
 2 - in sync - running  mastermode
 3 - in sync - running slave mode
 4 - in sync - running master mode (wait to reach state 2)
"
    ::= {exportInterval 6}

exportExtremeBlack  OBJECT-TYPE
    SYNTAX      OCTET STRING
    MAX-ACCESS  read-write
    STATUS      current
    DESCRIPTION
"
IP's in Penalty BlackBox which surpassed the extreme level will be regularly stored into this file. May be used for setting the firewall or similar applications.
"
    REFERENCE "Exported BlackBox Extreme File "
    DEFVAL { "file:files/exportedextreme.txt" }
    ::= {PenaltyBox 260}

syncStatexportExtremeBlack  OBJECT-TYPE
    SYNTAX      OCTET STRING
    MAX-ACCESS  read-only
    STATUS      current
    DESCRIPTION
"
synchronization status for exportExtremeBlack
-1 - exportExtremeBlack could not be synchronized
 0 - synchronization not configured
 1 - out of sync - running master mode
 2 - in sync - running  mastermode
 3 - in sync - running slave mode
 4 - in sync - running master mode (wait to reach state 2)
"
    ::= {exportExtremeBlack 5}

syncStatStrexportExtremeBlack  OBJECT-TYPE
    SYNTAX      OCTET STRING
    MAX-ACCESS  read-only
    STATUS      current
    DESCRIPTION
"
synchronization status line from file assp_sync.cfg for exportExtremeBlack
 0 - synchronization not configured
 1 - out of sync - running master mode
 2 - in sync - running  mastermode
 3 - in sync - running slave mode
 4 - in sync - running master mode (wait to reach state 2)
"
    ::= {exportExtremeBlack 6}

DoNotPenalizeRed  OBJECT-TYPE
    SYNTAX      OCTET STRING
    MAX-ACCESS  read-write
    STATUS      current
    DESCRIPTION
"
IP's matching Red Regex or Redlist will not collect scoring values from PenaltyBox.
"
    REFERENCE "Do Not Score IP's in Redlisted Messages"
    DEFVAL { "" }
    ::= {PenaltyBox 261}

syncStatDoNotPenalizeRed  OBJECT-TYPE
    SYNTAX      OCTET STRING
    MAX-ACCESS  read-only
    STATUS      current
    DESCRIPTION
"
synchronization status for DoNotPenalizeRed
-1 - DoNotPenalizeRed could not be synchronized
 0 - synchronization not configured
 1 - out of sync - running master mode
 2 - in sync - running  mastermode
 3 - in sync - running slave mode
 4 - in sync - running master mode (wait to reach state 2)
"
    ::= {DoNotPenalizeRed 5}

syncStatStrDoNotPenalizeRed  OBJECT-TYPE
    SYNTAX      OCTET STRING
    MAX-ACCESS  read-only
    STATUS      current
    DESCRIPTION
"
synchronization status line from file assp_sync.cfg for DoNotPenalizeRed
 0 - synchronization not configured
 1 - out of sync - running master mode
 2 - in sync - running  mastermode
 3 - in sync - running slave mode
 4 - in sync - running master mode (wait to reach state 2)
"
    ::= {DoNotPenalizeRed 6}

DoNotPenalizeNull  OBJECT-TYPE
    SYNTAX      OCTET STRING
    MAX-ACCESS  read-write
    STATUS      current
    DESCRIPTION
"
IP's matching BounceSenders will not be IP-penalized.
"
    REFERENCE "Do Not Score IP's From Bounce/Null-Senders"
    DEFVAL { "" }
    ::= {PenaltyBox 262}

syncStatDoNotPenalizeNull  OBJECT-TYPE
    SYNTAX      OCTET STRING
    MAX-ACCESS  read-only
    STATUS      current
    DESCRIPTION
"
synchronization status for DoNotPenalizeNull
-1 - DoNotPenalizeNull could not be synchronized
 0 - synchronization not configured
 1 - out of sync - running master mode
 2 - in sync - running  mastermode
 3 - in sync - running slave mode
 4 - in sync - running master mode (wait to reach state 2)
"
    ::= {DoNotPenalizeNull 5}

syncStatStrDoNotPenalizeNull  OBJECT-TYPE
    SYNTAX      OCTET STRING
    MAX-ACCESS  read-only
    STATUS      current
    DESCRIPTION
"
synchronization status line from file assp_sync.cfg for DoNotPenalizeNull
 0 - synchronization not configured
 1 - out of sync - running master mode
 2 - in sync - running  mastermode
 3 - in sync - running slave mode
 4 - in sync - running master mode (wait to reach state 2)
"
    ::= {DoNotPenalizeNull 6}

baValencePB  OBJECT-TYPE
    SYNTAX      OCTET STRING
    MAX-ACCESS  read-write
    STATUS      current
    DESCRIPTION
"
Message/IP scoring
"
    REFERENCE "Bad Attachment, default=20 +"
    DEFVAL { "20" }
    ::= {PenaltyBox 263}

syncStatbaValencePB  OBJECT-TYPE
    SYNTAX      OCTET STRING
    MAX-ACCESS  read-only
    STATUS      current
    DESCRIPTION
"
synchronization status for baValencePB
-1 - baValencePB could not be synchronized
 0 - synchronization not configured
 1 - out of sync - running master mode
 2 - in sync - running  mastermode
 3 - in sync - running slave mode
 4 - in sync - running master mode (wait to reach state 2)
"
    ::= {baValencePB 5}

syncStatStrbaValencePB  OBJECT-TYPE
    SYNTAX      OCTET STRING
    MAX-ACCESS  read-only
    STATUS      current
    DESCRIPTION
"
synchronization status line from file assp_sync.cfg for baValencePB
 0 - synchronization not configured
 1 - out of sync - running master mode
 2 - in sync - running  mastermode
 3 - in sync - running slave mode
 4 - in sync - running master mode (wait to reach state 2)
"
    ::= {baValencePB 6}

backsctrValencePB  OBJECT-TYPE
    SYNTAX      OCTET STRING
    MAX-ACCESS  read-write
    STATUS      current
    DESCRIPTION
"
Message scoring
"
    REFERENCE "Backscatter detection, default=10 +"
    DEFVAL { "10" }
    ::= {PenaltyBox 264}

syncStatbacksctrValencePB  OBJECT-TYPE
    SYNTAX      OCTET STRING
    MAX-ACCESS  read-only
    STATUS      current
    DESCRIPTION
"
synchronization status for backsctrValencePB
-1 - backsctrValencePB could not be synchronized
 0 - synchronization not configured
 1 - out of sync - running master mode
 2 - in sync - running  mastermode
 3 - in sync - running slave mode
 4 - in sync - running master mode (wait to reach state 2)
"
    ::= {backsctrValencePB 5}

syncStatStrbacksctrValencePB  OBJECT-TYPE
    SYNTAX      OCTET STRING
    MAX-ACCESS  read-only
    STATUS      current
    DESCRIPTION
"
synchronization status line from file assp_sync.cfg for backsctrValencePB
 0 - synchronization not configured
 1 - out of sync - running master mode
 2 - in sync - running  mastermode
 3 - in sync - running slave mode
 4 - in sync - running master mode (wait to reach state 2)
"
    ::= {backsctrValencePB 6}

baysValencePB  OBJECT-TYPE
    SYNTAX      OCTET STRING
    MAX-ACCESS  read-write
    STATUS      current
    DESCRIPTION
"
Message/IP scoring
"
    REFERENCE "Bayesian, default=49 +"
    DEFVAL { "49" }
    ::= {PenaltyBox 265}

syncStatbaysValencePB  OBJECT-TYPE
    SYNTAX      OCTET STRING
    MAX-ACCESS  read-only
    STATUS      current
    DESCRIPTION
"
synchronization status for baysValencePB
-1 - baysValencePB could not be synchronized
 0 - synchronization not configured
 1 - out of sync - running master mode
 2 - in sync - running  mastermode
 3 - in sync - running slave mode
 4 - in sync - running master mode (wait to reach state 2)
"
    ::= {baysValencePB 5}

syncStatStrbaysValencePB  OBJECT-TYPE
    SYNTAX      OCTET STRING
    MAX-ACCESS  read-only
    STATUS      current
    DESCRIPTION
"
synchronization status line from file assp_sync.cfg for baysValencePB
 0 - synchronization not configured
 1 - out of sync - running master mode
 2 - in sync - running  mastermode
 3 - in sync - running slave mode
 4 - in sync - running master mode (wait to reach state 2)
"
    ::= {baysValencePB 6}

blValencePB  OBJECT-TYPE
    SYNTAX      OCTET STRING
    MAX-ACCESS  read-write
    STATUS      current
    DESCRIPTION
"
Message/IP scoring
"
    REFERENCE "Blacklisted Domain, default=20 +"
    DEFVAL { "20" }
    ::= {PenaltyBox 266}

syncStatblValencePB  OBJECT-TYPE
    SYNTAX      OCTET STRING
    MAX-ACCESS  read-only
    STATUS      current
    DESCRIPTION
"
synchronization status for blValencePB
-1 - blValencePB could not be synchronized
 0 - synchronization not configured
 1 - out of sync - running master mode
 2 - in sync - running  mastermode
 3 - in sync - running slave mode
 4 - in sync - running master mode (wait to reach state 2)
"
    ::= {blValencePB 5}

syncStatStrblValencePB  OBJECT-TYPE
    SYNTAX      OCTET STRING
    MAX-ACCESS  read-only
    STATUS      current
    DESCRIPTION
"
synchronization status line from file assp_sync.cfg for blValencePB
 0 - synchronization not configured
 1 - out of sync - running master mode
 2 - in sync - running  mastermode
 3 - in sync - running slave mode
 4 - in sync - running master mode (wait to reach state 2)
"
    ::= {blValencePB 6}

bombSuspiciousValencePB  OBJECT-TYPE
    SYNTAX      OCTET STRING
    MAX-ACCESS  read-write
    STATUS      current
    DESCRIPTION
"
Message scoring
"
    REFERENCE "Bomb Suspicious - scoring only, default=10 +"
    DEFVAL { "10" }
    ::= {PenaltyBox 267}

syncStatbombSuspiciousValencePB  OBJECT-TYPE
    SYNTAX      OCTET STRING
    MAX-ACCESS  read-only
    STATUS      current
    DESCRIPTION
"
synchronization status for bombSuspiciousValencePB
-1 - bombSuspiciousValencePB could not be synchronized
 0 - synchronization not configured
 1 - out of sync - running master mode
 2 - in sync - running  mastermode
 3 - in sync - running slave mode
 4 - in sync - running master mode (wait to reach state 2)
"
    ::= {bombSuspiciousValencePB 5}

syncStatStrbombSuspiciousValencePB  OBJECT-TYPE
    SYNTAX      OCTET STRING
    MAX-ACCESS  read-only
    STATUS      current
    DESCRIPTION
"
synchronization status line from file assp_sync.cfg for bombSuspiciousValencePB
 0 - synchronization not configured
 1 - out of sync - running master mode
 2 - in sync - running  mastermode
 3 - in sync - running slave mode
 4 - in sync - running master mode (wait to reach state 2)
"
    ::= {bombSuspiciousValencePB 6}

bombValencePB  OBJECT-TYPE
    SYNTAX      OCTET STRING
    MAX-ACCESS  read-write
    STATUS      current
    DESCRIPTION
"
Message/IP scoring
"
    REFERENCE "Bomb Expression, default=20 +"
    DEFVAL { "20" }
    ::= {PenaltyBox 268}

syncStatbombValencePB  OBJECT-TYPE
    SYNTAX      OCTET STRING
    MAX-ACCESS  read-only
    STATUS      current
    DESCRIPTION
"
synchronization status for bombValencePB
-1 - bombValencePB could not be synchronized
 0 - synchronization not configured
 1 - out of sync - running master mode
 2 - in sync - running  mastermode
 3 - in sync - running slave mode
 4 - in sync - running master mode (wait to reach state 2)
"
    ::= {bombValencePB 5}

syncStatStrbombValencePB  OBJECT-TYPE
    SYNTAX      OCTET STRING
    MAX-ACCESS  read-only
    STATUS      current
    DESCRIPTION
"
synchronization status line from file assp_sync.cfg for bombValencePB
 0 - synchronization not configured
 1 - out of sync - running master mode
 2 - in sync - running  mastermode
 3 - in sync - running slave mode
 4 - in sync - running master mode (wait to reach state 2)
"
    ::= {bombValencePB 6}

blackValencePB  OBJECT-TYPE
    SYNTAX      OCTET STRING
    MAX-ACCESS  read-write
    STATUS      current
    DESCRIPTION
"
Message/IP scoring
"
    REFERENCE "Bomb Black Expression, default=20 +"
    DEFVAL { "20" }
    ::= {PenaltyBox 269}

syncStatblackValencePB  OBJECT-TYPE
    SYNTAX      OCTET STRING
    MAX-ACCESS  read-only
    STATUS      current
    DESCRIPTION
"
synchronization status for blackValencePB
-1 - blackValencePB could not be synchronized
 0 - synchronization not configured
 1 - out of sync - running master mode
 2 - in sync - running  mastermode
 3 - in sync - running slave mode
 4 - in sync - running master mode (wait to reach state 2)
"
    ::= {blackValencePB 5}

syncStatStrblackValencePB  OBJECT-TYPE
    SYNTAX      OCTET STRING
    MAX-ACCESS  read-only
    STATUS      current
    DESCRIPTION
"
synchronization status line from file assp_sync.cfg for blackValencePB
 0 - synchronization not configured
 1 - out of sync - running master mode
 2 - in sync - running  mastermode
 3 - in sync - running slave mode
 4 - in sync - running master mode (wait to reach state 2)
"
    ::= {blackValencePB 6}

dkimValencePB  OBJECT-TYPE
    SYNTAX      OCTET STRING
    MAX-ACCESS  read-write
    STATUS      current
    DESCRIPTION
"
Message/IP scoring
"
    REFERENCE "Domain Key Verification failed, default=15 +"
    DEFVAL { "15" }
    ::= {PenaltyBox 270}

syncStatdkimValencePB  OBJECT-TYPE
    SYNTAX      OCTET STRING
    MAX-ACCESS  read-only
    STATUS      current
    DESCRIPTION
"
synchronization status for dkimValencePB
-1 - dkimValencePB could not be synchronized
 0 - synchronization not configured
 1 - out of sync - running master mode
 2 - in sync - running  mastermode
 3 - in sync - running slave mode
 4 - in sync - running master mode (wait to reach state 2)
"
    ::= {dkimValencePB 5}

syncStatStrdkimValencePB  OBJECT-TYPE
    SYNTAX      OCTET STRING
    MAX-ACCESS  read-only
    STATUS      current
    DESCRIPTION
"
synchronization status line from file assp_sync.cfg for dkimValencePB
 0 - synchronization not configured
 1 - out of sync - running master mode
 2 - in sync - running  mastermode
 3 - in sync - running slave mode
 4 - in sync - running master mode (wait to reach state 2)
"
    ::= {dkimValencePB 6}

dkimOkValencePB  OBJECT-TYPE
    SYNTAX      OCTET STRING
    MAX-ACCESS  read-write
    STATUS      current
    DESCRIPTION
"
Message Scoring Bonus
"
    REFERENCE "Domain Key Verification OK, default=0"
    DEFVAL { "0" }
    ::= {PenaltyBox 271}

syncStatdkimOkValencePB  OBJECT-TYPE
    SYNTAX      OCTET STRING
    MAX-ACCESS  read-only
    STATUS      current
    DESCRIPTION
"
synchronization status for dkimOkValencePB
-1 - dkimOkValencePB could not be synchronized
 0 - synchronization not configured
 1 - out of sync - running master mode
 2 - in sync - running  mastermode
 3 - in sync - running slave mode
 4 - in sync - running master mode (wait to reach state 2)
"
    ::= {dkimOkValencePB 5}

syncStatStrdkimOkValencePB  OBJECT-TYPE
    SYNTAX      OCTET STRING
    MAX-ACCESS  read-only
    STATUS      current
    DESCRIPTION
"
synchronization status line from file assp_sync.cfg for dkimOkValencePB
 0 - synchronization not configured
 1 - out of sync - running master mode
 2 - in sync - running  mastermode
 3 - in sync - running slave mode
 4 - in sync - running master mode (wait to reach state 2)
"
    ::= {dkimOkValencePB 6}

erValencePB  OBJECT-TYPE
    SYNTAX      OCTET STRING
    MAX-ACCESS  read-write
    STATUS      current
    DESCRIPTION
"
Message/IP scoring
"
    REFERENCE "Empty Recipients, default=5 +"
    DEFVAL { "5" }
    ::= {PenaltyBox 272}

syncStaterValencePB  OBJECT-TYPE
    SYNTAX      OCTET STRING
    MAX-ACCESS  read-only
    STATUS      current
    DESCRIPTION
"
synchronization status for erValencePB
-1 - erValencePB could not be synchronized
 0 - synchronization not configured
 1 - out of sync - running master mode
 2 - in sync - running  mastermode
 3 - in sync - running slave mode
 4 - in sync - running master mode (wait to reach state 2)
"
    ::= {erValencePB 5}

syncStatStrerValencePB  OBJECT-TYPE
    SYNTAX      OCTET STRING
    MAX-ACCESS  read-only
    STATUS      current
    DESCRIPTION
"
synchronization status line from file assp_sync.cfg for erValencePB
 0 - synchronization not configured
 1 - out of sync - running master mode
 2 - in sync - running  mastermode
 3 - in sync - running slave mode
 4 - in sync - running master mode (wait to reach state 2)
"
    ::= {erValencePB 6}

etValencePB  OBJECT-TYPE
    SYNTAX      OCTET STRING
    MAX-ACCESS  read-write
    STATUS      current
    DESCRIPTION
"
Message/IP scoring for clients who talk before server's greeting is sent. An value of zero will disable this check - otherwise assp scores the IP and droppes the connection.
"
    REFERENCE "Early Talker Scoring, default=25 +"
    DEFVAL { "25" }
    ::= {PenaltyBox 273}

syncStatetValencePB  OBJECT-TYPE
    SYNTAX      OCTET STRING
    MAX-ACCESS  read-only
    STATUS      current
    DESCRIPTION
"
synchronization status for etValencePB
-1 - etValencePB could not be synchronized
 0 - synchronization not configured
 1 - out of sync - running master mode
 2 - in sync - running  mastermode
 3 - in sync - running slave mode
 4 - in sync - running master mode (wait to reach state 2)
"
    ::= {etValencePB 5}

syncStatStretValencePB  OBJECT-TYPE
    SYNTAX      OCTET STRING
    MAX-ACCESS  read-only
    STATUS      current
    DESCRIPTION
"
synchronization status line from file assp_sync.cfg for etValencePB
 0 - synchronization not configured
 1 - out of sync - running master mode
 2 - in sync - running  mastermode
 3 - in sync - running slave mode
 4 - in sync - running master mode (wait to reach state 2)
"
    ::= {etValencePB 6}

fhValencePB  OBJECT-TYPE
    SYNTAX      OCTET STRING
    MAX-ACCESS  read-write
    STATUS      current
    DESCRIPTION
"
Message/IP scoring
"
    REFERENCE "Forged HELO, default=150 +"
    DEFVAL { "150" }
    ::= {PenaltyBox 274}

syncStatfhValencePB  OBJECT-TYPE
    SYNTAX      OCTET STRING
    MAX-ACCESS  read-only
    STATUS      current
    DESCRIPTION
"
synchronization status for fhValencePB
-1 - fhValencePB could not be synchronized
 0 - synchronization not configured
 1 - out of sync - running master mode
 2 - in sync - running  mastermode
 3 - in sync - running slave mode
 4 - in sync - running master mode (wait to reach state 2)
"
    ::= {fhValencePB 5}

syncStatStrfhValencePB  OBJECT-TYPE
    SYNTAX      OCTET STRING
    MAX-ACCESS  read-only
    STATUS      current
    DESCRIPTION
"
synchronization status line from file assp_sync.cfg for fhValencePB
 0 - synchronization not configured
 1 - out of sync - running master mode
 2 - in sync - running  mastermode
 3 - in sync - running slave mode
 4 - in sync - running master mode (wait to reach state 2)
"
    ::= {fhValencePB 6}

fiphValencePB  OBJECT-TYPE
    SYNTAX      OCTET STRING
    MAX-ACCESS  read-write
    STATUS      current
    DESCRIPTION
"
Message/IP scoring
"
    REFERENCE "Suspicious HELO: IP in HELO, default=39 +"
    DEFVAL { "39" }
    ::= {PenaltyBox 275}

syncStatfiphValencePB  OBJECT-TYPE
    SYNTAX      OCTET STRING
    MAX-ACCESS  read-only
    STATUS      current
    DESCRIPTION
"
synchronization status for fiphValencePB
-1 - fiphValencePB could not be synchronized
 0 - synchronization not configured
 1 - out of sync - running master mode
 2 - in sync - running  mastermode
 3 - in sync - running slave mode
 4 - in sync - running master mode (wait to reach state 2)
"
    ::= {fiphValencePB 5}

syncStatStrfiphValencePB  OBJECT-TYPE
    SYNTAX      OCTET STRING
    MAX-ACCESS  read-only
    STATUS      current
    DESCRIPTION
"
synchronization status line from file assp_sync.cfg for fiphValencePB
 0 - synchronization not configured
 1 - out of sync - running master mode
 2 - in sync - running  mastermode
 3 - in sync - running slave mode
 4 - in sync - running master mode (wait to reach state 2)
"
    ::= {fiphValencePB 6}

fiphmValencePB  OBJECT-TYPE
    SYNTAX      OCTET STRING
    MAX-ACCESS  read-write
    STATUS      current
    DESCRIPTION
"
Message/IP scoring
"
    REFERENCE "Suspicious HELO: IP in HELO mismatch, default=60 +"
    DEFVAL { "60" }
    ::= {PenaltyBox 276}

syncStatfiphmValencePB  OBJECT-TYPE
    SYNTAX      OCTET STRING
    MAX-ACCESS  read-only
    STATUS      current
    DESCRIPTION
"
synchronization status for fiphmValencePB
-1 - fiphmValencePB could not be synchronized
 0 - synchronization not configured
 1 - out of sync - running master mode
 2 - in sync - running  mastermode
 3 - in sync - running slave mode
 4 - in sync - running master mode (wait to reach state 2)
"
    ::= {fiphmValencePB 5}

syncStatStrfiphmValencePB  OBJECT-TYPE
    SYNTAX      OCTET STRING
    MAX-ACCESS  read-only
    STATUS      current
    DESCRIPTION
"
synchronization status line from file assp_sync.cfg for fiphmValencePB
 0 - synchronization not configured
 1 - out of sync - running master mode
 2 - in sync - running  mastermode
 3 - in sync - running slave mode
 4 - in sync - running master mode (wait to reach state 2)
"
    ::= {fiphmValencePB 6}

flValencePB  OBJECT-TYPE
    SYNTAX      OCTET STRING
    MAX-ACCESS  read-write
    STATUS      current
    DESCRIPTION
"
Message/IP scoring
"
    REFERENCE "Invalid Local Sender, default=20 +"
    DEFVAL { "20" }
    ::= {PenaltyBox 277}

syncStatflValencePB  OBJECT-TYPE
    SYNTAX      OCTET STRING
    MAX-ACCESS  read-only
    STATUS      current
    DESCRIPTION
"
synchronization status for flValencePB
-1 - flValencePB could not be synchronized
 0 - synchronization not configured
 1 - out of sync - running master mode
 2 - in sync - running  mastermode
 3 - in sync - running slave mode
 4 - in sync - running master mode (wait to reach state 2)
"
    ::= {flValencePB 5}

syncStatStrflValencePB  OBJECT-TYPE
    SYNTAX      OCTET STRING
    MAX-ACCESS  read-only
    STATUS      current
    DESCRIPTION
"
synchronization status line from file assp_sync.cfg for flValencePB
 0 - synchronization not configured
 1 - out of sync - running master mode
 2 - in sync - running  mastermode
 3 - in sync - running slave mode
 4 - in sync - running master mode (wait to reach state 2)
"
    ::= {flValencePB 6}

hlValencePB  OBJECT-TYPE
    SYNTAX      OCTET STRING
    MAX-ACCESS  read-write
    STATUS      current
    DESCRIPTION
"
Message/IP scoring
"
    REFERENCE "Blacklisted/Good HELO, default=20 +"
    DEFVAL { "20" }
    ::= {PenaltyBox 278}

syncStathlValencePB  OBJECT-TYPE
    SYNTAX      OCTET STRING
    MAX-ACCESS  read-only
    STATUS      current
    DESCRIPTION
"
synchronization status for hlValencePB
-1 - hlValencePB could not be synchronized
 0 - synchronization not configured
 1 - out of sync - running master mode
 2 - in sync - running  mastermode
 3 - in sync - running slave mode
 4 - in sync - running master mode (wait to reach state 2)
"
    ::= {hlValencePB 5}

syncStatStrhlValencePB  OBJECT-TYPE
    SYNTAX      OCTET STRING
    MAX-ACCESS  read-only
    STATUS      current
    DESCRIPTION
"
synchronization status line from file assp_sync.cfg for hlValencePB
 0 - synchronization not configured
 1 - out of sync - running master mode
 2 - in sync - running  mastermode
 3 - in sync - running slave mode
 4 - in sync - running master mode (wait to reach state 2)
"
    ::= {hlValencePB 6}

iaValencePB  OBJECT-TYPE
    SYNTAX      OCTET STRING
    MAX-ACCESS  read-write
    STATUS      current
    DESCRIPTION
"
Message/IP scoring
"
    REFERENCE "Internal Only Address, default=25 +"
    DEFVAL { "25" }
    ::= {PenaltyBox 279}

syncStatiaValencePB  OBJECT-TYPE
    SYNTAX      OCTET STRING
    MAX-ACCESS  read-only
    STATUS      current
    DESCRIPTION
"
synchronization status for iaValencePB
-1 - iaValencePB could not be synchronized
 0 - synchronization not configured
 1 - out of sync - running master mode
 2 - in sync - running  mastermode
 3 - in sync - running slave mode
 4 - in sync - running master mode (wait to reach state 2)
"
    ::= {iaValencePB 5}

syncStatStriaValencePB  OBJECT-TYPE
    SYNTAX      OCTET STRING
    MAX-ACCESS  read-only
    STATUS      current
    DESCRIPTION
"
synchronization status line from file assp_sync.cfg for iaValencePB
 0 - synchronization not configured
 1 - out of sync - running master mode
 2 - in sync - running  mastermode
 3 - in sync - running slave mode
 4 - in sync - running master mode (wait to reach state 2)
"
    ::= {iaValencePB 6}

idValencePB  OBJECT-TYPE
    SYNTAX      OCTET STRING
    MAX-ACCESS  read-write
    STATUS      current
    DESCRIPTION
"
Message/IP scoring
"
    REFERENCE "Domain Changing IP Frequency, default=150 +"
    DEFVAL { "150" }
    ::= {PenaltyBox 280}

syncStatidValencePB  OBJECT-TYPE
    SYNTAX      OCTET STRING
    MAX-ACCESS  read-only
    STATUS      current
    DESCRIPTION
"
synchronization status for idValencePB
-1 - idValencePB could not be synchronized
 0 - synchronization not configured
 1 - out of sync - running master mode
 2 - in sync - running  mastermode
 3 - in sync - running slave mode
 4 - in sync - running master mode (wait to reach state 2)
"
    ::= {idValencePB 5}

syncStatStridValencePB  OBJECT-TYPE
    SYNTAX      OCTET STRING
    MAX-ACCESS  read-only
    STATUS      current
    DESCRIPTION
"
synchronization status line from file assp_sync.cfg for idValencePB
 0 - synchronization not configured
 1 - out of sync - running master mode
 2 - in sync - running  mastermode
 3 - in sync - running slave mode
 4 - in sync - running master mode (wait to reach state 2)
"
    ::= {idValencePB 6}

ifValencePB  OBJECT-TYPE
    SYNTAX      OCTET STRING
    MAX-ACCESS  read-write
    STATUS      current
    DESCRIPTION
"
Message/IP scoring
"
    REFERENCE "IP Frequency, default=150 +"
    DEFVAL { "150" }
    ::= {PenaltyBox 281}

syncStatifValencePB  OBJECT-TYPE
    SYNTAX      OCTET STRING
    MAX-ACCESS  read-only
    STATUS      current
    DESCRIPTION
"
synchronization status for ifValencePB
-1 - ifValencePB could not be synchronized
 0 - synchronization not configured
 1 - out of sync - running master mode
 2 - in sync - running  mastermode
 3 - in sync - running slave mode
 4 - in sync - running master mode (wait to reach state 2)
"
    ::= {ifValencePB 5}

syncStatStrifValencePB  OBJECT-TYPE
    SYNTAX      OCTET STRING
    MAX-ACCESS  read-only
    STATUS      current
    DESCRIPTION
"
synchronization status line from file assp_sync.cfg for ifValencePB
 0 - synchronization not configured
 1 - out of sync - running master mode
 2 - in sync - running  mastermode
 3 - in sync - running slave mode
 4 - in sync - running master mode (wait to reach state 2)
"
    ::= {ifValencePB 6}

iplValencePB  OBJECT-TYPE
    SYNTAX      OCTET STRING
    MAX-ACCESS  read-write
    STATUS      current
    DESCRIPTION
"
Message/IP scoring
"
    REFERENCE "IP Parallel Sessions, default=5 +"
    DEFVAL { "5" }
    ::= {PenaltyBox 282}

syncStatiplValencePB  OBJECT-TYPE
    SYNTAX      OCTET STRING
    MAX-ACCESS  read-only
    STATUS      current
    DESCRIPTION
"
synchronization status for iplValencePB
-1 - iplValencePB could not be synchronized
 0 - synchronization not configured
 1 - out of sync - running master mode
 2 - in sync - running  mastermode
 3 - in sync - running slave mode
 4 - in sync - running master mode (wait to reach state 2)
"
    ::= {iplValencePB 5}

syncStatStriplValencePB  OBJECT-TYPE
    SYNTAX      OCTET STRING
    MAX-ACCESS  read-only
    STATUS      current
    DESCRIPTION
"
synchronization status line from file assp_sync.cfg for iplValencePB
 0 - synchronization not configured
 1 - out of sync - running master mode
 2 - in sync - running  mastermode
 3 - in sync - running slave mode
 4 - in sync - running master mode (wait to reach state 2)
"
    ::= {iplValencePB 6}

ihValencePB  OBJECT-TYPE
    SYNTAX      OCTET STRING
    MAX-ACCESS  read-write
    STATUS      current
    DESCRIPTION
"
Message/IP scoring
"
    REFERENCE "Invalid HELO, default=10 +"
    DEFVAL { "10" }
    ::= {PenaltyBox 283}

syncStatihValencePB  OBJECT-TYPE
    SYNTAX      OCTET STRING
    MAX-ACCESS  read-only
    STATUS      current
    DESCRIPTION
"
synchronization status for ihValencePB
-1 - ihValencePB could not be synchronized
 0 - synchronization not configured
 1 - out of sync - running master mode
 2 - in sync - running  mastermode
 3 - in sync - running slave mode
 4 - in sync - running master mode (wait to reach state 2)
"
    ::= {ihValencePB 5}

syncStatStrihValencePB  OBJECT-TYPE
    SYNTAX      OCTET STRING
    MAX-ACCESS  read-only
    STATUS      current
    DESCRIPTION
"
synchronization status line from file assp_sync.cfg for ihValencePB
 0 - synchronization not configured
 1 - out of sync - running master mode
 2 - in sync - running  mastermode
 3 - in sync - running slave mode
 4 - in sync - running master mode (wait to reach state 2)
"
    ::= {ihValencePB 6}

mdrValencePB  OBJECT-TYPE
    SYNTAX      OCTET STRING
    MAX-ACCESS  read-write
    STATUS      current
    DESCRIPTION
"
Message/IP scoring
"
    REFERENCE "Duplicate Recipient, default=10 +"
    DEFVAL { "10" }
    ::= {PenaltyBox 284}

syncStatmdrValencePB  OBJECT-TYPE
    SYNTAX      OCTET STRING
    MAX-ACCESS  read-only
    STATUS      current
    DESCRIPTION
"
synchronization status for mdrValencePB
-1 - mdrValencePB could not be synchronized
 0 - synchronization not configured
 1 - out of sync - running master mode
 2 - in sync - running  mastermode
 3 - in sync - running slave mode
 4 - in sync - running master mode (wait to reach state 2)
"
    ::= {mdrValencePB 5}

syncStatStrmdrValencePB  OBJECT-TYPE
    SYNTAX      OCTET STRING
    MAX-ACCESS  read-only
    STATUS      current
    DESCRIPTION
"
synchronization status line from file assp_sync.cfg for mdrValencePB
 0 - synchronization not configured
 1 - out of sync - running master mode
 2 - in sync - running  mastermode
 3 - in sync - running slave mode
 4 - in sync - running master mode (wait to reach state 2)
"
    ::= {mdrValencePB 6}

midmValencePB  OBJECT-TYPE
    SYNTAX      OCTET STRING
    MAX-ACCESS  read-write
    STATUS      current
    DESCRIPTION
"
Message/IP scoring
"
    REFERENCE "Missing Message-ID, default=10 +"
    DEFVAL { "10" }
    ::= {PenaltyBox 285}

syncStatmidmValencePB  OBJECT-TYPE
    SYNTAX      OCTET STRING
    MAX-ACCESS  read-only
    STATUS      current
    DESCRIPTION
"
synchronization status for midmValencePB
-1 - midmValencePB could not be synchronized
 0 - synchronization not configured
 1 - out of sync - running master mode
 2 - in sync - running  mastermode
 3 - in sync - running slave mode
 4 - in sync - running master mode (wait to reach state 2)
"
    ::= {midmValencePB 5}

syncStatStrmidmValencePB  OBJECT-TYPE
    SYNTAX      OCTET STRING
    MAX-ACCESS  read-only
    STATUS      current
    DESCRIPTION
"
synchronization status line from file assp_sync.cfg for midmValencePB
 0 - synchronization not configured
 1 - out of sync - running master mode
 2 - in sync - running  mastermode
 3 - in sync - running slave mode
 4 - in sync - running master mode (wait to reach state 2)
"
    ::= {midmValencePB 6}

midsValencePB  OBJECT-TYPE
    SYNTAX      OCTET STRING
    MAX-ACCESS  read-write
    STATUS      current
    DESCRIPTION
"
Message/IP scoring
"
    REFERENCE "Suspicious Message-ID, default=10 +"
    DEFVAL { "10" }
    ::= {PenaltyBox 286}

syncStatmidsValencePB  OBJECT-TYPE
    SYNTAX      OCTET STRING
    MAX-ACCESS  read-only
    STATUS      current
    DESCRIPTION
"
synchronization status for midsValencePB
-1 - midsValencePB could not be synchronized
 0 - synchronization not configured
 1 - out of sync - running master mode
 2 - in sync - running  mastermode
 3 - in sync - running slave mode
 4 - in sync - running master mode (wait to reach state 2)
"
    ::= {midsValencePB 5}

syncStatStrmidsValencePB  OBJECT-TYPE
    SYNTAX      OCTET STRING
    MAX-ACCESS  read-only
    STATUS      current
    DESCRIPTION
"
synchronization status line from file assp_sync.cfg for midsValencePB
 0 - synchronization not configured
 1 - out of sync - running master mode
 2 - in sync - running  mastermode
 3 - in sync - running slave mode
 4 - in sync - running master mode (wait to reach state 2)
"
    ::= {midsValencePB 6}

midiValencePB  OBJECT-TYPE
    SYNTAX      OCTET STRING
    MAX-ACCESS  read-write
    STATUS      current
    DESCRIPTION
"
Message/IP scoring
"
    REFERENCE "Invalid Message-ID, default=10 +"
    DEFVAL { "10" }
    ::= {PenaltyBox 287}

syncStatmidiValencePB  OBJECT-TYPE
    SYNTAX      OCTET STRING
    MAX-ACCESS  read-only
    STATUS      current
    DESCRIPTION
"
synchronization status for midiValencePB
-1 - midiValencePB could not be synchronized
 0 - synchronization not configured
 1 - out of sync - running master mode
 2 - in sync - running  mastermode
 3 - in sync - running slave mode
 4 - in sync - running master mode (wait to reach state 2)
"
    ::= {midiValencePB 5}

syncStatStrmidiValencePB  OBJECT-TYPE
    SYNTAX      OCTET STRING
    MAX-ACCESS  read-only
    STATUS      current
    DESCRIPTION
"
synchronization status line from file assp_sync.cfg for midiValencePB
 0 - synchronization not configured
 1 - out of sync - running master mode
 2 - in sync - running  mastermode
 3 - in sync - running slave mode
 4 - in sync - running master mode (wait to reach state 2)
"
    ::= {midiValencePB 6}

fbmtvValencePB  OBJECT-TYPE
    SYNTAX      OCTET STRING
    MAX-ACCESS  read-write
    STATUS      current
    DESCRIPTION
"
Message/IP scoring
"
    REFERENCE "Invalid FBMTV check, default=25 +"
    DEFVAL { "25" }
    ::= {PenaltyBox 288}

syncStatfbmtvValencePB  OBJECT-TYPE
    SYNTAX      OCTET STRING
    MAX-ACCESS  read-only
    STATUS      current
    DESCRIPTION
"
synchronization status for fbmtvValencePB
-1 - fbmtvValencePB could not be synchronized
 0 - synchronization not configured
 1 - out of sync - running master mode
 2 - in sync - running  mastermode
 3 - in sync - running slave mode
 4 - in sync - running master mode (wait to reach state 2)
"
    ::= {fbmtvValencePB 5}

syncStatStrfbmtvValencePB  OBJECT-TYPE
    SYNTAX      OCTET STRING
    MAX-ACCESS  read-only
    STATUS      current
    DESCRIPTION
"
synchronization status line from file assp_sync.cfg for fbmtvValencePB
 0 - synchronization not configured
 1 - out of sync - running master mode
 2 - in sync - running  mastermode
 3 - in sync - running slave mode
 4 - in sync - running master mode (wait to reach state 2)
"
    ::= {fbmtvValencePB 6}

batvValencePB  OBJECT-TYPE
    SYNTAX      OCTET STRING
    MAX-ACCESS  read-write
    STATUS      current
    DESCRIPTION
"
Message/IP scoring
"
    REFERENCE "Invalid BATV check, default=25 +"
    DEFVAL { "25" }
    ::= {PenaltyBox 289}

syncStatbatvValencePB  OBJECT-TYPE
    SYNTAX      OCTET STRING
    MAX-ACCESS  read-only
    STATUS      current
    DESCRIPTION
"
synchronization status for batvValencePB
-1 - batvValencePB could not be synchronized
 0 - synchronization not configured
 1 - out of sync - running master mode
 2 - in sync - running  mastermode
 3 - in sync - running slave mode
 4 - in sync - running master mode (wait to reach state 2)
"
    ::= {batvValencePB 5}

syncStatStrbatvValencePB  OBJECT-TYPE
    SYNTAX      OCTET STRING
    MAX-ACCESS  read-only
    STATUS      current
    DESCRIPTION
"
synchronization status line from file assp_sync.cfg for batvValencePB
 0 - synchronization not configured
 1 - out of sync - running master mode
 2 - in sync - running  mastermode
 3 - in sync - running slave mode
 4 - in sync - running master mode (wait to reach state 2)
"
    ::= {batvValencePB 6}

meValencePB  OBJECT-TYPE
    SYNTAX      OCTET STRING
    MAX-ACCESS  read-write
    STATUS      current
    DESCRIPTION
"
Message/IP scoring
"
    REFERENCE "Max Errors Exceeded, default=10 +"
    DEFVAL { "10" }
    ::= {PenaltyBox 290}

syncStatmeValencePB  OBJECT-TYPE
    SYNTAX      OCTET STRING
    MAX-ACCESS  read-only
    STATUS      current
    DESCRIPTION
"
synchronization status for meValencePB
-1 - meValencePB could not be synchronized
 0 - synchronization not configured
 1 - out of sync - running master mode
 2 - in sync - running  mastermode
 3 - in sync - running slave mode
 4 - in sync - running master mode (wait to reach state 2)
"
    ::= {meValencePB 5}

syncStatStrmeValencePB  OBJECT-TYPE
    SYNTAX      OCTET STRING
    MAX-ACCESS  read-only
    STATUS      current
    DESCRIPTION
"
synchronization status line from file assp_sync.cfg for meValencePB
 0 - synchronization not configured
 1 - out of sync - running master mode
 2 - in sync - running  mastermode
 3 - in sync - running slave mode
 4 - in sync - running master mode (wait to reach state 2)
"
    ::= {meValencePB 6}

msValencePB  OBJECT-TYPE
    SYNTAX      OCTET STRING
    MAX-ACCESS  read-write
    STATUS      current
    DESCRIPTION
"
IP scoring
"
    REFERENCE "Message Scoring Limit Exceeded, default=10 +"
    DEFVAL { "10" }
    ::= {PenaltyBox 291}

syncStatmsValencePB  OBJECT-TYPE
    SYNTAX      OCTET STRING
    MAX-ACCESS  read-only
    STATUS      current
    DESCRIPTION
"
synchronization status for msValencePB
-1 - msValencePB could not be synchronized
 0 - synchronization not configured
 1 - out of sync - running master mode
 2 - in sync - running  mastermode
 3 - in sync - running slave mode
 4 - in sync - running master mode (wait to reach state 2)
"
    ::= {msValencePB 5}

syncStatStrmsValencePB  OBJECT-TYPE
    SYNTAX      OCTET STRING
    MAX-ACCESS  read-only
    STATUS      current
    DESCRIPTION
"
synchronization status line from file assp_sync.cfg for msValencePB
 0 - synchronization not configured
 1 - out of sync - running master mode
 2 - in sync - running  mastermode
 3 - in sync - running slave mode
 4 - in sync - running master mode (wait to reach state 2)
"
    ::= {msValencePB 6}

mxValencePB  OBJECT-TYPE
    SYNTAX      OCTET STRING
    MAX-ACCESS  read-write
    STATUS      current
    DESCRIPTION
"
Message/IP scoring
"
    REFERENCE "Missing MX, default=10 +"
    DEFVAL { "10" }
    ::= {PenaltyBox 292}

syncStatmxValencePB  OBJECT-TYPE
    SYNTAX      OCTET STRING
    MAX-ACCESS  read-only
    STATUS      current
    DESCRIPTION
"
synchronization status for mxValencePB
-1 - mxValencePB could not be synchronized
 0 - synchronization not configured
 1 - out of sync - running master mode
 2 - in sync - running  mastermode
 3 - in sync - running slave mode
 4 - in sync - running master mode (wait to reach state 2)
"
    ::= {mxValencePB 5}

syncStatStrmxValencePB  OBJECT-TYPE
    SYNTAX      OCTET STRING
    MAX-ACCESS  read-only
    STATUS      current
    DESCRIPTION
"
synchronization status line from file assp_sync.cfg for mxValencePB
 0 - synchronization not configured
 1 - out of sync - running master mode
 2 - in sync - running  mastermode
 3 - in sync - running slave mode
 4 - in sync - running master mode (wait to reach state 2)
"
    ::= {mxValencePB 6}

mxaValencePB  OBJECT-TYPE
    SYNTAX      OCTET STRING
    MAX-ACCESS  read-write
    STATUS      current
    DESCRIPTION
"
Message/IP scoring
"
    REFERENCE "Missing MX &amp; A Record, default=15 +"
    DEFVAL { "15" }
    ::= {PenaltyBox 293}

syncStatmxaValencePB  OBJECT-TYPE
    SYNTAX      OCTET STRING
    MAX-ACCESS  read-only
    STATUS      current
    DESCRIPTION
"
synchronization status for mxaValencePB
-1 - mxaValencePB could not be synchronized
 0 - synchronization not configured
 1 - out of sync - running master mode
 2 - in sync - running  mastermode
 3 - in sync - running slave mode
 4 - in sync - running master mode (wait to reach state 2)
"
    ::= {mxaValencePB 5}

syncStatStrmxaValencePB  OBJECT-TYPE
    SYNTAX      OCTET STRING
    MAX-ACCESS  read-only
    STATUS      current
    DESCRIPTION
"
synchronization status line from file assp_sync.cfg for mxaValencePB
 0 - synchronization not configured
 1 - out of sync - running master mode
 2 - in sync - running  mastermode
 3 - in sync - running slave mode
 4 - in sync - running master mode (wait to reach state 2)
"
    ::= {mxaValencePB 6}

nofromValencePB  OBJECT-TYPE
    SYNTAX      OCTET STRING
    MAX-ACCESS  read-write
    STATUS      current
    DESCRIPTION
"
For Message/IP scoring in DoNoFrom.
"
    REFERENCE "No From Score, default=50 +"
    DEFVAL { "50" }
    ::= {PenaltyBox 294}

syncStatnofromValencePB  OBJECT-TYPE
    SYNTAX      OCTET STRING
    MAX-ACCESS  read-only
    STATUS      current
    DESCRIPTION
"
synchronization status for nofromValencePB
-1 - nofromValencePB could not be synchronized
 0 - synchronization not configured
 1 - out of sync - running master mode
 2 - in sync - running  mastermode
 3 - in sync - running slave mode
 4 - in sync - running master mode (wait to reach state 2)
"
    ::= {nofromValencePB 5}

syncStatStrnofromValencePB  OBJECT-TYPE
    SYNTAX      OCTET STRING
    MAX-ACCESS  read-only
    STATUS      current
    DESCRIPTION
"
synchronization status line from file assp_sync.cfg for nofromValencePB
 0 - synchronization not configured
 1 - out of sync - running master mode
 2 - in sync - running  mastermode
 3 - in sync - running slave mode
 4 - in sync - running master mode (wait to reach state 2)
"
    ::= {nofromValencePB 6}

pbeValencePB  OBJECT-TYPE
    SYNTAX      OCTET STRING
    MAX-ACCESS  read-write
    STATUS      current
    DESCRIPTION
"
Message Scoring
"
    REFERENCE "Extreme Bad IP History, TotalScore larger than PenaltyExtreme, default=25"
    DEFVAL { "25" }
    ::= {PenaltyBox 295}

syncStatpbeValencePB  OBJECT-TYPE
    SYNTAX      OCTET STRING
    MAX-ACCESS  read-only
    STATUS      current
    DESCRIPTION
"
synchronization status for pbeValencePB
-1 - pbeValencePB could not be synchronized
 0 - synchronization not configured
 1 - out of sync - running master mode
 2 - in sync - running  mastermode
 3 - in sync - running slave mode
 4 - in sync - running master mode (wait to reach state 2)
"
    ::= {pbeValencePB 5}

syncStatStrpbeValencePB  OBJECT-TYPE
    SYNTAX      OCTET STRING
    MAX-ACCESS  read-only
    STATUS      current
    DESCRIPTION
"
synchronization status line from file assp_sync.cfg for pbeValencePB
 0 - synchronization not configured
 1 - out of sync - running master mode
 2 - in sync - running  mastermode
 3 - in sync - running slave mode
 4 - in sync - running master mode (wait to reach state 2)
"
    ::= {pbeValencePB 6}

pbValencePB  OBJECT-TYPE
    SYNTAX      OCTET STRING
    MAX-ACCESS  read-write
    STATUS      current
    DESCRIPTION
"
Message Scoring
"
    REFERENCE "Bad IP History, TotalScore larger than PenaltyLimit, default=15"
    DEFVAL { "15" }
    ::= {PenaltyBox 296}

syncStatpbValencePB  OBJECT-TYPE
    SYNTAX      OCTET STRING
    MAX-ACCESS  read-only
    STATUS      current
    DESCRIPTION
"
synchronization status for pbValencePB
-1 - pbValencePB could not be synchronized
 0 - synchronization not configured
 1 - out of sync - running master mode
 2 - in sync - running  mastermode
 3 - in sync - running slave mode
 4 - in sync - running master mode (wait to reach state 2)
"
    ::= {pbValencePB 5}

syncStatStrpbValencePB  OBJECT-TYPE
    SYNTAX      OCTET STRING
    MAX-ACCESS  read-only
    STATUS      current
    DESCRIPTION
"
synchronization status line from file assp_sync.cfg for pbValencePB
 0 - synchronization not configured
 1 - out of sync - running master mode
 2 - in sync - running  mastermode
 3 - in sync - running slave mode
 4 - in sync - running master mode (wait to reach state 2)
"
    ::= {pbValencePB 6}

pbwValencePB  OBJECT-TYPE
    SYNTAX      OCTET STRING
    MAX-ACCESS  read-write
    STATUS      current
    DESCRIPTION
"
Message Scoring Bonus
"
    REFERENCE "Good IP History (IP in PB WhiteBox), default=-15"
    DEFVAL { "-15" }
    ::= {PenaltyBox 297}

syncStatpbwValencePB  OBJECT-TYPE
    SYNTAX      OCTET STRING
    MAX-ACCESS  read-only
    STATUS      current
    DESCRIPTION
"
synchronization status for pbwValencePB
-1 - pbwValencePB could not be synchronized
 0 - synchronization not configured
 1 - out of sync - running master mode
 2 - in sync - running  mastermode
 3 - in sync - running slave mode
 4 - in sync - running master mode (wait to reach state 2)
"
    ::= {pbwValencePB 5}

syncStatStrpbwValencePB  OBJECT-TYPE
    SYNTAX      OCTET STRING
    MAX-ACCESS  read-only
    STATUS      current
    DESCRIPTION
"
synchronization status line from file assp_sync.cfg for pbwValencePB
 0 - synchronization not configured
 1 - out of sync - running master mode
 2 - in sync - running  mastermode
 3 - in sync - running slave mode
 4 - in sync - running master mode (wait to reach state 2)
"
    ::= {pbwValencePB 6}

gripValencePB  OBJECT-TYPE
    SYNTAX      OCTET STRING
    MAX-ACCESS  read-write
    STATUS      current
    DESCRIPTION
"
Message scoring
"
    REFERENCE "GRIP value (+ if &gt; 0.9,- if &lt; 0.1), default=5"
    DEFVAL { "5" }
    ::= {PenaltyBox 298}

syncStatgripValencePB  OBJECT-TYPE
    SYNTAX      OCTET STRING
    MAX-ACCESS  read-only
    STATUS      current
    DESCRIPTION
"
synchronization status for gripValencePB
-1 - gripValencePB could not be synchronized
 0 - synchronization not configured
 1 - out of sync - running master mode
 2 - in sync - running  mastermode
 3 - in sync - running slave mode
 4 - in sync - running master mode (wait to reach state 2)
"
    ::= {gripValencePB 5}

syncStatStrgripValencePB  OBJECT-TYPE
    SYNTAX      OCTET STRING
    MAX-ACCESS  read-only
    STATUS      current
    DESCRIPTION
"
synchronization status line from file assp_sync.cfg for gripValencePB
 0 - synchronization not configured
 1 - out of sync - running master mode
 2 - in sync - running  mastermode
 3 - in sync - running slave mode
 4 - in sync - running master mode (wait to reach state 2)
"
    ::= {gripValencePB 6}

okValencePB  OBJECT-TYPE
    SYNTAX      OCTET STRING
    MAX-ACCESS  read-write
    STATUS      current
    DESCRIPTION
"
IP Bonus
"
    REFERENCE "Message OK, default=-25"
    DEFVAL { "-25" }
    ::= {PenaltyBox 299}

syncStatokValencePB  OBJECT-TYPE
    SYNTAX      OCTET STRING
    MAX-ACCESS  read-only
    STATUS      current
    DESCRIPTION
"
synchronization status for okValencePB
-1 - okValencePB could not be synchronized
 0 - synchronization not configured
 1 - out of sync - running master mode
 2 - in sync - running  mastermode
 3 - in sync - running slave mode
 4 - in sync - running master mode (wait to reach state 2)
"
    ::= {okValencePB 5}

syncStatStrokValencePB  OBJECT-TYPE
    SYNTAX      OCTET STRING
    MAX-ACCESS  read-only
    STATUS      current
    DESCRIPTION
"
synchronization status line from file assp_sync.cfg for okValencePB
 0 - synchronization not configured
 1 - out of sync - running master mode
 2 - in sync - running  mastermode
 3 - in sync - running slave mode
 4 - in sync - running master mode (wait to reach state 2)
"
    ::= {okValencePB 6}

ptmValencePB  OBJECT-TYPE
    SYNTAX      OCTET STRING
    MAX-ACCESS  read-write
    STATUS      current
    DESCRIPTION
"
Message/IP scoring
"
    REFERENCE "Missing PTR Record, default=10 +"
    DEFVAL { "10" }
    ::= {PenaltyBox 300}

syncStatptmValencePB  OBJECT-TYPE
    SYNTAX      OCTET STRING
    MAX-ACCESS  read-only
    STATUS      current
    DESCRIPTION
"
synchronization status for ptmValencePB
-1 - ptmValencePB could not be synchronized
 0 - synchronization not configured
 1 - out of sync - running master mode
 2 - in sync - running  mastermode
 3 - in sync - running slave mode
 4 - in sync - running master mode (wait to reach state 2)
"
    ::= {ptmValencePB 5}

syncStatStrptmValencePB  OBJECT-TYPE
    SYNTAX      OCTET STRING
    MAX-ACCESS  read-only
    STATUS      current
    DESCRIPTION
"
synchronization status line from file assp_sync.cfg for ptmValencePB
 0 - synchronization not configured
 1 - out of sync - running master mode
 2 - in sync - running  mastermode
 3 - in sync - running slave mode
 4 - in sync - running master mode (wait to reach state 2)
"
    ::= {ptmValencePB 6}

ptiValencePB  OBJECT-TYPE
    SYNTAX      OCTET STRING
    MAX-ACCESS  read-write
    STATUS      current
    DESCRIPTION
"
Message/IP scoring
"
    REFERENCE "Invalid PTR Record, default=15 +"
    DEFVAL { "15" }
    ::= {PenaltyBox 301}

syncStatptiValencePB  OBJECT-TYPE
    SYNTAX      OCTET STRING
    MAX-ACCESS  read-only
    STATUS      current
    DESCRIPTION
"
synchronization status for ptiValencePB
-1 - ptiValencePB could not be synchronized
 0 - synchronization not configured
 1 - out of sync - running master mode
 2 - in sync - running  mastermode
 3 - in sync - running slave mode
 4 - in sync - running master mode (wait to reach state 2)
"
    ::= {ptiValencePB 5}

syncStatStrptiValencePB  OBJECT-TYPE
    SYNTAX      OCTET STRING
    MAX-ACCESS  read-only
    STATUS      current
    DESCRIPTION
"
synchronization status line from file assp_sync.cfg for ptiValencePB
 0 - synchronization not configured
 1 - out of sync - running master mode
 2 - in sync - running  mastermode
 3 - in sync - running slave mode
 4 - in sync - running master mode (wait to reach state 2)
"
    ::= {ptiValencePB 6}

rblnValencePB  OBJECT-TYPE
    SYNTAX      OCTET STRING
    MAX-ACCESS  read-write
    STATUS      current
    DESCRIPTION
"
Message/IP scoring
"
    REFERENCE "DNSBL Neutral, default=35 +"
    DEFVAL { "35" }
    ::= {PenaltyBox 302}

syncStatrblnValencePB  OBJECT-TYPE
    SYNTAX      OCTET STRING
    MAX-ACCESS  read-only
    STATUS      current
    DESCRIPTION
"
synchronization status for rblnValencePB
-1 - rblnValencePB could not be synchronized
 0 - synchronization not configured
 1 - out of sync - running master mode
 2 - in sync - running  mastermode
 3 - in sync - running slave mode
 4 - in sync - running master mode (wait to reach state 2)
"
    ::= {rblnValencePB 5}

syncStatStrrblnValencePB  OBJECT-TYPE
    SYNTAX      OCTET STRING
    MAX-ACCESS  read-only
    STATUS      current
    DESCRIPTION
"
synchronization status line from file assp_sync.cfg for rblnValencePB
 0 - synchronization not configured
 1 - out of sync - running master mode
 2 - in sync - running  mastermode
 3 - in sync - running slave mode
 4 - in sync - running master mode (wait to reach state 2)
"
    ::= {rblnValencePB 6}

rblValencePB  OBJECT-TYPE
    SYNTAX      OCTET STRING
    MAX-ACCESS  read-write
    STATUS      current
    DESCRIPTION
"
Message/IP scoring
"
    REFERENCE "DNSBL Failed, default=100 +"
    DEFVAL { "100" }
    ::= {PenaltyBox 303}

syncStatrblValencePB  OBJECT-TYPE
    SYNTAX      OCTET STRING
    MAX-ACCESS  read-only
    STATUS      current
    DESCRIPTION
"
synchronization status for rblValencePB
-1 - rblValencePB could not be synchronized
 0 - synchronization not configured
 1 - out of sync - running master mode
 2 - in sync - running  mastermode
 3 - in sync - running slave mode
 4 - in sync - running master mode (wait to reach state 2)
"
    ::= {rblValencePB 5}

syncStatStrrblValencePB  OBJECT-TYPE
    SYNTAX      OCTET STRING
    MAX-ACCESS  read-only
    STATUS      current
    DESCRIPTION
"
synchronization status line from file assp_sync.cfg for rblValencePB
 0 - synchronization not configured
 1 - out of sync - running master mode
 2 - in sync - running  mastermode
 3 - in sync - running slave mode
 4 - in sync - running master mode (wait to reach state 2)
"
    ::= {rblValencePB 6}

rlValencePB  OBJECT-TYPE
    SYNTAX      OCTET STRING
    MAX-ACCESS  read-write
    STATUS      current
    DESCRIPTION
"
Message/IP scoring
"
    REFERENCE "Failed Relay Attempt, default=10 +"
    DEFVAL { "10" }
    ::= {PenaltyBox 304}

syncStatrlValencePB  OBJECT-TYPE
    SYNTAX      OCTET STRING
    MAX-ACCESS  read-only
    STATUS      current
    DESCRIPTION
"
synchronization status for rlValencePB
-1 - rlValencePB could not be synchronized
 0 - synchronization not configured
 1 - out of sync - running master mode
 2 - in sync - running  mastermode
 3 - in sync - running slave mode
 4 - in sync - running master mode (wait to reach state 2)
"
    ::= {rlValencePB 5}

syncStatStrrlValencePB  OBJECT-TYPE
    SYNTAX      OCTET STRING
    MAX-ACCESS  read-only
    STATUS      current
    DESCRIPTION
"
synchronization status line from file assp_sync.cfg for rlValencePB
 0 - synchronization not configured
 1 - out of sync - running master mode
 2 - in sync - running  mastermode
 3 - in sync - running slave mode
 4 - in sync - running master mode (wait to reach state 2)
"
    ::= {rlValencePB 6}

saValencePB  OBJECT-TYPE
    SYNTAX      OCTET STRING
    MAX-ACCESS  read-write
    STATUS      current
    DESCRIPTION
"
IP scoring
"
    REFERENCE "Spam Collect Address, default=25"
    DEFVAL { "25" }
    ::= {PenaltyBox 305}

syncStatsaValencePB  OBJECT-TYPE
    SYNTAX      OCTET STRING
    MAX-ACCESS  read-only
    STATUS      current
    DESCRIPTION
"
synchronization status for saValencePB
-1 - saValencePB could not be synchronized
 0 - synchronization not configured
 1 - out of sync - running master mode
 2 - in sync - running  mastermode
 3 - in sync - running slave mode
 4 - in sync - running master mode (wait to reach state 2)
"
    ::= {saValencePB 5}

syncStatStrsaValencePB  OBJECT-TYPE
    SYNTAX      OCTET STRING
    MAX-ACCESS  read-only
    STATUS      current
    DESCRIPTION
"
synchronization status line from file assp_sync.cfg for saValencePB
 0 - synchronization not configured
 1 - out of sync - running master mode
 2 - in sync - running  mastermode
 3 - in sync - running slave mode
 4 - in sync - running master mode (wait to reach state 2)
"
    ::= {saValencePB 6}

scriptValencePB  OBJECT-TYPE
    SYNTAX      OCTET STRING
    MAX-ACCESS  read-write
    STATUS      current
    DESCRIPTION
"
Message/IP scoring
"
    REFERENCE "Script Expression, default=25 +"
    DEFVAL { "25" }
    ::= {PenaltyBox 306}

syncStatscriptValencePB  OBJECT-TYPE
    SYNTAX      OCTET STRING
    MAX-ACCESS  read-only
    STATUS      current
    DESCRIPTION
"
synchronization status for scriptValencePB
-1 - scriptValencePB could not be synchronized
 0 - synchronization not configured
 1 - out of sync - running master mode
 2 - in sync - running  mastermode
 3 - in sync - running slave mode
 4 - in sync - running master mode (wait to reach state 2)
"
    ::= {scriptValencePB 5}

syncStatStrscriptValencePB  OBJECT-TYPE
    SYNTAX      OCTET STRING
    MAX-ACCESS  read-only
    STATUS      current
    DESCRIPTION
"
synchronization status line from file assp_sync.cfg for scriptValencePB
 0 - synchronization not configured
 1 - out of sync - running master mode
 2 - in sync - running  mastermode
 3 - in sync - running slave mode
 4 - in sync - running master mode (wait to reach state 2)
"
    ::= {scriptValencePB 6}

sbnValencePB  OBJECT-TYPE
    SYNTAX      OCTET STRING
    MAX-ACCESS  read-write
    STATUS      current
    DESCRIPTION
"
For Message/IP scoring in DoOrgBlocking/DoCountryBlocking
"
    REFERENCE "No Organization and No CountryCode, default=10 +"
    DEFVAL { "10" }
    ::= {PenaltyBox 307}

syncStatsbnValencePB  OBJECT-TYPE
    SYNTAX      OCTET STRING
    MAX-ACCESS  read-only
    STATUS      current
    DESCRIPTION
"
synchronization status for sbnValencePB
-1 - sbnValencePB could not be synchronized
 0 - synchronization not configured
 1 - out of sync - running master mode
 2 - in sync - running  mastermode
 3 - in sync - running slave mode
 4 - in sync - running master mode (wait to reach state 2)
"
    ::= {sbnValencePB 5}

syncStatStrsbnValencePB  OBJECT-TYPE
    SYNTAX      OCTET STRING
    MAX-ACCESS  read-only
    STATUS      current
    DESCRIPTION
"
synchronization status line from file assp_sync.cfg for sbnValencePB
 0 - synchronization not configured
 1 - out of sync - running master mode
 2 - in sync - running  mastermode
 3 - in sync - running slave mode
 4 - in sync - running master mode (wait to reach state 2)
"
    ::= {sbnValencePB 6}

sworgValencePB  OBJECT-TYPE
    SYNTAX      OCTET STRING
    MAX-ACCESS  read-write
    STATUS      current
    DESCRIPTION
"
 Bonus for Message/IP scoring in DoOrgWhiting
"
    REFERENCE "White Organizations Score, default=-25"
    DEFVAL { "-25" }
    ::= {PenaltyBox 308}

syncStatsworgValencePB  OBJECT-TYPE
    SYNTAX      OCTET STRING
    MAX-ACCESS  read-only
    STATUS      current
    DESCRIPTION
"
synchronization status for sworgValencePB
-1 - sworgValencePB could not be synchronized
 0 - synchronization not configured
 1 - out of sync - running master mode
 2 - in sync - running  mastermode
 3 - in sync - running slave mode
 4 - in sync - running master mode (wait to reach state 2)
"
    ::= {sworgValencePB 5}

syncStatStrsworgValencePB  OBJECT-TYPE
    SYNTAX      OCTET STRING
    MAX-ACCESS  read-only
    STATUS      current
    DESCRIPTION
"
synchronization status line from file assp_sync.cfg for sworgValencePB
 0 - synchronization not configured
 1 - out of sync - running master mode
 2 - in sync - running  mastermode
 3 - in sync - running slave mode
 4 - in sync - running master mode (wait to reach state 2)
"
    ::= {sworgValencePB 6}

sbsccValencePB  OBJECT-TYPE
    SYNTAX      OCTET STRING
    MAX-ACCESS  read-write
    STATUS      current
    DESCRIPTION
"
Message scoring
"
    REFERENCE "Suspicious Country Code, default=10"
    DEFVAL { "10" }
    ::= {PenaltyBox 309}

syncStatsbsccValencePB  OBJECT-TYPE
    SYNTAX      OCTET STRING
    MAX-ACCESS  read-only
    STATUS      current
    DESCRIPTION
"
synchronization status for sbsccValencePB
-1 - sbsccValencePB could not be synchronized
 0 - synchronization not configured
 1 - out of sync - running master mode
 2 - in sync - running  mastermode
 3 - in sync - running slave mode
 4 - in sync - running master mode (wait to reach state 2)
"
    ::= {sbsccValencePB 5}

syncStatStrsbsccValencePB  OBJECT-TYPE
    SYNTAX      OCTET STRING
    MAX-ACCESS  read-only
    STATUS      current
    DESCRIPTION
"
synchronization status line from file assp_sync.cfg for sbsccValencePB
 0 - synchronization not configured
 1 - out of sync - running master mode
 2 - in sync - running  mastermode
 3 - in sync - running slave mode
 4 - in sync - running master mode (wait to reach state 2)
"
    ::= {sbsccValencePB 6}

bccValencePB  OBJECT-TYPE
    SYNTAX      OCTET STRING
    MAX-ACCESS  read-write
    STATUS      current
    DESCRIPTION
"
For Message/IP scoring  in PenaltyBox ( DoPenalty )
"
    REFERENCE "Blocked Country Code Score, default=25 +"
    DEFVAL { "25" }
    ::= {PenaltyBox 310}

syncStatbccValencePB  OBJECT-TYPE
    SYNTAX      OCTET STRING
    MAX-ACCESS  read-only
    STATUS      current
    DESCRIPTION
"
synchronization status for bccValencePB
-1 - bccValencePB could not be synchronized
 0 - synchronization not configured
 1 - out of sync - running master mode
 2 - in sync - running  mastermode
 3 - in sync - running slave mode
 4 - in sync - running master mode (wait to reach state 2)
"
    ::= {bccValencePB 5}

syncStatStrbccValencePB  OBJECT-TYPE
    SYNTAX      OCTET STRING
    MAX-ACCESS  read-only
    STATUS      current
    DESCRIPTION
"
synchronization status line from file assp_sync.cfg for bccValencePB
 0 - synchronization not configured
 1 - out of sync - running master mode
 2 - in sync - running  mastermode
 3 - in sync - running slave mode
 4 - in sync - running master mode (wait to reach state 2)
"
    ::= {bccValencePB 6}

sbfccValencePB  OBJECT-TYPE
    SYNTAX      OCTET STRING
    MAX-ACCESS  read-write
    STATUS      current
    DESCRIPTION
"
message scoring  in PenaltyBox ( DoPenaltyMessage )
"
    REFERENCE "Foreign Country Code Score, default=10 +"
    DEFVAL { "10" }
    ::= {PenaltyBox 311}

syncStatsbfccValencePB  OBJECT-TYPE
    SYNTAX      OCTET STRING
    MAX-ACCESS  read-only
    STATUS      current
    DESCRIPTION
"
synchronization status for sbfccValencePB
-1 - sbfccValencePB could not be synchronized
 0 - synchronization not configured
 1 - out of sync - running master mode
 2 - in sync - running  mastermode
 3 - in sync - running slave mode
 4 - in sync - running master mode (wait to reach state 2)
"
    ::= {sbfccValencePB 5}

syncStatStrsbfccValencePB  OBJECT-TYPE
    SYNTAX      OCTET STRING
    MAX-ACCESS  read-only
    STATUS      current
    DESCRIPTION
"
synchronization status line from file assp_sync.cfg for sbfccValencePB
 0 - synchronization not configured
 1 - out of sync - running master mode
 2 - in sync - running  mastermode
 3 - in sync - running slave mode
 4 - in sync - running master mode (wait to reach state 2)
"
    ::= {sbfccValencePB 6}

sbhccValencePB  OBJECT-TYPE
    SYNTAX      OCTET STRING
    MAX-ACCESS  read-write
    STATUS      current
    DESCRIPTION
"
 Bonus for Message/IP Scoring  in PenaltyBox ( DoPenalty )
"
    REFERENCE "Home Country Code Score, default=-10 +"
    DEFVAL { "-10" }
    ::= {PenaltyBox 312}

syncStatsbhccValencePB  OBJECT-TYPE
    SYNTAX      OCTET STRING
    MAX-ACCESS  read-only
    STATUS      current
    DESCRIPTION
"
synchronization status for sbhccValencePB
-1 - sbhccValencePB could not be synchronized
 0 - synchronization not configured
 1 - out of sync - running master mode
 2 - in sync - running  mastermode
 3 - in sync - running slave mode
 4 - in sync - running master mode (wait to reach state 2)
"
    ::= {sbhccValencePB 5}

syncStatStrsbhccValencePB  OBJECT-TYPE
    SYNTAX      OCTET STRING
    MAX-ACCESS  read-only
    STATUS      current
    DESCRIPTION
"
synchronization status line from file assp_sync.cfg for sbhccValencePB
 0 - synchronization not configured
 1 - out of sync - running master mode
 2 - in sync - running  mastermode
 3 - in sync - running slave mode
 4 - in sync - running master mode (wait to reach state 2)
"
    ::= {sbhccValencePB 6}

sborgValencePB  OBJECT-TYPE
    SYNTAX      OCTET STRING
    MAX-ACCESS  read-write
    STATUS      current
    DESCRIPTION
"
For Message/IP scoring  in PenaltyBox ( DoPenalty )
"
    REFERENCE "Blocked Organizations Score, default=25 +"
    DEFVAL { "25" }
    ::= {PenaltyBox 313}

syncStatsborgValencePB  OBJECT-TYPE
    SYNTAX      OCTET STRING
    MAX-ACCESS  read-only
    STATUS      current
    DESCRIPTION
"
synchronization status for sborgValencePB
-1 - sborgValencePB could not be synchronized
 0 - synchronization not configured
 1 - out of sync - running master mode
 2 - in sync - running  mastermode
 3 - in sync - running slave mode
 4 - in sync - running master mode (wait to reach state 2)
"
    ::= {sborgValencePB 5}

syncStatStrsborgValencePB  OBJECT-TYPE
    SYNTAX      OCTET STRING
    MAX-ACCESS  read-only
    STATUS      current
    DESCRIPTION
"
synchronization status line from file assp_sync.cfg for sborgValencePB
 0 - synchronization not configured
 1 - out of sync - running master mode
 2 - in sync - running  mastermode
 3 - in sync - running slave mode
 4 - in sync - running master mode (wait to reach state 2)
"
    ::= {sborgValencePB 6}

spfpValencePB  OBJECT-TYPE
    SYNTAX      OCTET STRING
    MAX-ACCESS  read-write
    STATUS      current
    DESCRIPTION
"
 Bonus for Message/IP scoring with SPF
"
    REFERENCE "SPF Pass Score, default=-10"
    DEFVAL { "-10" }
    ::= {PenaltyBox 314}

syncStatspfpValencePB  OBJECT-TYPE
    SYNTAX      OCTET STRING
    MAX-ACCESS  read-only
    STATUS      current
    DESCRIPTION
"
synchronization status for spfpValencePB
-1 - spfpValencePB could not be synchronized
 0 - synchronization not configured
 1 - out of sync - running master mode
 2 - in sync - running  mastermode
 3 - in sync - running slave mode
 4 - in sync - running master mode (wait to reach state 2)
"
    ::= {spfpValencePB 5}

syncStatStrspfpValencePB  OBJECT-TYPE
    SYNTAX      OCTET STRING
    MAX-ACCESS  read-only
    STATUS      current
    DESCRIPTION
"
synchronization status line from file assp_sync.cfg for spfpValencePB
 0 - synchronization not configured
 1 - out of sync - running master mode
 2 - in sync - running  mastermode
 3 - in sync - running slave mode
 4 - in sync - running master mode (wait to reach state 2)
"
    ::= {spfpValencePB 6}

spfnValencePB  OBJECT-TYPE
    SYNTAX      OCTET STRING
    MAX-ACCESS  read-write
    STATUS      current
    DESCRIPTION
"
Message/IP scoring
"
    REFERENCE "SPF Neutral, default=5 +"
    DEFVAL { "5" }
    ::= {PenaltyBox 315}

syncStatspfnValencePB  OBJECT-TYPE
    SYNTAX      OCTET STRING
    MAX-ACCESS  read-only
    STATUS      current
    DESCRIPTION
"
synchronization status for spfnValencePB
-1 - spfnValencePB could not be synchronized
 0 - synchronization not configured
 1 - out of sync - running master mode
 2 - in sync - running  mastermode
 3 - in sync - running slave mode
 4 - in sync - running master mode (wait to reach state 2)
"
    ::= {spfnValencePB 5}

syncStatStrspfnValencePB  OBJECT-TYPE
    SYNTAX      OCTET STRING
    MAX-ACCESS  read-only
    STATUS      current
    DESCRIPTION
"
synchronization status line from file assp_sync.cfg for spfnValencePB
 0 - synchronization not configured
 1 - out of sync - running master mode
 2 - in sync - running  mastermode
 3 - in sync - running slave mode
 4 - in sync - running master mode (wait to reach state 2)
"
    ::= {spfnValencePB 6}

spfsValencePB  OBJECT-TYPE
    SYNTAX      OCTET STRING
    MAX-ACCESS  read-write
    STATUS      current
    DESCRIPTION
"
Message/IP scoring
"
    REFERENCE "SPF Softfailed, default=5 +"
    DEFVAL { "5" }
    ::= {PenaltyBox 316}

syncStatspfsValencePB  OBJECT-TYPE
    SYNTAX      OCTET STRING
    MAX-ACCESS  read-only
    STATUS      current
    DESCRIPTION
"
synchronization status for spfsValencePB
-1 - spfsValencePB could not be synchronized
 0 - synchronization not configured
 1 - out of sync - running master mode
 2 - in sync - running  mastermode
 3 - in sync - running slave mode
 4 - in sync - running master mode (wait to reach state 2)
"
    ::= {spfsValencePB 5}

syncStatStrspfsValencePB  OBJECT-TYPE
    SYNTAX      OCTET STRING
    MAX-ACCESS  read-only
    STATUS      current
    DESCRIPTION
"
synchronization status line from file assp_sync.cfg for spfsValencePB
 0 - synchronization not configured
 1 - out of sync - running master mode
 2 - in sync - running  mastermode
 3 - in sync - running slave mode
 4 - in sync - running master mode (wait to reach state 2)
"
    ::= {spfsValencePB 6}

spfnonValencePB  OBJECT-TYPE
    SYNTAX      OCTET STRING
    MAX-ACCESS  read-write
    STATUS      current
    DESCRIPTION
"
Message/IP scoring
"
    REFERENCE "SPF None, default=0 +"
    DEFVAL { "0" }
    ::= {PenaltyBox 317}

syncStatspfnonValencePB  OBJECT-TYPE
    SYNTAX      OCTET STRING
    MAX-ACCESS  read-only
    STATUS      current
    DESCRIPTION
"
synchronization status for spfnonValencePB
-1 - spfnonValencePB could not be synchronized
 0 - synchronization not configured
 1 - out of sync - running master mode
 2 - in sync - running  mastermode
 3 - in sync - running slave mode
 4 - in sync - running master mode (wait to reach state 2)
"
    ::= {spfnonValencePB 5}

syncStatStrspfnonValencePB  OBJECT-TYPE
    SYNTAX      OCTET STRING
    MAX-ACCESS  read-only
    STATUS      current
    DESCRIPTION
"
synchronization status line from file assp_sync.cfg for spfnonValencePB
 0 - synchronization not configured
 1 - out of sync - running master mode
 2 - in sync - running  mastermode
 3 - in sync - running slave mode
 4 - in sync - running master mode (wait to reach state 2)
"
    ::= {spfnonValencePB 6}

spfuValencePB  OBJECT-TYPE
    SYNTAX      OCTET STRING
    MAX-ACCESS  read-write
    STATUS      current
    DESCRIPTION
"
Message/IP scoring
"
    REFERENCE "SPF Unknown, default=0 +"
    DEFVAL { "0" }
    ::= {PenaltyBox 318}

syncStatspfuValencePB  OBJECT-TYPE
    SYNTAX      OCTET STRING
    MAX-ACCESS  read-only
    STATUS      current
    DESCRIPTION
"
synchronization status for spfuValencePB
-1 - spfuValencePB could not be synchronized
 0 - synchronization not configured
 1 - out of sync - running master mode
 2 - in sync - running  mastermode
 3 - in sync - running slave mode
 4 - in sync - running master mode (wait to reach state 2)
"
    ::= {spfuValencePB 5}

syncStatStrspfuValencePB  OBJECT-TYPE
    SYNTAX      OCTET STRING
    MAX-ACCESS  read-only
    STATUS      current
    DESCRIPTION
"
synchronization status line from file assp_sync.cfg for spfuValencePB
 0 - synchronization not configured
 1 - out of sync - running master mode
 2 - in sync - running  mastermode
 3 - in sync - running slave mode
 4 - in sync - running master mode (wait to reach state 2)
"
    ::= {spfuValencePB 6}

spfeValencePB  OBJECT-TYPE
    SYNTAX      OCTET STRING
    MAX-ACCESS  read-write
    STATUS      current
    DESCRIPTION
"
Message/IP scoring
"
    REFERENCE "SPF Error, default=5 +"
    DEFVAL { "5" }
    ::= {PenaltyBox 319}

syncStatspfeValencePB  OBJECT-TYPE
    SYNTAX      OCTET STRING
    MAX-ACCESS  read-only
    STATUS      current
    DESCRIPTION
"
synchronization status for spfeValencePB
-1 - spfeValencePB could not be synchronized
 0 - synchronization not configured
 1 - out of sync - running master mode
 2 - in sync - running  mastermode
 3 - in sync - running slave mode
 4 - in sync - running master mode (wait to reach state 2)
"
    ::= {spfeValencePB 5}

syncStatStrspfeValencePB  OBJECT-TYPE
    SYNTAX      OCTET STRING
    MAX-ACCESS  read-only
    STATUS      current
    DESCRIPTION
"
synchronization status line from file assp_sync.cfg for spfeValencePB
 0 - synchronization not configured
 1 - out of sync - running master mode
 2 - in sync - running  mastermode
 3 - in sync - running slave mode
 4 - in sync - running master mode (wait to reach state 2)
"
    ::= {spfeValencePB 6}

spfValencePB  OBJECT-TYPE
    SYNTAX      OCTET STRING
    MAX-ACCESS  read-write
    STATUS      current
    DESCRIPTION
"
Message/IP scoring
"
    REFERENCE "SPF Failed, default=10 +"
    DEFVAL { "10" }
    ::= {PenaltyBox 320}

syncStatspfValencePB  OBJECT-TYPE
    SYNTAX      OCTET STRING
    MAX-ACCESS  read-only
    STATUS      current
    DESCRIPTION
"
synchronization status for spfValencePB
-1 - spfValencePB could not be synchronized
 0 - synchronization not configured
 1 - out of sync - running master mode
 2 - in sync - running  mastermode
 3 - in sync - running slave mode
 4 - in sync - running master mode (wait to reach state 2)
"
    ::= {spfValencePB 5}

syncStatStrspfValencePB  OBJECT-TYPE
    SYNTAX      OCTET STRING
    MAX-ACCESS  read-only
    STATUS      current
    DESCRIPTION
"
synchronization status line from file assp_sync.cfg for spfValencePB
 0 - synchronization not configured
 1 - out of sync - running master mode
 2 - in sync - running  mastermode
 3 - in sync - running slave mode
 4 - in sync - running master mode (wait to reach state 2)
"
    ::= {spfValencePB 6}

srsValencePB  OBJECT-TYPE
    SYNTAX      OCTET STRING
    MAX-ACCESS  read-write
    STATUS      current
    DESCRIPTION
"
For Message/IP scoring in SRSValidateBounce
"
    REFERENCE "SRS Validate Bounce Failed Score, default=10 +"
    DEFVAL { "10" }
    ::= {PenaltyBox 321}

syncStatsrsValencePB  OBJECT-TYPE
    SYNTAX      OCTET STRING
    MAX-ACCESS  read-only
    STATUS      current
    DESCRIPTION
"
synchronization status for srsValencePB
-1 - srsValencePB could not be synchronized
 0 - synchronization not configured
 1 - out of sync - running master mode
 2 - in sync - running  mastermode
 3 - in sync - running slave mode
 4 - in sync - running master mode (wait to reach state 2)
"
    ::= {srsValencePB 5}

syncStatStrsrsValencePB  OBJECT-TYPE
    SYNTAX      OCTET STRING
    MAX-ACCESS  read-only
    STATUS      current
    DESCRIPTION
"
synchronization status line from file assp_sync.cfg for srsValencePB
 0 - synchronization not configured
 1 - out of sync - running master mode
 2 - in sync - running  mastermode
 3 - in sync - running slave mode
 4 - in sync - running master mode (wait to reach state 2)
"
    ::= {srsValencePB 6}

stValencePB  OBJECT-TYPE
    SYNTAX      OCTET STRING
    MAX-ACCESS  read-write
    STATUS      current
    DESCRIPTION
"
For Message/IP scoring
"
    REFERENCE "Penalty Trap Address, default=50 +"
    DEFVAL { "50" }
    ::= {PenaltyBox 322}

syncStatstValencePB  OBJECT-TYPE
    SYNTAX      OCTET STRING
    MAX-ACCESS  read-only
    STATUS      current
    DESCRIPTION
"
synchronization status for stValencePB
-1 - stValencePB could not be synchronized
 0 - synchronization not configured
 1 - out of sync - running master mode
 2 - in sync - running  mastermode
 3 - in sync - running slave mode
 4 - in sync - running master mode (wait to reach state 2)
"
    ::= {stValencePB 5}

syncStatStrstValencePB  OBJECT-TYPE
    SYNTAX      OCTET STRING
    MAX-ACCESS  read-only
    STATUS      current
    DESCRIPTION
"
synchronization status line from file assp_sync.cfg for stValencePB
 0 - synchronization not configured
 1 - out of sync - running master mode
 2 - in sync - running  mastermode
 3 - in sync - running slave mode
 4 - in sync - running master mode (wait to reach state 2)
"
    ::= {stValencePB 6}

tlsValencePB  OBJECT-TYPE
    SYNTAX      OCTET STRING
    MAX-ACCESS  read-write
    STATUS      current
    DESCRIPTION
"
Message Scoring/IP scoring Bonus for SSL/TLS connections
"
    REFERENCE "OK, Is a SSL/TLS connection, default=-10 +"
    DEFVAL { "-10" }
    ::= {PenaltyBox 323}

syncStattlsValencePB  OBJECT-TYPE
    SYNTAX      OCTET STRING
    MAX-ACCESS  read-only
    STATUS      current
    DESCRIPTION
"
synchronization status for tlsValencePB
-1 - tlsValencePB could not be synchronized
 0 - synchronization not configured
 1 - out of sync - running master mode
 2 - in sync - running  mastermode
 3 - in sync - running slave mode
 4 - in sync - running master mode (wait to reach state 2)
"
    ::= {tlsValencePB 5}

syncStatStrtlsValencePB  OBJECT-TYPE
    SYNTAX      OCTET STRING
    MAX-ACCESS  read-only
    STATUS      current
    DESCRIPTION
"
synchronization status line from file assp_sync.cfg for tlsValencePB
 0 - synchronization not configured
 1 - out of sync - running master mode
 2 - in sync - running  mastermode
 3 - in sync - running slave mode
 4 - in sync - running master mode (wait to reach state 2)
"
    ::= {tlsValencePB 6}

uriblnValencePB  OBJECT-TYPE
    SYNTAX      OCTET STRING
    MAX-ACCESS  read-write
    STATUS      current
    DESCRIPTION
"
Message/IP scoring
"
    REFERENCE "URIBL Neutral, default=20 +"
    DEFVAL { "20" }
    ::= {PenaltyBox 324}

syncStaturiblnValencePB  OBJECT-TYPE
    SYNTAX      OCTET STRING
    MAX-ACCESS  read-only
    STATUS      current
    DESCRIPTION
"
synchronization status for uriblnValencePB
-1 - uriblnValencePB could not be synchronized
 0 - synchronization not configured
 1 - out of sync - running master mode
 2 - in sync - running  mastermode
 3 - in sync - running slave mode
 4 - in sync - running master mode (wait to reach state 2)
"
    ::= {uriblnValencePB 5}

syncStatStruriblnValencePB  OBJECT-TYPE
    SYNTAX      OCTET STRING
    MAX-ACCESS  read-only
    STATUS      current
    DESCRIPTION
"
synchronization status line from file assp_sync.cfg for uriblnValencePB
 0 - synchronization not configured
 1 - out of sync - running master mode
 2 - in sync - running  mastermode
 3 - in sync - running slave mode
 4 - in sync - running master mode (wait to reach state 2)
"
    ::= {uriblnValencePB 6}

uriblValencePB  OBJECT-TYPE
    SYNTAX      OCTET STRING
    MAX-ACCESS  read-write
    STATUS      current
    DESCRIPTION
"
Message/IP scoring
"
    REFERENCE "URIBL Failed, default=25 +"
    DEFVAL { "25" }
    ::= {PenaltyBox 325}

syncStaturiblValencePB  OBJECT-TYPE
    SYNTAX      OCTET STRING
    MAX-ACCESS  read-only
    STATUS      current
    DESCRIPTION
"
synchronization status for uriblValencePB
-1 - uriblValencePB could not be synchronized
 0 - synchronization not configured
 1 - out of sync - running master mode
 2 - in sync - running  mastermode
 3 - in sync - running slave mode
 4 - in sync - running master mode (wait to reach state 2)
"
    ::= {uriblValencePB 5}

syncStatStruriblValencePB  OBJECT-TYPE
    SYNTAX      OCTET STRING
    MAX-ACCESS  read-only
    STATUS      current
    DESCRIPTION
"
synchronization status line from file assp_sync.cfg for uriblValencePB
 0 - synchronization not configured
 1 - out of sync - running master mode
 2 - in sync - running  mastermode
 3 - in sync - running slave mode
 4 - in sync - running master mode (wait to reach state 2)
"
    ::= {uriblValencePB 6}

vsValencePB  OBJECT-TYPE
    SYNTAX      OCTET STRING
    MAX-ACCESS  read-write
    STATUS      current
    DESCRIPTION
"
Message scoring
"
    REFERENCE "Virus suspicious, default=25"
    DEFVAL { "25" }
    ::= {PenaltyBox 326}

syncStatvsValencePB  OBJECT-TYPE
    SYNTAX      OCTET STRING
    MAX-ACCESS  read-only
    STATUS      current
    DESCRIPTION
"
synchronization status for vsValencePB
-1 - vsValencePB could not be synchronized
 0 - synchronization not configured
 1 - out of sync - running master mode
 2 - in sync - running  mastermode
 3 - in sync - running slave mode
 4 - in sync - running master mode (wait to reach state 2)
"
    ::= {vsValencePB 5}

syncStatStrvsValencePB  OBJECT-TYPE
    SYNTAX      OCTET STRING
    MAX-ACCESS  read-only
    STATUS      current
    DESCRIPTION
"
synchronization status line from file assp_sync.cfg for vsValencePB
 0 - synchronization not configured
 1 - out of sync - running master mode
 2 - in sync - running  mastermode
 3 - in sync - running slave mode
 4 - in sync - running master mode (wait to reach state 2)
"
    ::= {vsValencePB 6}

vdValencePB  OBJECT-TYPE
    SYNTAX      OCTET STRING
    MAX-ACCESS  read-write
    STATUS      current
    DESCRIPTION
"
Message/IP scoring
"
    REFERENCE "Virus detected, default=50 +"
    DEFVAL { "50" }
    ::= {PenaltyBox 327}

syncStatvdValencePB  OBJECT-TYPE
    SYNTAX      OCTET STRING
    MAX-ACCESS  read-only
    STATUS      current
    DESCRIPTION
"
synchronization status for vdValencePB
-1 - vdValencePB could not be synchronized
 0 - synchronization not configured
 1 - out of sync - running master mode
 2 - in sync - running  mastermode
 3 - in sync - running slave mode
 4 - in sync - running master mode (wait to reach state 2)
"
    ::= {vdValencePB 5}

syncStatStrvdValencePB  OBJECT-TYPE
    SYNTAX      OCTET STRING
    MAX-ACCESS  read-only
    STATUS      current
    DESCRIPTION
"
synchronization status line from file assp_sync.cfg for vdValencePB
 0 - synchronization not configured
 1 - out of sync - running master mode
 2 - in sync - running  mastermode
 3 - in sync - running slave mode
 4 - in sync - running master mode (wait to reach state 2)
"
    ::= {vdValencePB 6}

teValencePB  OBJECT-TYPE
    SYNTAX      OCTET STRING
    MAX-ACCESS  read-write
    STATUS      current
    DESCRIPTION
"
Valence for testing testRe
  
  
"
    REFERENCE "TestRe Valence, default=20 +"
    DEFVAL { "20" }
    ::= {PenaltyBox 871}

syncStatteValencePB  OBJECT-TYPE
    SYNTAX      OCTET STRING
    MAX-ACCESS  read-only
    STATUS      current
    DESCRIPTION
"
synchronization status for teValencePB
-1 - teValencePB could not be synchronized
 0 - synchronization not configured
 1 - out of sync - running master mode
 2 - in sync - running  mastermode
 3 - in sync - running slave mode
 4 - in sync - running master mode (wait to reach state 2)
"
    ::= {teValencePB 5}

syncStatStrteValencePB  OBJECT-TYPE
    SYNTAX      OCTET STRING
    MAX-ACCESS  read-only
    STATUS      current
    DESCRIPTION
"
synchronization status line from file assp_sync.cfg for teValencePB
 0 - synchronization not configured
 1 - out of sync - running master mode
 2 - in sync - running  mastermode
 3 - in sync - running slave mode
 4 - in sync - running master mode (wait to reach state 2)
"
    ::= {teValencePB 6}

idleValencePB  OBJECT-TYPE
    SYNTAX      OCTET STRING
    MAX-ACCESS  read-write
    STATUS      current
    DESCRIPTION
"
For IP scoring with smtpIdleTimeout.
"
    REFERENCE "Timeout Score"
    DEFVAL { "0" }
    ::= {PenaltyBox 887}

syncStatidleValencePB  OBJECT-TYPE
    SYNTAX      OCTET STRING
    MAX-ACCESS  read-only
    STATUS      current
    DESCRIPTION
"
synchronization status for idleValencePB
-1 - idleValencePB could not be synchronized
 0 - synchronization not configured
 1 - out of sync - running master mode
 2 - in sync - running  mastermode
 3 - in sync - running slave mode
 4 - in sync - running master mode (wait to reach state 2)
"
    ::= {idleValencePB 5}

syncStatStridleValencePB  OBJECT-TYPE
    SYNTAX      OCTET STRING
    MAX-ACCESS  read-only
    STATUS      current
    DESCRIPTION
"
synchronization status line from file assp_sync.cfg for idleValencePB
 0 - synchronization not configured
 1 - out of sync - running master mode
 2 - in sync - running  mastermode
 3 - in sync - running slave mode
 4 - in sync - running master mode (wait to reach state 2)
"
    ::= {idleValencePB 6}

irValencePB  OBJECT-TYPE
    SYNTAX      OCTET STRING
    MAX-ACCESS  read-write
    STATUS      current
    DESCRIPTION
"
Message/IP scoring
"
    REFERENCE "Invalid Recipient, default=10 +"
    DEFVAL { "10" }
    ::= {PenaltyBox 894}

syncStatirValencePB  OBJECT-TYPE
    SYNTAX      OCTET STRING
    MAX-ACCESS  read-only
    STATUS      current
    DESCRIPTION
"
synchronization status for irValencePB
-1 - irValencePB could not be synchronized
 0 - synchronization not configured
 1 - out of sync - running master mode
 2 - in sync - running  mastermode
 3 - in sync - running slave mode
 4 - in sync - running master mode (wait to reach state 2)
"
    ::= {irValencePB 5}

syncStatStrirValencePB  OBJECT-TYPE
    SYNTAX      OCTET STRING
    MAX-ACCESS  read-only
    STATUS      current
    DESCRIPTION
"
synchronization status line from file assp_sync.cfg for irValencePB
 0 - synchronization not configured
 1 - out of sync - running master mode
 2 - in sync - running  mastermode
 3 - in sync - running slave mode
 4 - in sync - running master mode (wait to reach state 2)
"
    ::= {irValencePB 6}

noExtremePB  OBJECT-TYPE
    SYNTAX      OCTET STRING
    MAX-ACCESS  read-write
    STATUS      current
    DESCRIPTION
"
Enter IP's that you don't want to be extreme penalized. IP's in noPB are already included. For example: 127.0.0.1|172.16.
"
    REFERENCE "Don't do Extreme Profiling for these IP's*"
    DEFVAL { "" }
    ::= {PenaltyBox 928}

syncStatnoExtremePB  OBJECT-TYPE
    SYNTAX      OCTET STRING
    MAX-ACCESS  read-only
    STATUS      current
    DESCRIPTION
"
synchronization status for noExtremePB
-1 - noExtremePB could not be synchronized
 0 - synchronization not configured
 1 - out of sync - running master mode
 2 - in sync - running  mastermode
 3 - in sync - running slave mode
 4 - in sync - running master mode (wait to reach state 2)
"
    ::= {noExtremePB 5}

syncStatStrnoExtremePB  OBJECT-TYPE
    SYNTAX      OCTET STRING
    MAX-ACCESS  read-only
    STATUS      current
    DESCRIPTION
"
synchronization status line from file assp_sync.cfg for noExtremePB
 0 - synchronization not configured
 1 - out of sync - running master mode
 2 - in sync - running  mastermode
 3 - in sync - running slave mode
 4 - in sync - running master mode (wait to reach state 2)
"
    ::= {noExtremePB 6}

noExtremePBAddresses  OBJECT-TYPE
    SYNTAX      OCTET STRING
    MAX-ACCESS  read-write
    STATUS      current
    DESCRIPTION
"
Mails from any of these addresses will not be extreme profiled if DoPenaltyExtremeSMTP is not set. Accepts specific addresses (user@domain.com), user parts (user) or entire domains (@domain.com).  Wildcards are supported (fribo*@domain.com).
"
    REFERENCE "Don't do Extreme Profiling for Mails from any of these Addresses*"
    DEFVAL { "" }
    ::= {PenaltyBox 929}

syncStatnoExtremePBAddresses  OBJECT-TYPE
    SYNTAX      OCTET STRING
    MAX-ACCESS  read-only
    STATUS      current
    DESCRIPTION
"
synchronization status for noExtremePBAddresses
-1 - noExtremePBAddresses could not be synchronized
 0 - synchronization not configured
 1 - out of sync - running master mode
 2 - in sync - running  mastermode
 3 - in sync - running slave mode
 4 - in sync - running master mode (wait to reach state 2)
"
    ::= {noExtremePBAddresses 5}

syncStatStrnoExtremePBAddresses  OBJECT-TYPE
    SYNTAX      OCTET STRING
    MAX-ACCESS  read-only
    STATUS      current
    DESCRIPTION
"
synchronization status line from file assp_sync.cfg for noExtremePBAddresses
 0 - synchronization not configured
 1 - out of sync - running master mode
 2 - in sync - running  mastermode
 3 - in sync - running slave mode
 4 - in sync - running master mode (wait to reach state 2)
"
    ::= {noExtremePBAddresses 6}

autValencePB  OBJECT-TYPE
    SYNTAX      OCTET STRING
    MAX-ACCESS  read-write
    STATUS      current
    DESCRIPTION
"
Message/IP scoring
 This option and all other *ValencePB options with an '+' at the end of the description, accepts a second comma or pipe separated value like: '20,10' .
  In this case the first value is used for message scoring and the second value is used for IP scoring.
  If only the first value is defined, this value is used for both scoring mechanism.
  If a *ValencePB option is related to any feature which allowes the usage of weighted penalties, the message scoring value is used to calculate the weighted penalty and the result is used calculating (result * ipscorevalence / messagescorevalence ) for IP scoring.
"
    REFERENCE "Bad SMTP Authentication, default=60 +"
    DEFVAL { "60" }
    ::= {PenaltyBox 930}

syncStatautValencePB  OBJECT-TYPE
    SYNTAX      OCTET STRING
    MAX-ACCESS  read-only
    STATUS      current
    DESCRIPTION
"
synchronization status for autValencePB
-1 - autValencePB could not be synchronized
 0 - synchronization not configured
 1 - out of sync - running master mode
 2 - in sync - running  mastermode
 3 - in sync - running slave mode
 4 - in sync - running master mode (wait to reach state 2)
"
    ::= {autValencePB 5}

syncStatStrautValencePB  OBJECT-TYPE
    SYNTAX      OCTET STRING
    MAX-ACCESS  read-only
    STATUS      current
    DESCRIPTION
"
synchronization status line from file assp_sync.cfg for autValencePB
 0 - synchronization not configured
 1 - out of sync - running master mode
 2 - in sync - running  mastermode
 3 - in sync - running slave mode
 4 - in sync - running master mode (wait to reach state 2)
"
    ::= {autValencePB 6}

bayslocalValencePB  OBJECT-TYPE
    SYNTAX      OCTET STRING
    MAX-ACCESS  read-write
    STATUS      current
    DESCRIPTION
"
Message/IP scoring
"
    REFERENCE "Bayesian for Local Messages, default=55 +"
    DEFVAL { "55" }
    ::= {PenaltyBox 955}

syncStatbayslocalValencePB  OBJECT-TYPE
    SYNTAX      OCTET STRING
    MAX-ACCESS  read-only
    STATUS      current
    DESCRIPTION
"
synchronization status for bayslocalValencePB
-1 - bayslocalValencePB could not be synchronized
 0 - synchronization not configured
 1 - out of sync - running master mode
 2 - in sync - running  mastermode
 3 - in sync - running slave mode
 4 - in sync - running master mode (wait to reach state 2)
"
    ::= {bayslocalValencePB 5}

syncStatStrbayslocalValencePB  OBJECT-TYPE
    SYNTAX      OCTET STRING
    MAX-ACCESS  read-only
    STATUS      current
    DESCRIPTION
"
synchronization status line from file assp_sync.cfg for bayslocalValencePB
 0 - synchronization not configured
 1 - out of sync - running master mode
 2 - in sync - running  mastermode
 3 - in sync - running slave mode
 4 - in sync - running master mode (wait to reach state 2)
"
    ::= {bayslocalValencePB 6}

HMMValencePB  OBJECT-TYPE
    SYNTAX      OCTET STRING
    MAX-ACCESS  read-write
    STATUS      current
    DESCRIPTION
"
Message/IP scoring
"
    REFERENCE "Hidden-Makov-Model, default=49 +"
    DEFVAL { "49" }
    ::= {PenaltyBox 964}

syncStatHMMValencePB  OBJECT-TYPE
    SYNTAX      OCTET STRING
    MAX-ACCESS  read-only
    STATUS      current
    DESCRIPTION
"
synchronization status for HMMValencePB
-1 - HMMValencePB could not be synchronized
 0 - synchronization not configured
 1 - out of sync - running master mode
 2 - in sync - running  mastermode
 3 - in sync - running slave mode
 4 - in sync - running master mode (wait to reach state 2)
"
    ::= {HMMValencePB 5}

syncStatStrHMMValencePB  OBJECT-TYPE
    SYNTAX      OCTET STRING
    MAX-ACCESS  read-only
    STATUS      current
    DESCRIPTION
"
synchronization status line from file assp_sync.cfg for HMMValencePB
 0 - synchronization not configured
 1 - out of sync - running master mode
 2 - in sync - running  mastermode
 3 - in sync - running slave mode
 4 - in sync - running master mode (wait to reach state 2)
"
    ::= {HMMValencePB 6}

HMMlocalValencePB  OBJECT-TYPE
    SYNTAX      OCTET STRING
    MAX-ACCESS  read-write
    STATUS      current
    DESCRIPTION
"
Message/IP scoring
"
    REFERENCE "Hidden-Makov-Model for Local Messages, default=55 +"
    DEFVAL { "55" }
    ::= {PenaltyBox 965}

syncStatHMMlocalValencePB  OBJECT-TYPE
    SYNTAX      OCTET STRING
    MAX-ACCESS  read-only
    STATUS      current
    DESCRIPTION
"
synchronization status for HMMlocalValencePB
-1 - HMMlocalValencePB could not be synchronized
 0 - synchronization not configured
 1 - out of sync - running master mode
 2 - in sync - running  mastermode
 3 - in sync - running slave mode
 4 - in sync - running master mode (wait to reach state 2)
"
    ::= {HMMlocalValencePB 5}

syncStatStrHMMlocalValencePB  OBJECT-TYPE
    SYNTAX      OCTET STRING
    MAX-ACCESS  read-only
    STATUS      current
    DESCRIPTION
"
synchronization status line from file assp_sync.cfg for HMMlocalValencePB
 0 - synchronization not configured
 1 - out of sync - running master mode
 2 - in sync - running  mastermode
 3 - in sync - running slave mode
 4 - in sync - running master mode (wait to reach state 2)
"
    ::= {HMMlocalValencePB 6}

isValencePB  OBJECT-TYPE
    SYNTAX      OCTET STRING
    MAX-ACCESS  read-write
    STATUS      current
    DESCRIPTION
"
Message/IP scoring
"
    REFERENCE "Subject Frequency, default=150 +"
    DEFVAL { "150" }
    ::= {PenaltyBox 1003}

syncStatisValencePB  OBJECT-TYPE
    SYNTAX      OCTET STRING
    MAX-ACCESS  read-only
    STATUS      current
    DESCRIPTION
"
synchronization status for isValencePB
-1 - isValencePB could not be synchronized
 0 - synchronization not configured
 1 - out of sync - running master mode
 2 - in sync - running  mastermode
 3 - in sync - running slave mode
 4 - in sync - running master mode (wait to reach state 2)
"
    ::= {isValencePB 5}

syncStatStrisValencePB  OBJECT-TYPE
    SYNTAX      OCTET STRING
    MAX-ACCESS  read-only
    STATUS      current
    DESCRIPTION
"
synchronization status line from file assp_sync.cfg for isValencePB
 0 - synchronization not configured
 1 - out of sync - running master mode
 2 - in sync - running  mastermode
 3 - in sync - running slave mode
 4 - in sync - running master mode (wait to reach state 2)
"
    ::= {isValencePB 6}

bayshamValencePB  OBJECT-TYPE
    SYNTAX      OCTET STRING
    MAX-ACCESS  read-write
    STATUS      current
    DESCRIPTION
"
Message/IP scoring bonus (zero or negative value only)
"
    REFERENCE "Bayesian HAM Bonus, default=0 +"
    DEFVAL { "0" }
    ::= {PenaltyBox 1029}

syncStatbayshamValencePB  OBJECT-TYPE
    SYNTAX      OCTET STRING
    MAX-ACCESS  read-only
    STATUS      current
    DESCRIPTION
"
synchronization status for bayshamValencePB
-1 - bayshamValencePB could not be synchronized
 0 - synchronization not configured
 1 - out of sync - running master mode
 2 - in sync - running  mastermode
 3 - in sync - running slave mode
 4 - in sync - running master mode (wait to reach state 2)
"
    ::= {bayshamValencePB 5}

syncStatStrbayshamValencePB  OBJECT-TYPE
    SYNTAX      OCTET STRING
    MAX-ACCESS  read-only
    STATUS      current
    DESCRIPTION
"
synchronization status line from file assp_sync.cfg for bayshamValencePB
 0 - synchronization not configured
 1 - out of sync - running master mode
 2 - in sync - running  mastermode
 3 - in sync - running slave mode
 4 - in sync - running master mode (wait to reach state 2)
"
    ::= {bayshamValencePB 6}

HMMhamValencePB  OBJECT-TYPE
    SYNTAX      OCTET STRING
    MAX-ACCESS  read-write
    STATUS      current
    DESCRIPTION
"
Message/IP scoring bonus (zero or negative value only)
"
    REFERENCE "Hidden-Makov-Model HAM Bonus, default=0 +"
    DEFVAL { "0" }
    ::= {PenaltyBox 1030}

syncStatHMMhamValencePB  OBJECT-TYPE
    SYNTAX      OCTET STRING
    MAX-ACCESS  read-only
    STATUS      current
    DESCRIPTION
"
synchronization status for HMMhamValencePB
-1 - HMMhamValencePB could not be synchronized
 0 - synchronization not configured
 1 - out of sync - running master mode
 2 - in sync - running  mastermode
 3 - in sync - running slave mode
 4 - in sync - running master mode (wait to reach state 2)
"
    ::= {HMMhamValencePB 5}

syncStatStrHMMhamValencePB  OBJECT-TYPE
    SYNTAX      OCTET STRING
    MAX-ACCESS  read-only
    STATUS      current
    DESCRIPTION
"
synchronization status line from file assp_sync.cfg for HMMhamValencePB
 0 - synchronization not configured
 1 - out of sync - running master mode
 2 - in sync - running  mastermode
 3 - in sync - running slave mode
 4 - in sync - running master mode (wait to reach state 2)
"
    ::= {HMMhamValencePB 6}

DoLocalPenaltyMessage  OBJECT-TYPE
    SYNTAX      OCTET STRING
    MAX-ACCESS  read-write
    STATUS      current
    DESCRIPTION
"
If this feature is selected, the total score for all checks during a local or outgoing message is used to determine if the email is Spam. If the combined score is greater than the Local Low MessageLimit (LocalPenaltyMessageLow) and less than or equal the Local High MessageLimit (LocalPenaltyMessageLimit) the message will not be blocked but tagged. If the combined score is greater than the Local High MessageLimit (LocalPenaltyMessageLimit), the message will be blocked.
"
    REFERENCE "Message Scoring Mode for Local and Outgoing Mails"
    DEFVAL { "0" }
    ::= {PenaltyBox 1033}

syncStatDoLocalPenaltyMessage  OBJECT-TYPE
    SYNTAX      OCTET STRING
    MAX-ACCESS  read-only
    STATUS      current
    DESCRIPTION
"
synchronization status for DoLocalPenaltyMessage
-1 - DoLocalPenaltyMessage could not be synchronized
 0 - synchronization not configured
 1 - out of sync - running master mode
 2 - in sync - running  mastermode
 3 - in sync - running slave mode
 4 - in sync - running master mode (wait to reach state 2)
"
    ::= {DoLocalPenaltyMessage 5}

syncStatStrDoLocalPenaltyMessage  OBJECT-TYPE
    SYNTAX      OCTET STRING
    MAX-ACCESS  read-only
    STATUS      current
    DESCRIPTION
"
synchronization status line from file assp_sync.cfg for DoLocalPenaltyMessage
 0 - synchronization not configured
 1 - out of sync - running master mode
 2 - in sync - running  mastermode
 3 - in sync - running slave mode
 4 - in sync - running master mode (wait to reach state 2)
"
    ::= {DoLocalPenaltyMessage 6}

LocalPenaltyMessageLow  OBJECT-TYPE
    SYNTAX      OCTET STRING
    MAX-ACCESS  read-write
    STATUS      current
    DESCRIPTION
"
MessageMode will not block local and outgoing messages whose score exceeds this threshold during the message but will tag them.  For example: 40
"
    REFERENCE "Low MessageLimit for Local and Outgoing Mails"
    DEFVAL { "40" }
    ::= {PenaltyBox 1034}

syncStatLocalPenaltyMessageLow  OBJECT-TYPE
    SYNTAX      OCTET STRING
    MAX-ACCESS  read-only
    STATUS      current
    DESCRIPTION
"
synchronization status for LocalPenaltyMessageLow
-1 - LocalPenaltyMessageLow could not be synchronized
 0 - synchronization not configured
 1 - out of sync - running master mode
 2 - in sync - running  mastermode
 3 - in sync - running slave mode
 4 - in sync - running master mode (wait to reach state 2)
"
    ::= {LocalPenaltyMessageLow 5}

syncStatStrLocalPenaltyMessageLow  OBJECT-TYPE
    SYNTAX      OCTET STRING
    MAX-ACCESS  read-only
    STATUS      current
    DESCRIPTION
"
synchronization status line from file assp_sync.cfg for LocalPenaltyMessageLow
 0 - synchronization not configured
 1 - out of sync - running master mode
 2 - in sync - running  mastermode
 3 - in sync - running slave mode
 4 - in sync - running master mode (wait to reach state 2)
"
    ::= {LocalPenaltyMessageLow 6}

LocalPenaltyMessageLimit  OBJECT-TYPE
    SYNTAX      OCTET STRING
    MAX-ACCESS  read-write
    STATUS      current
    DESCRIPTION
"
MessageMode will block local and outgoing messages whose score exceeds this threshold during the message.  For example: 50
"
    REFERENCE "High MessageLimit for Local and Outgoing Mails"
    DEFVAL { "50" }
    ::= {PenaltyBox 1035}

syncStatLocalPenaltyMessageLimit  OBJECT-TYPE
    SYNTAX      OCTET STRING
    MAX-ACCESS  read-only
    STATUS      current
    DESCRIPTION
"
synchronization status for LocalPenaltyMessageLimit
-1 - LocalPenaltyMessageLimit could not be synchronized
 0 - synchronization not configured
 1 - out of sync - running master mode
 2 - in sync - running  mastermode
 3 - in sync - running slave mode
 4 - in sync - running master mode (wait to reach state 2)
"
    ::= {LocalPenaltyMessageLimit 5}

syncStatStrLocalPenaltyMessageLimit  OBJECT-TYPE
    SYNTAX      OCTET STRING
    MAX-ACCESS  read-only
    STATUS      current
    DESCRIPTION
"
synchronization status line from file assp_sync.cfg for LocalPenaltyMessageLimit
 0 - synchronization not configured
 1 - out of sync - running master mode
 2 - in sync - running  mastermode
 3 - in sync - running slave mode
 4 - in sync - running master mode (wait to reach state 2)
"
    ::= {LocalPenaltyMessageLimit 6}

DelayingGreylisting  OBJECT IDENTIFIER ::= {asspConfig 16}
EnableDelaying  OBJECT-TYPE
    SYNTAX      OCTET STRING
    MAX-ACCESS  read-write
    STATUS      current
    DESCRIPTION
"
Enable Greylisting as described at .
  It's a new method of blocking significant amounts of spam at the mailserver level, but without resorting to heavyweight statistical analysis or other heuristical approaches.
"
    REFERENCE "Enable Delaying/Greylisting"
    DEFVAL { "1" }
    ::= {DelayingGreylisting 328}

syncStatEnableDelaying  OBJECT-TYPE
    SYNTAX      OCTET STRING
    MAX-ACCESS  read-only
    STATUS      current
    DESCRIPTION
"
synchronization status for EnableDelaying
-1 - EnableDelaying could not be synchronized
 0 - synchronization not configured
 1 - out of sync - running master mode
 2 - in sync - running  mastermode
 3 - in sync - running slave mode
 4 - in sync - running master mode (wait to reach state 2)
"
    ::= {EnableDelaying 5}

syncStatStrEnableDelaying  OBJECT-TYPE
    SYNTAX      OCTET STRING
    MAX-ACCESS  read-only
    STATUS      current
    DESCRIPTION
"
synchronization status line from file assp_sync.cfg for EnableDelaying
 0 - synchronization not configured
 1 - out of sync - running master mode
 2 - in sync - running  mastermode
 3 - in sync - running slave mode
 4 - in sync - running master mode (wait to reach state 2)
"
    ::= {EnableDelaying 6}

DelayWL  OBJECT-TYPE
    SYNTAX      OCTET STRING
    MAX-ACCESS  read-write
    STATUS      current
    DESCRIPTION
"
Enable Greylisting for whitelisted mails. This also enables Geylisting for SPF-Cache-OK listed IP's and mails from white organizations, which are normally not greylisted.
"
    REFERENCE "Whitelisted Greylisting"
    DEFVAL { "" }
    ::= {DelayingGreylisting 329}

syncStatDelayWL  OBJECT-TYPE
    SYNTAX      OCTET STRING
    MAX-ACCESS  read-only
    STATUS      current
    DESCRIPTION
"
synchronization status for DelayWL
-1 - DelayWL could not be synchronized
 0 - synchronization not configured
 1 - out of sync - running master mode
 2 - in sync - running  mastermode
 3 - in sync - running slave mode
 4 - in sync - running master mode (wait to reach state 2)
"
    ::= {DelayWL 5}

syncStatStrDelayWL  OBJECT-TYPE
    SYNTAX      OCTET STRING
    MAX-ACCESS  read-only
    STATUS      current
    DESCRIPTION
"
synchronization status line from file assp_sync.cfg for DelayWL
 0 - synchronization not configured
 1 - out of sync - running master mode
 2 - in sync - running  mastermode
 3 - in sync - running slave mode
 4 - in sync - running master mode (wait to reach state 2)
"
    ::= {DelayWL 6}

DelayNP  OBJECT-TYPE
    SYNTAX      OCTET STRING
    MAX-ACCESS  read-write
    STATUS      current
    DESCRIPTION
"
Enable Greylisting for noprocessing mails.
"
    REFERENCE "NoProcessing Greylisting"
    DEFVAL { "" }
    ::= {DelayingGreylisting 330}

syncStatDelayNP  OBJECT-TYPE
    SYNTAX      OCTET STRING
    MAX-ACCESS  read-only
    STATUS      current
    DESCRIPTION
"
synchronization status for DelayNP
-1 - DelayNP could not be synchronized
 0 - synchronization not configured
 1 - out of sync - running master mode
 2 - in sync - running  mastermode
 3 - in sync - running slave mode
 4 - in sync - running master mode (wait to reach state 2)
"
    ::= {DelayNP 5}

syncStatStrDelayNP  OBJECT-TYPE
    SYNTAX      OCTET STRING
    MAX-ACCESS  read-only
    STATUS      current
    DESCRIPTION
"
synchronization status line from file assp_sync.cfg for DelayNP
 0 - synchronization not configured
 1 - out of sync - running master mode
 2 - in sync - running  mastermode
 3 - in sync - running slave mode
 4 - in sync - running master mode (wait to reach state 2)
"
    ::= {DelayNP 6}

DelaySL  OBJECT-TYPE
    SYNTAX      OCTET STRING
    MAX-ACCESS  read-write
    STATUS      current
    DESCRIPTION
"
Enable Greylisting for Spam-Lovers.
"
    REFERENCE "Spam-Lovers Greylisting"
    DEFVAL { "" }
    ::= {DelayingGreylisting 331}

syncStatDelaySL  OBJECT-TYPE
    SYNTAX      OCTET STRING
    MAX-ACCESS  read-only
    STATUS      current
    DESCRIPTION
"
synchronization status for DelaySL
-1 - DelaySL could not be synchronized
 0 - synchronization not configured
 1 - out of sync - running master mode
 2 - in sync - running  mastermode
 3 - in sync - running slave mode
 4 - in sync - running master mode (wait to reach state 2)
"
    ::= {DelaySL 5}

syncStatStrDelaySL  OBJECT-TYPE
    SYNTAX      OCTET STRING
    MAX-ACCESS  read-only
    STATUS      current
    DESCRIPTION
"
synchronization status line from file assp_sync.cfg for DelaySL
 0 - synchronization not configured
 1 - out of sync - running master mode
 2 - in sync - running  mastermode
 3 - in sync - running slave mode
 4 - in sync - running master mode (wait to reach state 2)
"
    ::= {DelaySL 6}

DelayAddHeader  OBJECT-TYPE
    SYNTAX      OCTET STRING
    MAX-ACCESS  read-write
    STATUS      current
    DESCRIPTION
"
Add X-Assp-Delayed header to header of all delayed or whitelisted mails.
"
    REFERENCE "Add X-Assp-Delayed Header"
    DEFVAL { "1" }
    ::= {DelayingGreylisting 332}

syncStatDelayAddHeader  OBJECT-TYPE
    SYNTAX      OCTET STRING
    MAX-ACCESS  read-only
    STATUS      current
    DESCRIPTION
"
synchronization status for DelayAddHeader
-1 - DelayAddHeader could not be synchronized
 0 - synchronization not configured
 1 - out of sync - running master mode
 2 - in sync - running  mastermode
 3 - in sync - running slave mode
 4 - in sync - running master mode (wait to reach state 2)
"
    ::= {DelayAddHeader 5}

syncStatStrDelayAddHeader  OBJECT-TYPE
    SYNTAX      OCTET STRING
    MAX-ACCESS  read-only
    STATUS      current
    DESCRIPTION
"
synchronization status line from file assp_sync.cfg for DelayAddHeader
 0 - synchronization not configured
 1 - out of sync - running master mode
 2 - in sync - running  mastermode
 3 - in sync - running slave mode
 4 - in sync - running master mode (wait to reach state 2)
"
    ::= {DelayAddHeader 6}

DelayEmbargoTime  OBJECT-TYPE
    SYNTAX      OCTET STRING
    MAX-ACCESS  read-write
    STATUS      current
    DESCRIPTION
"
Enter the number of minutes for which delivery, related with new 'triplet' (IP address of the sending
  host + mail from + rcpt to), is refused with a temporary failure. Default is 5 minutes.
"
    REFERENCE "Embargo Time"
    DEFVAL { "5" }
    ::= {DelayingGreylisting 333}

syncStatDelayEmbargoTime  OBJECT-TYPE
    SYNTAX      OCTET STRING
    MAX-ACCESS  read-only
    STATUS      current
    DESCRIPTION
"
synchronization status for DelayEmbargoTime
-1 - DelayEmbargoTime could not be synchronized
 0 - synchronization not configured
 1 - out of sync - running master mode
 2 - in sync - running  mastermode
 3 - in sync - running slave mode
 4 - in sync - running master mode (wait to reach state 2)
"
    ::= {DelayEmbargoTime 5}

syncStatStrDelayEmbargoTime  OBJECT-TYPE
    SYNTAX      OCTET STRING
    MAX-ACCESS  read-only
    STATUS      current
    DESCRIPTION
"
synchronization status line from file assp_sync.cfg for DelayEmbargoTime
 0 - synchronization not configured
 1 - out of sync - running master mode
 2 - in sync - running  mastermode
 3 - in sync - running slave mode
 4 - in sync - running master mode (wait to reach state 2)
"
    ::= {DelayEmbargoTime 6}

DelayWaitTime  OBJECT-TYPE
    SYNTAX      OCTET STRING
    MAX-ACCESS  read-write
    STATUS      current
    DESCRIPTION
"
Enter the number of hours to wait for delivery attempts related with recognised 'triplet'; delivery is accepted 
  immediately and the 'tuplet' (IP address of the sending host + sender's domain) is safelisted. Default is 28 hours.
"
    REFERENCE "Wait Time"
    DEFVAL { "28" }
    ::= {DelayingGreylisting 334}

syncStatDelayWaitTime  OBJECT-TYPE
    SYNTAX      OCTET STRING
    MAX-ACCESS  read-only
    STATUS      current
    DESCRIPTION
"
synchronization status for DelayWaitTime
-1 - DelayWaitTime could not be synchronized
 0 - synchronization not configured
 1 - out of sync - running master mode
 2 - in sync - running  mastermode
 3 - in sync - running slave mode
 4 - in sync - running master mode (wait to reach state 2)
"
    ::= {DelayWaitTime 5}

syncStatStrDelayWaitTime  OBJECT-TYPE
    SYNTAX      OCTET STRING
    MAX-ACCESS  read-only
    STATUS      current
    DESCRIPTION
"
synchronization status line from file assp_sync.cfg for DelayWaitTime
 0 - synchronization not configured
 1 - out of sync - running master mode
 2 - in sync - running  mastermode
 3 - in sync - running slave mode
 4 - in sync - running master mode (wait to reach state 2)
"
    ::= {DelayWaitTime 6}

DelayExpiryTime  OBJECT-TYPE
    SYNTAX      OCTET STRING
    MAX-ACCESS  read-write
    STATUS      current
    DESCRIPTION
"
Enter the number of days for which whitelisted 'tuplet' is considered valid. Default is 36 days.
"
    REFERENCE "Expiry Time"
    DEFVAL { "36" }
    ::= {DelayingGreylisting 335}

syncStatDelayExpiryTime  OBJECT-TYPE
    SYNTAX      OCTET STRING
    MAX-ACCESS  read-only
    STATUS      current
    DESCRIPTION
"
synchronization status for DelayExpiryTime
-1 - DelayExpiryTime could not be synchronized
 0 - synchronization not configured
 1 - out of sync - running master mode
 2 - in sync - running  mastermode
 3 - in sync - running slave mode
 4 - in sync - running master mode (wait to reach state 2)
"
    ::= {DelayExpiryTime 5}

syncStatStrDelayExpiryTime  OBJECT-TYPE
    SYNTAX      OCTET STRING
    MAX-ACCESS  read-only
    STATUS      current
    DESCRIPTION
"
synchronization status line from file assp_sync.cfg for DelayExpiryTime
 0 - synchronization not configured
 1 - out of sync - running master mode
 2 - in sync - running  mastermode
 3 - in sync - running slave mode
 4 - in sync - running master mode (wait to reach state 2)
"
    ::= {DelayExpiryTime 6}

DelayUseNetblocks  OBJECT-TYPE
    SYNTAX      OCTET STRING
    MAX-ACCESS  read-write
    STATUS      current
    DESCRIPTION
"
Perform the IP address checks of the sending host based on the /24 subnet it is at rather than the specific IP. 
  This feature may be useful for legitimate mail systems that shuffle messages among SMTP clients between retransmissions.
"
    REFERENCE "Use IP Netblocks"
    DEFVAL { "1" }
    ::= {DelayingGreylisting 336}

syncStatDelayUseNetblocks  OBJECT-TYPE
    SYNTAX      OCTET STRING
    MAX-ACCESS  read-only
    STATUS      current
    DESCRIPTION
"
synchronization status for DelayUseNetblocks
-1 - DelayUseNetblocks could not be synchronized
 0 - synchronization not configured
 1 - out of sync - running master mode
 2 - in sync - running  mastermode
 3 - in sync - running slave mode
 4 - in sync - running master mode (wait to reach state 2)
"
    ::= {DelayUseNetblocks 5}

syncStatStrDelayUseNetblocks  OBJECT-TYPE
    SYNTAX      OCTET STRING
    MAX-ACCESS  read-only
    STATUS      current
    DESCRIPTION
"
synchronization status line from file assp_sync.cfg for DelayUseNetblocks
 0 - synchronization not configured
 1 - out of sync - running master mode
 2 - in sync - running  mastermode
 3 - in sync - running slave mode
 4 - in sync - running master mode (wait to reach state 2)
"
    ::= {DelayUseNetblocks 6}

DelayNormalizeVERPs  OBJECT-TYPE
    SYNTAX      OCTET STRING
    MAX-ACCESS  read-write
    STATUS      current
    DESCRIPTION
"
Some mailing lists (such as Ezmlm) try to track bounces to individual mails, rather than just individual recipients, which creates a variation on the VERP method where each email has its own unique envelope sender. Since the automatic whitelisting (called savelisting to make a difference to the standard whitelisting) that is built into Greylisting depends on the envelope addresses for subsequent mails being the same, the greylisting filter will attempt to normalize the unique sender addresses, when this option is checked.
"
    REFERENCE "Normalize VERP Addresses"
    DEFVAL { "1" }
    ::= {DelayingGreylisting 337}

syncStatDelayNormalizeVERPs  OBJECT-TYPE
    SYNTAX      OCTET STRING
    MAX-ACCESS  read-only
    STATUS      current
    DESCRIPTION
"
synchronization status for DelayNormalizeVERPs
-1 - DelayNormalizeVERPs could not be synchronized
 0 - synchronization not configured
 1 - out of sync - running master mode
 2 - in sync - running  mastermode
 3 - in sync - running slave mode
 4 - in sync - running master mode (wait to reach state 2)
"
    ::= {DelayNormalizeVERPs 5}

syncStatStrDelayNormalizeVERPs  OBJECT-TYPE
    SYNTAX      OCTET STRING
    MAX-ACCESS  read-only
    STATUS      current
    DESCRIPTION
"
synchronization status line from file assp_sync.cfg for DelayNormalizeVERPs
 0 - synchronization not configured
 1 - out of sync - running master mode
 2 - in sync - running  mastermode
 3 - in sync - running slave mode
 4 - in sync - running master mode (wait to reach state 2)
"
    ::= {DelayNormalizeVERPs 6}

DelayWithMyName  OBJECT-TYPE
    SYNTAX      OCTET STRING
    MAX-ACCESS  read-write
    STATUS      current
    DESCRIPTION
"
If set, myName is added to every delay triplet (not to tuplets). This is useful and recommended, if you are using more than one ASSP host with shared databases for delaydb. This option makes the triplets unique to every ASSP host, because it is allowed for SMTP-hosts, to request a backup MX immediately after the primary MX, without waiting 5 minutes (DelayEmbargoTime) between the two requests.
"
    REFERENCE "Add myName to Triplets"
    DEFVAL { "0" }
    ::= {DelayingGreylisting 338}

syncStatDelayWithMyName  OBJECT-TYPE
    SYNTAX      OCTET STRING
    MAX-ACCESS  read-only
    STATUS      current
    DESCRIPTION
"
synchronization status for DelayWithMyName
-1 - DelayWithMyName could not be synchronized
 0 - synchronization not configured
 1 - out of sync - running master mode
 2 - in sync - running  mastermode
 3 - in sync - running slave mode
 4 - in sync - running master mode (wait to reach state 2)
"
    ::= {DelayWithMyName 5}

syncStatStrDelayWithMyName  OBJECT-TYPE
    SYNTAX      OCTET STRING
    MAX-ACCESS  read-only
    STATUS      current
    DESCRIPTION
"
synchronization status line from file assp_sync.cfg for DelayWithMyName
 0 - synchronization not configured
 1 - out of sync - running master mode
 2 - in sync - running  mastermode
 3 - in sync - running slave mode
 4 - in sync - running master mode (wait to reach state 2)
"
    ::= {DelayWithMyName 6}

DelayMD5  OBJECT-TYPE
    SYNTAX      OCTET STRING
    MAX-ACCESS  read-write
    STATUS      current
    DESCRIPTION
"
Message-Digest algorithm 5 is a cryptographic hash function and adds some level of security to the delay database. Must be set to off if you want to list the database with DelayShowDB/DelayShowDBwhite. This requires an installed  module in PERL.
"
    REFERENCE "Use MD5 for DelayDB"
    DEFVAL { "1" }
    ::= {DelayingGreylisting 339}

syncStatDelayMD5  OBJECT-TYPE
    SYNTAX      OCTET STRING
    MAX-ACCESS  read-only
    STATUS      current
    DESCRIPTION
"
synchronization status for DelayMD5
-1 - DelayMD5 could not be synchronized
 0 - synchronization not configured
 1 - out of sync - running master mode
 2 - in sync - running  mastermode
 3 - in sync - running slave mode
 4 - in sync - running master mode (wait to reach state 2)
"
    ::= {DelayMD5 5}

syncStatStrDelayMD5  OBJECT-TYPE
    SYNTAX      OCTET STRING
    MAX-ACCESS  read-only
    STATUS      current
    DESCRIPTION
"
synchronization status line from file assp_sync.cfg for DelayMD5
 0 - synchronization not configured
 1 - out of sync - running master mode
 2 - in sync - running  mastermode
 3 - in sync - running slave mode
 4 - in sync - running master mode (wait to reach state 2)
"
    ::= {DelayMD5 6}

DelayShowDB  OBJECT-TYPE
    SYNTAX      OCTET STRING
    MAX-ACCESS  read-write
    STATUS      current
    DESCRIPTION
"
The directory/file with the delay database file. If you change the filename in section Filepath ( delaydb ) you must change it here too.
"
    REFERENCE "Show Delay/Greylisting Database"
    DEFVAL { "file:delaydb" }
    ::= {DelayingGreylisting 340}

DelayShowDBwhite  OBJECT-TYPE
    SYNTAX      OCTET STRING
    MAX-ACCESS  read-write
    STATUS      current
    DESCRIPTION
"
The directory/file with the save delay database file. If you change the filename in section Filepath ( delaydb )  you must change it here too.
"
    REFERENCE "Show Delay/Greylisting Save Database"
    DEFVAL { "file:delaydb.white" }
    ::= {DelayingGreylisting 341}

DelayExpireOnSpam  OBJECT-TYPE
    SYNTAX      OCTET STRING
    MAX-ACCESS  read-write
    STATUS      current
    DESCRIPTION
"
If a safelisted 'tuplet' is ever associated with spam, viruses, failed rbl, spf etc, it is deleted from the safelist. 
  This renews the temporary embargo for subsequent mail involving the tuplet.
"
    REFERENCE "Expire Spamming Safelisted Tuplets"
    DEFVAL { "1" }
    ::= {DelayingGreylisting 342}

syncStatDelayExpireOnSpam  OBJECT-TYPE
    SYNTAX      OCTET STRING
    MAX-ACCESS  read-only
    STATUS      current
    DESCRIPTION
"
synchronization status for DelayExpireOnSpam
-1 - DelayExpireOnSpam could not be synchronized
 0 - synchronization not configured
 1 - out of sync - running master mode
 2 - in sync - running  mastermode
 3 - in sync - running slave mode
 4 - in sync - running master mode (wait to reach state 2)
"
    ::= {DelayExpireOnSpam 5}

syncStatStrDelayExpireOnSpam  OBJECT-TYPE
    SYNTAX      OCTET STRING
    MAX-ACCESS  read-only
    STATUS      current
    DESCRIPTION
"
synchronization status line from file assp_sync.cfg for DelayExpireOnSpam
 0 - synchronization not configured
 1 - out of sync - running master mode
 2 - in sync - running  mastermode
 3 - in sync - running slave mode
 4 - in sync - running master mode (wait to reach state 2)
"
    ::= {DelayExpireOnSpam 6}

CleanDelayDBInterval  OBJECT-TYPE
    SYNTAX      OCTET STRING
    MAX-ACCESS  read-write
    STATUS      current
    DESCRIPTION
"
Delete outdated entries from triplets and safelisted tuplets databases every this many seconds.
  Defaults to 3 hour.
"
    REFERENCE "Clean Up Delaying Database <sup>s</sup>"
    DEFVAL { "10800" }
    ::= {DelayingGreylisting 343}

syncStatCleanDelayDBInterval  OBJECT-TYPE
    SYNTAX      OCTET STRING
    MAX-ACCESS  read-only
    STATUS      current
    DESCRIPTION
"
synchronization status for CleanDelayDBInterval
-1 - CleanDelayDBInterval could not be synchronized
 0 - synchronization not configured
 1 - out of sync - running master mode
 2 - in sync - running  mastermode
 3 - in sync - running slave mode
 4 - in sync - running master mode (wait to reach state 2)
"
    ::= {CleanDelayDBInterval 5}

syncStatStrCleanDelayDBInterval  OBJECT-TYPE
    SYNTAX      OCTET STRING
    MAX-ACCESS  read-only
    STATUS      current
    DESCRIPTION
"
synchronization status line from file assp_sync.cfg for CleanDelayDBInterval
 0 - synchronization not configured
 1 - out of sync - running master mode
 2 - in sync - running  mastermode
 3 - in sync - running slave mode
 4 - in sync - running master mode (wait to reach state 2)
"
    ::= {CleanDelayDBInterval 6}

noDelay  OBJECT-TYPE
    SYNTAX      OCTET STRING
    MAX-ACCESS  read-write
    STATUS      current
    DESCRIPTION
"
Enter IP addresses that you don't want to be delayed, separated by pipes (|). There are misbehaving MTAs that will not be able to get a legitimate email through a Greylisting server because they do not try again later. An INCOMPLETE list of such mailers is available at . 
  When using mentioned list remember to add trailing dots in IP addresses which specify subnets (eg. 192.168 -> 192.168. ).
  For example:  127.0.0.1|172.16..
  To define IP's only for specific email addresses or domains (recipients) you must use the file:... option
  An entry (line) may look as follows:
  145.146.0.0/16=>*@local.domain|user@mydomain|user2@*.mydomain # comment
  It is possible to define a predefined group on any or both sides of the '=>' separator, like:
  [ipgroup]=>[usergroup]|user@mydomain
  NOTICE: the following combination of two entries, will lead in to a user/domain based matching - the global entry will be ignored!
  145.146.0.0/16 # comment
  145.146.0.0/16=>*@local.domain|user@mydomain|user2@*.mydomain # comment
  If multiple user/domain based entries are defined for the same IP, only the last one will be used!
"
    REFERENCE "Don't Delay these IPs*"
    DEFVAL { "file:files/nodelay.txt" }
    ::= {DelayingGreylisting 344}

syncStatnoDelay  OBJECT-TYPE
    SYNTAX      OCTET STRING
    MAX-ACCESS  read-only
    STATUS      current
    DESCRIPTION
"
synchronization status for noDelay
-1 - noDelay could not be synchronized
 0 - synchronization not configured
 1 - out of sync - running master mode
 2 - in sync - running  mastermode
 3 - in sync - running slave mode
 4 - in sync - running master mode (wait to reach state 2)
"
    ::= {noDelay 5}

syncStatStrnoDelay  OBJECT-TYPE
    SYNTAX      OCTET STRING
    MAX-ACCESS  read-only
    STATUS      current
    DESCRIPTION
"
synchronization status line from file assp_sync.cfg for noDelay
 0 - synchronization not configured
 1 - out of sync - running master mode
 2 - in sync - running  mastermode
 3 - in sync - running slave mode
 4 - in sync - running master mode (wait to reach state 2)
"
    ::= {noDelay 6}

DelayError  OBJECT-TYPE
    SYNTAX      OCTET STRING
    MAX-ACCESS  read-write
    STATUS      current
    DESCRIPTION
"
SMTP reply code to refuse delayed messages. Default: 451 4.7.1 Please try again later
  
  
  
"
    REFERENCE "Reply Code to Refuse Delayed Messages"
    DEFVAL { "451 4.7.1 Please try again later" }
    ::= {DelayingGreylisting 345}

syncStatDelayError  OBJECT-TYPE
    SYNTAX      OCTET STRING
    MAX-ACCESS  read-only
    STATUS      current
    DESCRIPTION
"
synchronization status for DelayError
-1 - DelayError could not be synchronized
 0 - synchronization not configured
 1 - out of sync - running master mode
 2 - in sync - running  mastermode
 3 - in sync - running slave mode
 4 - in sync - running master mode (wait to reach state 2)
"
    ::= {DelayError 5}

syncStatStrDelayError  OBJECT-TYPE
    SYNTAX      OCTET STRING
    MAX-ACCESS  read-only
    STATUS      current
    DESCRIPTION
"
synchronization status line from file assp_sync.cfg for DelayError
 0 - synchronization not configured
 1 - out of sync - running master mode
 2 - in sync - running  mastermode
 3 - in sync - running slave mode
 4 - in sync - running master mode (wait to reach state 2)
"
    ::= {DelayError 6}

noDelayAddresses  OBJECT-TYPE
    SYNTAX      OCTET STRING
    MAX-ACCESS  read-write
    STATUS      current
    DESCRIPTION
"
Enter senders email addresses that you don't want to be delayed, separated by pipes (|). You can list specific addresses (user@anydomain.com), addresses at any domain (user), or entire domains (@anydomain.com).  Wildcards are supported (fribo*@domain.com). (|).For example: fribo@anydomain.com|jhanna|@sillyguys.org or place them in a plain ASCII file one address per line:file:files/nodelayuser.txt.
"
    REFERENCE "Do not Delay these Addresses*"
    DEFVAL { "" }
    ::= {DelayingGreylisting 861}

syncStatnoDelayAddresses  OBJECT-TYPE
    SYNTAX      OCTET STRING
    MAX-ACCESS  read-only
    STATUS      current
    DESCRIPTION
"
synchronization status for noDelayAddresses
-1 - noDelayAddresses could not be synchronized
 0 - synchronization not configured
 1 - out of sync - running master mode
 2 - in sync - running  mastermode
 3 - in sync - running slave mode
 4 - in sync - running master mode (wait to reach state 2)
"
    ::= {noDelayAddresses 5}

syncStatStrnoDelayAddresses  OBJECT-TYPE
    SYNTAX      OCTET STRING
    MAX-ACCESS  read-only
    STATUS      current
    DESCRIPTION
"
synchronization status line from file assp_sync.cfg for noDelayAddresses
 0 - synchronization not configured
 1 - out of sync - running master mode
 2 - in sync - running  mastermode
 3 - in sync - running slave mode
 4 - in sync - running master mode (wait to reach state 2)
"
    ::= {noDelayAddresses 6}

SPFDMARCSRS  OBJECT IDENTIFIER ::= {asspConfig 17}
ValidateSPF  OBJECT-TYPE
    SYNTAX      OCTET STRING
    MAX-ACCESS  read-write
    STATUS      current
    DESCRIPTION
"
Enable Sender Policy Framework Validation as described at  and Domain-based Message Authentication, Reporting &amp; Conformance - described in  (DMARC requires also DoDKIM to be enabled).
  This requires an installed  module in PERL. Testmode is set with spfTestMode, scoring is set with spfValencePB. If you need more information about the syntax of SPF records, visit .
"
    REFERENCE "Enable SPF Validation"
    DEFVAL { "3" }
    ::= {SPFDMARCSRS 346}

syncStatValidateSPF  OBJECT-TYPE
    SYNTAX      OCTET STRING
    MAX-ACCESS  read-only
    STATUS      current
    DESCRIPTION
"
synchronization status for ValidateSPF
-1 - ValidateSPF could not be synchronized
 0 - synchronization not configured
 1 - out of sync - running master mode
 2 - in sync - running  mastermode
 3 - in sync - running slave mode
 4 - in sync - running master mode (wait to reach state 2)
"
    ::= {ValidateSPF 5}

syncStatStrValidateSPF  OBJECT-TYPE
    SYNTAX      OCTET STRING
    MAX-ACCESS  read-only
    STATUS      current
    DESCRIPTION
"
synchronization status line from file assp_sync.cfg for ValidateSPF
 0 - synchronization not configured
 1 - out of sync - running master mode
 2 - in sync - running  mastermode
 3 - in sync - running slave mode
 4 - in sync - running master mode (wait to reach state 2)
"
    ::= {ValidateSPF 6}

SPF2  OBJECT-TYPE
    SYNTAX      OCTET STRING
    MAX-ACCESS  read-write
    STATUS      current
    DESCRIPTION
"
Enable Sender Policy Framework Validation Version 2.
  This requires an installed  object-oriented Perl module that supersedes the old Mail::SPF::Query module. 
"
    REFERENCE "Do SPF Version 2 Validation"
    DEFVAL { "1" }
    ::= {SPFDMARCSRS 347}

syncStatSPF2  OBJECT-TYPE
    SYNTAX      OCTET STRING
    MAX-ACCESS  read-only
    STATUS      current
    DESCRIPTION
"
synchronization status for SPF2
-1 - SPF2 could not be synchronized
 0 - synchronization not configured
 1 - out of sync - running master mode
 2 - in sync - running  mastermode
 3 - in sync - running slave mode
 4 - in sync - running master mode (wait to reach state 2)
"
    ::= {SPF2 5}

syncStatStrSPF2  OBJECT-TYPE
    SYNTAX      OCTET STRING
    MAX-ACCESS  read-only
    STATUS      current
    DESCRIPTION
"
synchronization status line from file assp_sync.cfg for SPF2
 0 - synchronization not configured
 1 - out of sync - running master mode
 2 - in sync - running  mastermode
 3 - in sync - running slave mode
 4 - in sync - running master mode (wait to reach state 2)
"
    ::= {SPF2 6}

SPFWL  OBJECT-TYPE
    SYNTAX      OCTET STRING
    MAX-ACCESS  read-write
    STATUS      current
    DESCRIPTION
"
Enable Sender Policy Framework Validation for whitelisted users also.
"
    REFERENCE "Whitelisted SPF Validation"
    DEFVAL { "" }
    ::= {SPFDMARCSRS 348}

syncStatSPFWL  OBJECT-TYPE
    SYNTAX      OCTET STRING
    MAX-ACCESS  read-only
    STATUS      current
    DESCRIPTION
"
synchronization status for SPFWL
-1 - SPFWL could not be synchronized
 0 - synchronization not configured
 1 - out of sync - running master mode
 2 - in sync - running  mastermode
 3 - in sync - running slave mode
 4 - in sync - running master mode (wait to reach state 2)
"
    ::= {SPFWL 5}

syncStatStrSPFWL  OBJECT-TYPE
    SYNTAX      OCTET STRING
    MAX-ACCESS  read-only
    STATUS      current
    DESCRIPTION
"
synchronization status line from file assp_sync.cfg for SPFWL
 0 - synchronization not configured
 1 - out of sync - running master mode
 2 - in sync - running  mastermode
 3 - in sync - running slave mode
 4 - in sync - running master mode (wait to reach state 2)
"
    ::= {SPFWL 6}

SPFLocal  OBJECT-TYPE
    SYNTAX      OCTET STRING
    MAX-ACCESS  read-write
    STATUS      current
    DESCRIPTION
"
Enable Sender Policy Framework Validation for local and outgoing messages also. Don't forget to configure your DNS-server for SPF and/or to configure SPFoverride / SPFfallback / SPFlocalRecord, if you enable this option.
"
    REFERENCE "Local and outgoing mail SPF Validation"
    DEFVAL { "" }
    ::= {SPFDMARCSRS 349}

syncStatSPFLocal  OBJECT-TYPE
    SYNTAX      OCTET STRING
    MAX-ACCESS  read-only
    STATUS      current
    DESCRIPTION
"
synchronization status for SPFLocal
-1 - SPFLocal could not be synchronized
 0 - synchronization not configured
 1 - out of sync - running master mode
 2 - in sync - running  mastermode
 3 - in sync - running slave mode
 4 - in sync - running master mode (wait to reach state 2)
"
    ::= {SPFLocal 5}

syncStatStrSPFLocal  OBJECT-TYPE
    SYNTAX      OCTET STRING
    MAX-ACCESS  read-only
    STATUS      current
    DESCRIPTION
"
synchronization status line from file assp_sync.cfg for SPFLocal
 0 - synchronization not configured
 1 - out of sync - running master mode
 2 - in sync - running  mastermode
 3 - in sync - running slave mode
 4 - in sync - running master mode (wait to reach state 2)
"
    ::= {SPFLocal 6}

enableSPFbackground  OBJECT-TYPE
    SYNTAX      OCTET STRING
    MAX-ACCESS  read-write
    STATUS      current
    DESCRIPTION
"
SPF background checks are initiated by some features (for example DoDomainIP) to fillup the SPFCache. The collected results are later used to prevent blocking good mails.
"
    REFERENCE "Enable SPF Background Check"
    DEFVAL { "1" }
    ::= {SPFDMARCSRS 350}

syncStatenableSPFbackground  OBJECT-TYPE
    SYNTAX      OCTET STRING
    MAX-ACCESS  read-only
    STATUS      current
    DESCRIPTION
"
synchronization status for enableSPFbackground
-1 - enableSPFbackground could not be synchronized
 0 - synchronization not configured
 1 - out of sync - running master mode
 2 - in sync - running  mastermode
 3 - in sync - running slave mode
 4 - in sync - running master mode (wait to reach state 2)
"
    ::= {enableSPFbackground 5}

syncStatStrenableSPFbackground  OBJECT-TYPE
    SYNTAX      OCTET STRING
    MAX-ACCESS  read-only
    STATUS      current
    DESCRIPTION
"
synchronization status line from file assp_sync.cfg for enableSPFbackground
 0 - synchronization not configured
 1 - out of sync - running master mode
 2 - in sync - running  mastermode
 3 - in sync - running slave mode
 4 - in sync - running master mode (wait to reach state 2)
"
    ::= {enableSPFbackground 6}

AddSPFHeader  OBJECT-TYPE
    SYNTAX      OCTET STRING
    MAX-ACCESS  read-write
    STATUS      current
    DESCRIPTION
"
Add Received-SPF header to header of all mails processed by SPF.
"
    REFERENCE "Add Received-SPF Header"
    DEFVAL { "1" }
    ::= {SPFDMARCSRS 351}

syncStatAddSPFHeader  OBJECT-TYPE
    SYNTAX      OCTET STRING
    MAX-ACCESS  read-only
    STATUS      current
    DESCRIPTION
"
synchronization status for AddSPFHeader
-1 - AddSPFHeader could not be synchronized
 0 - synchronization not configured
 1 - out of sync - running master mode
 2 - in sync - running  mastermode
 3 - in sync - running slave mode
 4 - in sync - running master mode (wait to reach state 2)
"
    ::= {AddSPFHeader 5}

syncStatStrAddSPFHeader  OBJECT-TYPE
    SYNTAX      OCTET STRING
    MAX-ACCESS  read-only
    STATUS      current
    DESCRIPTION
"
synchronization status line from file assp_sync.cfg for AddSPFHeader
 0 - synchronization not configured
 1 - out of sync - running master mode
 2 - in sync - running  mastermode
 3 - in sync - running slave mode
 4 - in sync - running master mode (wait to reach state 2)
"
    ::= {AddSPFHeader 6}

SPFError  OBJECT-TYPE
    SYNTAX      OCTET STRING
    MAX-ACCESS  read-write
    STATUS      current
    DESCRIPTION
"
SMTP reply for SPF failed messages. Default: '554 5.7.1 failed SPF: SPFRESULT'
  The literal SPFRESULT (case sensitive) is replaced by the actual result.
"
    REFERENCE "SPF Failed Reply"
    DEFVAL { "554 5.7.1 failed SPF: SPFRESULT" }
    ::= {SPFDMARCSRS 352}

syncStatSPFError  OBJECT-TYPE
    SYNTAX      OCTET STRING
    MAX-ACCESS  read-only
    STATUS      current
    DESCRIPTION
"
synchronization status for SPFError
-1 - SPFError could not be synchronized
 0 - synchronization not configured
 1 - out of sync - running master mode
 2 - in sync - running  mastermode
 3 - in sync - running slave mode
 4 - in sync - running master mode (wait to reach state 2)
"
    ::= {SPFError 5}

syncStatStrSPFError  OBJECT-TYPE
    SYNTAX      OCTET STRING
    MAX-ACCESS  read-only
    STATUS      current
    DESCRIPTION
"
synchronization status line from file assp_sync.cfg for SPFError
 0 - synchronization not configured
 1 - out of sync - running master mode
 2 - in sync - running  mastermode
 3 - in sync - running slave mode
 4 - in sync - running master mode (wait to reach state 2)
"
    ::= {SPFError 6}

noSPFRe  OBJECT-TYPE
    SYNTAX      OCTET STRING
    MAX-ACCESS  read-write
    STATUS      current
    DESCRIPTION
"
Put anything here to identify these messages in mailfrom or header
"
    REFERENCE "Skip SPF Processing*"
    DEFVAL { "" }
    ::= {SPFDMARCSRS 353}

syncStatnoSPFRe  OBJECT-TYPE
    SYNTAX      OCTET STRING
    MAX-ACCESS  read-only
    STATUS      current
    DESCRIPTION
"
synchronization status for noSPFRe
-1 - noSPFRe could not be synchronized
 0 - synchronization not configured
 1 - out of sync - running master mode
 2 - in sync - running  mastermode
 3 - in sync - running slave mode
 4 - in sync - running master mode (wait to reach state 2)
"
    ::= {noSPFRe 5}

syncStatStrnoSPFRe  OBJECT-TYPE
    SYNTAX      OCTET STRING
    MAX-ACCESS  read-only
    STATUS      current
    DESCRIPTION
"
synchronization status line from file assp_sync.cfg for noSPFRe
 0 - synchronization not configured
 1 - out of sync - running master mode
 2 - in sync - running  mastermode
 3 - in sync - running slave mode
 4 - in sync - running master mode (wait to reach state 2)
"
    ::= {noSPFRe 6}

SPFoverride  OBJECT-TYPE
    SYNTAX      OCTET STRING
    MAX-ACCESS  read-write
    STATUS      current
    DESCRIPTION
"
Set override to define SPF records for domains that do publish but which you want to override anyway. If you specify only domains the Local SPF Record ( SPFlocalRecord ) below will be used as default. Wildcards are supported. For example: abc.com=>v=spf1 a/24 mx/24 ptr -all|cello.ch=>v=spf1 ip4:213.46.243.0/26  ~all|abc.com|*.def.com . 
 To generate a SPF record for a domain:
 - go to 
 - lookup the domain information in 'Look up your network'
 - right beside 'Addresses in domain used to send email' click on export, and export the list in to plain text
 - copy and past the list in to an editor and generate a comma separated IP list
 - go to an online SPF record generator - for example:  and generate the SPF record
 - put 'domain=>SPF-record' in any of SPFoverride or SPFfallback
 - define the policy as strict as possible
"
    REFERENCE "Override Domains*"
    DEFVAL { "" }
    ::= {SPFDMARCSRS 354}

syncStatSPFoverride  OBJECT-TYPE
    SYNTAX      OCTET STRING
    MAX-ACCESS  read-only
    STATUS      current
    DESCRIPTION
"
synchronization status for SPFoverride
-1 - SPFoverride could not be synchronized
 0 - synchronization not configured
 1 - out of sync - running master mode
 2 - in sync - running  mastermode
 3 - in sync - running slave mode
 4 - in sync - running master mode (wait to reach state 2)
"
    ::= {SPFoverride 5}

syncStatStrSPFoverride  OBJECT-TYPE
    SYNTAX      OCTET STRING
    MAX-ACCESS  read-only
    STATUS      current
    DESCRIPTION
"
synchronization status line from file assp_sync.cfg for SPFoverride
 0 - synchronization not configured
 1 - out of sync - running master mode
 2 - in sync - running  mastermode
 3 - in sync - running slave mode
 4 - in sync - running master mode (wait to reach state 2)
"
    ::= {SPFoverride 6}

SPFfallback  OBJECT-TYPE
    SYNTAX      OCTET STRING
    MAX-ACCESS  read-write
    STATUS      current
    DESCRIPTION
"
Set fallback to define 'pretend' SPF records for domains that don't publish them yet. If you specify only domains the Local SPF Record ( SPFlocalRecord ) below will be used as default. Wildcards are supported. For example: abc.com=>v=spf1 a/24 mx/24 ptr -all|cello.ch=>v=spf1 ip4:213.46.243.0/26  ~all|abc.com|*.def.com
"
    REFERENCE "Fallback Domains*"
    DEFVAL { "" }
    ::= {SPFDMARCSRS 355}

syncStatSPFfallback  OBJECT-TYPE
    SYNTAX      OCTET STRING
    MAX-ACCESS  read-only
    STATUS      current
    DESCRIPTION
"
synchronization status for SPFfallback
-1 - SPFfallback could not be synchronized
 0 - synchronization not configured
 1 - out of sync - running master mode
 2 - in sync - running  mastermode
 3 - in sync - running slave mode
 4 - in sync - running master mode (wait to reach state 2)
"
    ::= {SPFfallback 5}

syncStatStrSPFfallback  OBJECT-TYPE
    SYNTAX      OCTET STRING
    MAX-ACCESS  read-only
    STATUS      current
    DESCRIPTION
"
synchronization status line from file assp_sync.cfg for SPFfallback
 0 - synchronization not configured
 1 - out of sync - running master mode
 2 - in sync - running  mastermode
 3 - in sync - running slave mode
 4 - in sync - running master mode (wait to reach state 2)
"
    ::= {SPFfallback 6}

LocalPolicySPF  OBJECT-TYPE
    SYNTAX      OCTET STRING
    MAX-ACCESS  read-write
    STATUS      current
    DESCRIPTION
"
If the sending domain does not publish its own SPF Records this will be used.The default is v=spf1 a/24 mx/24 ptr ~all
 This option applies to Mail::SPF::Query module only.
"
    REFERENCE "Local SPF Policy"
    DEFVAL { "v=spf1 a/24 mx/24 ptr ~all" }
    ::= {SPFDMARCSRS 356}

syncStatLocalPolicySPF  OBJECT-TYPE
    SYNTAX      OCTET STRING
    MAX-ACCESS  read-only
    STATUS      current
    DESCRIPTION
"
synchronization status for LocalPolicySPF
-1 - LocalPolicySPF could not be synchronized
 0 - synchronization not configured
 1 - out of sync - running master mode
 2 - in sync - running  mastermode
 3 - in sync - running slave mode
 4 - in sync - running master mode (wait to reach state 2)
"
    ::= {LocalPolicySPF 5}

syncStatStrLocalPolicySPF  OBJECT-TYPE
    SYNTAX      OCTET STRING
    MAX-ACCESS  read-only
    STATUS      current
    DESCRIPTION
"
synchronization status line from file assp_sync.cfg for LocalPolicySPF
 0 - synchronization not configured
 1 - out of sync - running master mode
 2 - in sync - running  mastermode
 3 - in sync - running slave mode
 4 - in sync - running master mode (wait to reach state 2)
"
    ::= {LocalPolicySPF 6}

SPFlocalRecord  OBJECT-TYPE
    SYNTAX      OCTET STRING
    MAX-ACCESS  read-write
    STATUS      current
    DESCRIPTION
"
Used in Fallback/Override DomainsThe default is v=spf1 a/24 mx/24 ptr -all
"
    REFERENCE "Fallback/Override SPF Record"
    DEFVAL { "v=spf1 a/24 mx/24 ptr -all" }
    ::= {SPFDMARCSRS 357}

syncStatSPFlocalRecord  OBJECT-TYPE
    SYNTAX      OCTET STRING
    MAX-ACCESS  read-only
    STATUS      current
    DESCRIPTION
"
synchronization status for SPFlocalRecord
-1 - SPFlocalRecord could not be synchronized
 0 - synchronization not configured
 1 - out of sync - running master mode
 2 - in sync - running  mastermode
 3 - in sync - running slave mode
 4 - in sync - running master mode (wait to reach state 2)
"
    ::= {SPFlocalRecord 5}

syncStatStrSPFlocalRecord  OBJECT-TYPE
    SYNTAX      OCTET STRING
    MAX-ACCESS  read-only
    STATUS      current
    DESCRIPTION
"
synchronization status line from file assp_sync.cfg for SPFlocalRecord
 0 - synchronization not configured
 1 - out of sync - running master mode
 2 - in sync - running  mastermode
 3 - in sync - running slave mode
 4 - in sync - running master mode (wait to reach state 2)
"
    ::= {SPFlocalRecord 6}

strictSPFRe  OBJECT-TYPE
    SYNTAX      OCTET STRING
    MAX-ACCESS  read-write
    STATUS      current
    DESCRIPTION
"
Softfail/Neutral will be failed for these sending addresses. Put anything here to identify the addresses
"
    REFERENCE "Strict SPF Processing Regex*"
    DEFVAL { "file:files/strictspf.txt" }
    ::= {SPFDMARCSRS 358}

syncStatstrictSPFRe  OBJECT-TYPE
    SYNTAX      OCTET STRING
    MAX-ACCESS  read-only
    STATUS      current
    DESCRIPTION
"
synchronization status for strictSPFRe
-1 - strictSPFRe could not be synchronized
 0 - synchronization not configured
 1 - out of sync - running master mode
 2 - in sync - running  mastermode
 3 - in sync - running slave mode
 4 - in sync - running master mode (wait to reach state 2)
"
    ::= {strictSPFRe 5}

syncStatStrstrictSPFRe  OBJECT-TYPE
    SYNTAX      OCTET STRING
    MAX-ACCESS  read-only
    STATUS      current
    DESCRIPTION
"
synchronization status line from file assp_sync.cfg for strictSPFRe
 0 - synchronization not configured
 1 - out of sync - running master mode
 2 - in sync - running  mastermode
 3 - in sync - running slave mode
 4 - in sync - running master mode (wait to reach state 2)
"
    ::= {strictSPFRe 6}

blockstrictSPFRe  OBJECT-TYPE
    SYNTAX      OCTET STRING
    MAX-ACCESS  read-write
    STATUS      current
    DESCRIPTION
"
All failed messages will be blocked for these sending addresses. Put anything here to identify the addresses.
"
    REFERENCE "Block SPF Processing Regex*"
    DEFVAL { "@ebay.com|@paypal.com" }
    ::= {SPFDMARCSRS 359}

syncStatblockstrictSPFRe  OBJECT-TYPE
    SYNTAX      OCTET STRING
    MAX-ACCESS  read-only
    STATUS      current
    DESCRIPTION
"
synchronization status for blockstrictSPFRe
-1 - blockstrictSPFRe could not be synchronized
 0 - synchronization not configured
 1 - out of sync - running master mode
 2 - in sync - running  mastermode
 3 - in sync - running slave mode
 4 - in sync - running master mode (wait to reach state 2)
"
    ::= {blockstrictSPFRe 5}

syncStatStrblockstrictSPFRe  OBJECT-TYPE
    SYNTAX      OCTET STRING
    MAX-ACCESS  read-only
    STATUS      current
    DESCRIPTION
"
synchronization status line from file assp_sync.cfg for blockstrictSPFRe
 0 - synchronization not configured
 1 - out of sync - running master mode
 2 - in sync - running  mastermode
 3 - in sync - running slave mode
 4 - in sync - running master mode (wait to reach state 2)
"
    ::= {blockstrictSPFRe 6}

SPFsoftfail  OBJECT-TYPE
    SYNTAX      OCTET STRING
    MAX-ACCESS  read-write
    STATUS      current
    DESCRIPTION
"
Intentionally fail SPF softfail status responses. The possible results of a query are:
pass:The client IP address is an authorized mailer for the sender. The mail should be accepted subject to local policy regarding the sender.
fail:The client IP address is not an authorized mailer, and the sender wants you to reject the transaction for fear of forgery.
softfail:The client IP address is not an authorized mailer, but the sender prefers that you accept the transaction because it isn't absolutely sure all its users are mailing through approved servers. The softfail status is often used during initial deployment of SPF records by a domain.
neutral:The sender makes no assertion about the status of the client IP.
none:There is no SPF record for this domain.
permerror &amp; temperror:The DNS lookup encountered an error during processing.
unknown:The domain has a configuration error in the published data or defines a mechanism that this library does not understand.
"
    REFERENCE "Fail SPF Softfail Validations"
    DEFVAL { "" }
    ::= {SPFDMARCSRS 360}

syncStatSPFsoftfail  OBJECT-TYPE
    SYNTAX      OCTET STRING
    MAX-ACCESS  read-only
    STATUS      current
    DESCRIPTION
"
synchronization status for SPFsoftfail
-1 - SPFsoftfail could not be synchronized
 0 - synchronization not configured
 1 - out of sync - running master mode
 2 - in sync - running  mastermode
 3 - in sync - running slave mode
 4 - in sync - running master mode (wait to reach state 2)
"
    ::= {SPFsoftfail 5}

syncStatStrSPFsoftfail  OBJECT-TYPE
    SYNTAX      OCTET STRING
    MAX-ACCESS  read-only
    STATUS      current
    DESCRIPTION
"
synchronization status line from file assp_sync.cfg for SPFsoftfail
 0 - synchronization not configured
 1 - out of sync - running master mode
 2 - in sync - running  mastermode
 3 - in sync - running slave mode
 4 - in sync - running master mode (wait to reach state 2)
"
    ::= {SPFsoftfail 6}

SPFneutral  OBJECT-TYPE
    SYNTAX      OCTET STRING
    MAX-ACCESS  read-write
    STATUS      current
    DESCRIPTION
"
Intentionally fail SPF neutral status responses
"
    REFERENCE "Fail SPF Neutral Validations"
    DEFVAL { "" }
    ::= {SPFDMARCSRS 361}

syncStatSPFneutral  OBJECT-TYPE
    SYNTAX      OCTET STRING
    MAX-ACCESS  read-only
    STATUS      current
    DESCRIPTION
"
synchronization status for SPFneutral
-1 - SPFneutral could not be synchronized
 0 - synchronization not configured
 1 - out of sync - running master mode
 2 - in sync - running  mastermode
 3 - in sync - running slave mode
 4 - in sync - running master mode (wait to reach state 2)
"
    ::= {SPFneutral 5}

syncStatStrSPFneutral  OBJECT-TYPE
    SYNTAX      OCTET STRING
    MAX-ACCESS  read-only
    STATUS      current
    DESCRIPTION
"
synchronization status line from file assp_sync.cfg for SPFneutral
 0 - synchronization not configured
 1 - out of sync - running master mode
 2 - in sync - running  mastermode
 3 - in sync - running slave mode
 4 - in sync - running master mode (wait to reach state 2)
"
    ::= {SPFneutral 6}

SPFqueryerror  OBJECT-TYPE
    SYNTAX      OCTET STRING
    MAX-ACCESS  read-write
    STATUS      current
    DESCRIPTION
"
Intentionally fail SPF 'error' status responses
"
    REFERENCE "Fail SPF Error Responses"
    DEFVAL { "" }
    ::= {SPFDMARCSRS 362}

syncStatSPFqueryerror  OBJECT-TYPE
    SYNTAX      OCTET STRING
    MAX-ACCESS  read-only
    STATUS      current
    DESCRIPTION
"
synchronization status for SPFqueryerror
-1 - SPFqueryerror could not be synchronized
 0 - synchronization not configured
 1 - out of sync - running master mode
 2 - in sync - running  mastermode
 3 - in sync - running slave mode
 4 - in sync - running master mode (wait to reach state 2)
"
    ::= {SPFqueryerror 5}

syncStatStrSPFqueryerror  OBJECT-TYPE
    SYNTAX      OCTET STRING
    MAX-ACCESS  read-only
    STATUS      current
    DESCRIPTION
"
synchronization status line from file assp_sync.cfg for SPFqueryerror
 0 - synchronization not configured
 1 - out of sync - running master mode
 2 - in sync - running  mastermode
 3 - in sync - running slave mode
 4 - in sync - running master mode (wait to reach state 2)
"
    ::= {SPFqueryerror 6}

SPFnone  OBJECT-TYPE
    SYNTAX      OCTET STRING
    MAX-ACCESS  read-write
    STATUS      current
    DESCRIPTION
"
Intentionally fail SPF 'none' and 'unknown' status responses
"
    REFERENCE "Fail SPF None and Unknown Responses"
    DEFVAL { "" }
    ::= {SPFDMARCSRS 363}

syncStatSPFnone  OBJECT-TYPE
    SYNTAX      OCTET STRING
    MAX-ACCESS  read-only
    STATUS      current
    DESCRIPTION
"
synchronization status for SPFnone
-1 - SPFnone could not be synchronized
 0 - synchronization not configured
 1 - out of sync - running master mode
 2 - in sync - running  mastermode
 3 - in sync - running slave mode
 4 - in sync - running master mode (wait to reach state 2)
"
    ::= {SPFnone 5}

syncStatStrSPFnone  OBJECT-TYPE
    SYNTAX      OCTET STRING
    MAX-ACCESS  read-only
    STATUS      current
    DESCRIPTION
"
synchronization status line from file assp_sync.cfg for SPFnone
 0 - synchronization not configured
 1 - out of sync - running master mode
 2 - in sync - running  mastermode
 3 - in sync - running slave mode
 4 - in sync - running master mode (wait to reach state 2)
"
    ::= {SPFnone 6}

SPFunknown  OBJECT-TYPE
    SYNTAX      OCTET STRING
    MAX-ACCESS  read-write
    STATUS      current
    DESCRIPTION
"
Intentionally fail SPF 'unknown'  status responses
"
    REFERENCE "Fail SPF Unknown  Responses"
    DEFVAL { "" }
    ::= {SPFDMARCSRS 364}

syncStatSPFunknown  OBJECT-TYPE
    SYNTAX      OCTET STRING
    MAX-ACCESS  read-only
    STATUS      current
    DESCRIPTION
"
synchronization status for SPFunknown
-1 - SPFunknown could not be synchronized
 0 - synchronization not configured
 1 - out of sync - running master mode
 2 - in sync - running  mastermode
 3 - in sync - running slave mode
 4 - in sync - running master mode (wait to reach state 2)
"
    ::= {SPFunknown 5}

syncStatStrSPFunknown  OBJECT-TYPE
    SYNTAX      OCTET STRING
    MAX-ACCESS  read-only
    STATUS      current
    DESCRIPTION
"
synchronization status line from file assp_sync.cfg for SPFunknown
 0 - synchronization not configured
 1 - out of sync - running master mode
 2 - in sync - running  mastermode
 3 - in sync - running slave mode
 4 - in sync - running master mode (wait to reach state 2)
"
    ::= {SPFunknown 6}

SPFCacheInterval  OBJECT-TYPE
    SYNTAX      OCTET STRING
    MAX-ACCESS  read-write
    STATUS      current
    DESCRIPTION
"
SPF records in cache will be removed after this interval in days. 0 will disable the cache.
"
    REFERENCE "SPF Cache Refresh Interval"
    DEFVAL { "7" }
    ::= {SPFDMARCSRS 365}

syncStatSPFCacheInterval  OBJECT-TYPE
    SYNTAX      OCTET STRING
    MAX-ACCESS  read-only
    STATUS      current
    DESCRIPTION
"
synchronization status for SPFCacheInterval
-1 - SPFCacheInterval could not be synchronized
 0 - synchronization not configured
 1 - out of sync - running master mode
 2 - in sync - running  mastermode
 3 - in sync - running slave mode
 4 - in sync - running master mode (wait to reach state 2)
"
    ::= {SPFCacheInterval 5}

syncStatStrSPFCacheInterval  OBJECT-TYPE
    SYNTAX      OCTET STRING
    MAX-ACCESS  read-only
    STATUS      current
    DESCRIPTION
"
synchronization status line from file assp_sync.cfg for SPFCacheInterval
 0 - synchronization not configured
 1 - out of sync - running master mode
 2 - in sync - running  mastermode
 3 - in sync - running slave mode
 4 - in sync - running master mode (wait to reach state 2)
"
    ::= {SPFCacheInterval 6}

DebugSPF  OBJECT-TYPE
    SYNTAX      OCTET STRING
    MAX-ACCESS  read-write
    STATUS      current
    DESCRIPTION
"
Enables verbose debugging of SPF/DNS/Whois/Senderbase queries within the Mail::SPF and Net::DNS modules.
 
 
  
"
    REFERENCE "Enable SPF/DNS Debug output to ASSP Logfile"
    DEFVAL { "" }
    ::= {SPFDMARCSRS 366}

syncStatDebugSPF  OBJECT-TYPE
    SYNTAX      OCTET STRING
    MAX-ACCESS  read-only
    STATUS      current
    DESCRIPTION
"
synchronization status for DebugSPF
-1 - DebugSPF could not be synchronized
 0 - synchronization not configured
 1 - out of sync - running master mode
 2 - in sync - running  mastermode
 3 - in sync - running slave mode
 4 - in sync - running master mode (wait to reach state 2)
"
    ::= {DebugSPF 5}

syncStatStrDebugSPF  OBJECT-TYPE
    SYNTAX      OCTET STRING
    MAX-ACCESS  read-only
    STATUS      current
    DESCRIPTION
"
synchronization status line from file assp_sync.cfg for DebugSPF
 0 - synchronization not configured
 1 - out of sync - running master mode
 2 - in sync - running  mastermode
 3 - in sync - running slave mode
 4 - in sync - running master mode (wait to reach state 2)
"
    ::= {DebugSPF 6}

EnableSRS  OBJECT-TYPE
    SYNTAX      OCTET STRING
    MAX-ACCESS  read-write
    STATUS      current
    DESCRIPTION
"
Enable Sender Rewriting Scheme as described at .
  This requires an installed  module in PERL.
  You should use SRS if your message handling system forwards email for domains with published spf records and there SPF record not includes your MX.
  NOTICE: In case your local users are forwarding mails (e.g. from external domains) to external domains (external mail accounts) and these foreign domains bounces back (e.g. out_of_office / vacation), your MTA (smtpDestination) will possibly get mails from external domains to be deliverd to external domains!
  Note that you have to setup the outgoing path (Relay Host and Port) to let ASSP see and rewrite your outgoing traffic. Testmode is set with srsTestMode.
"
    REFERENCE "Enable Sender Rewriting Scheme"
    DEFVAL { "" }
    ::= {SPFDMARCSRS 367}

syncStatEnableSRS  OBJECT-TYPE
    SYNTAX      OCTET STRING
    MAX-ACCESS  read-only
    STATUS      current
    DESCRIPTION
"
synchronization status for EnableSRS
-1 - EnableSRS could not be synchronized
 0 - synchronization not configured
 1 - out of sync - running master mode
 2 - in sync - running  mastermode
 3 - in sync - running slave mode
 4 - in sync - running master mode (wait to reach state 2)
"
    ::= {EnableSRS 5}

syncStatStrEnableSRS  OBJECT-TYPE
    SYNTAX      OCTET STRING
    MAX-ACCESS  read-only
    STATUS      current
    DESCRIPTION
"
synchronization status line from file assp_sync.cfg for EnableSRS
 0 - synchronization not configured
 1 - out of sync - running master mode
 2 - in sync - running  mastermode
 3 - in sync - running slave mode
 4 - in sync - running master mode (wait to reach state 2)
"
    ::= {EnableSRS 6}

SRSAliasDomain  OBJECT-TYPE
    SYNTAX      OCTET STRING
    MAX-ACCESS  read-write
    STATUS      current
    DESCRIPTION
"
SPF requires the SMTP client IP to match the envelope sender (return-path). When a message is forwarded through
  an intermediate server, that intermediate server may need to rewrite the return-path to remain SPF compliant.
  For example: thisdomain.com
"
    REFERENCE "Alias Domain"
    DEFVAL { "thisdomain.com" }
    ::= {SPFDMARCSRS 368}

syncStatSRSAliasDomain  OBJECT-TYPE
    SYNTAX      OCTET STRING
    MAX-ACCESS  read-only
    STATUS      current
    DESCRIPTION
"
synchronization status for SRSAliasDomain
-1 - SRSAliasDomain could not be synchronized
 0 - synchronization not configured
 1 - out of sync - running master mode
 2 - in sync - running  mastermode
 3 - in sync - running slave mode
 4 - in sync - running master mode (wait to reach state 2)
"
    ::= {SRSAliasDomain 5}

syncStatStrSRSAliasDomain  OBJECT-TYPE
    SYNTAX      OCTET STRING
    MAX-ACCESS  read-only
    STATUS      current
    DESCRIPTION
"
synchronization status line from file assp_sync.cfg for SRSAliasDomain
 0 - synchronization not configured
 1 - out of sync - running master mode
 2 - in sync - running  mastermode
 3 - in sync - running slave mode
 4 - in sync - running master mode (wait to reach state 2)
"
    ::= {SRSAliasDomain 6}

SRSSecretKey  OBJECT-TYPE
    SYNTAX      OCTET STRING
    MAX-ACCESS  read-write
    STATUS      current
    DESCRIPTION
"
A key for the cryptographic algorithms -- Must be at least 5 characters long.
"
    REFERENCE "Secret Key"
    DEFVAL { "" }
    ::= {SPFDMARCSRS 369}

syncStatSRSSecretKey  OBJECT-TYPE
    SYNTAX      OCTET STRING
    MAX-ACCESS  read-only
    STATUS      current
    DESCRIPTION
"
synchronization status for SRSSecretKey
-1 - SRSSecretKey could not be synchronized
 0 - synchronization not configured
 1 - out of sync - running master mode
 2 - in sync - running  mastermode
 3 - in sync - running slave mode
 4 - in sync - running master mode (wait to reach state 2)
"
    ::= {SRSSecretKey 5}

syncStatStrSRSSecretKey  OBJECT-TYPE
    SYNTAX      OCTET STRING
    MAX-ACCESS  read-only
    STATUS      current
    DESCRIPTION
"
synchronization status line from file assp_sync.cfg for SRSSecretKey
 0 - synchronization not configured
 1 - out of sync - running master mode
 2 - in sync - running  mastermode
 3 - in sync - running slave mode
 4 - in sync - running master mode (wait to reach state 2)
"
    ::= {SRSSecretKey 6}

SRSTimestampMaxAge  OBJECT-TYPE
    SYNTAX      OCTET STRING
    MAX-ACCESS  read-write
    STATUS      current
    DESCRIPTION
"
Enter the maximum number of days for which a timestamp is considered valid. Default is 2 days. After this number of days a SRS bounce is no longer valid!
"
    REFERENCE "Maximum Timestamp Age"
    DEFVAL { "2" }
    ::= {SPFDMARCSRS 370}

syncStatSRSTimestampMaxAge  OBJECT-TYPE
    SYNTAX      OCTET STRING
    MAX-ACCESS  read-only
    STATUS      current
    DESCRIPTION
"
synchronization status for SRSTimestampMaxAge
-1 - SRSTimestampMaxAge could not be synchronized
 0 - synchronization not configured
 1 - out of sync - running master mode
 2 - in sync - running  mastermode
 3 - in sync - running slave mode
 4 - in sync - running master mode (wait to reach state 2)
"
    ::= {SRSTimestampMaxAge 5}

syncStatStrSRSTimestampMaxAge  OBJECT-TYPE
    SYNTAX      OCTET STRING
    MAX-ACCESS  read-only
    STATUS      current
    DESCRIPTION
"
synchronization status line from file assp_sync.cfg for SRSTimestampMaxAge
 0 - synchronization not configured
 1 - out of sync - running master mode
 2 - in sync - running  mastermode
 3 - in sync - running slave mode
 4 - in sync - running master mode (wait to reach state 2)
"
    ::= {SRSTimestampMaxAge 6}

SRSHashLength  OBJECT-TYPE
    SYNTAX      OCTET STRING
    MAX-ACCESS  read-write
    STATUS      current
    DESCRIPTION
"
The number of bytes of base64 encoded data to use for the cryptographic hash.
  More is better, but makes for longer addresses which might exceed the 64 character length suggested by RFC2821.
  This defaults to 6, which gives 6 x 6 = 36 bits of cryptographic information, which means that a spammer will have 
  to make 2^36 attempts to guarantee forging an SRS address.
"
    REFERENCE "Hash Length"
    DEFVAL { "6" }
    ::= {SPFDMARCSRS 371}

syncStatSRSHashLength  OBJECT-TYPE
    SYNTAX      OCTET STRING
    MAX-ACCESS  read-only
    STATUS      current
    DESCRIPTION
"
synchronization status for SRSHashLength
-1 - SRSHashLength could not be synchronized
 0 - synchronization not configured
 1 - out of sync - running master mode
 2 - in sync - running  mastermode
 3 - in sync - running slave mode
 4 - in sync - running master mode (wait to reach state 2)
"
    ::= {SRSHashLength 5}

syncStatStrSRSHashLength  OBJECT-TYPE
    SYNTAX      OCTET STRING
    MAX-ACCESS  read-only
    STATUS      current
    DESCRIPTION
"
synchronization status line from file assp_sync.cfg for SRSHashLength
 0 - synchronization not configured
 1 - out of sync - running master mode
 2 - in sync - running  mastermode
 3 - in sync - running slave mode
 4 - in sync - running master mode (wait to reach state 2)
"
    ::= {SRSHashLength 6}

SRSValidateBounce  OBJECT-TYPE
    SYNTAX      OCTET STRING
    MAX-ACCESS  read-write
    STATUS      current
    DESCRIPTION
"
Bounce messages that fail reverse SRS validation (but not a valid SMTP probe)
  will receive a 554 5.7.5 [Bounce address not SRS signed] SMTP error code. Testmode is set with srsTestMode, scoring is set with srsValencePB.
"
    REFERENCE "Enable Bounce Recipient Validation"
    DEFVAL { "0" }
    ::= {SPFDMARCSRS 372}

syncStatSRSValidateBounce  OBJECT-TYPE
    SYNTAX      OCTET STRING
    MAX-ACCESS  read-only
    STATUS      current
    DESCRIPTION
"
synchronization status for SRSValidateBounce
-1 - SRSValidateBounce could not be synchronized
 0 - synchronization not configured
 1 - out of sync - running master mode
 2 - in sync - running  mastermode
 3 - in sync - running slave mode
 4 - in sync - running master mode (wait to reach state 2)
"
    ::= {SRSValidateBounce 5}

syncStatStrSRSValidateBounce  OBJECT-TYPE
    SYNTAX      OCTET STRING
    MAX-ACCESS  read-only
    STATUS      current
    DESCRIPTION
"
synchronization status line from file assp_sync.cfg for SRSValidateBounce
 0 - synchronization not configured
 1 - out of sync - running master mode
 2 - in sync - running  mastermode
 3 - in sync - running slave mode
 4 - in sync - running master mode (wait to reach state 2)
"
    ::= {SRSValidateBounce 6}

SRSno  OBJECT-TYPE
    SYNTAX      OCTET STRING
    MAX-ACCESS  read-write
    STATUS      current
    DESCRIPTION
"
Don't rewrite addresses when messages come from these addresses. Accepts specific addresses (user@domain.com), user parts (user) or entire domains (@domain.com). For example: fribo@thisdomain.com|jhanna|@sillyguys.org
"
    REFERENCE "Don't Rewrite These Addresses*"
    DEFVAL { "" }
    ::= {SPFDMARCSRS 373}

syncStatSRSno  OBJECT-TYPE
    SYNTAX      OCTET STRING
    MAX-ACCESS  read-only
    STATUS      current
    DESCRIPTION
"
synchronization status for SRSno
-1 - SRSno could not be synchronized
 0 - synchronization not configured
 1 - out of sync - running master mode
 2 - in sync - running  mastermode
 3 - in sync - running slave mode
 4 - in sync - running master mode (wait to reach state 2)
"
    ::= {SRSno 5}

syncStatStrSRSno  OBJECT-TYPE
    SYNTAX      OCTET STRING
    MAX-ACCESS  read-only
    STATUS      current
    DESCRIPTION
"
synchronization status line from file assp_sync.cfg for SRSno
 0 - synchronization not configured
 1 - out of sync - running master mode
 2 - in sync - running  mastermode
 3 - in sync - running slave mode
 4 - in sync - running master mode (wait to reach state 2)
"
    ::= {SRSno 6}

noSRS  OBJECT-TYPE
    SYNTAX      OCTET STRING
    MAX-ACCESS  read-write
    STATUS      current
    DESCRIPTION
"
Enter IP addresses that you don't want to validate bounces from, separated by pipes (|).
  For example:  127.0.0.1|172.16..
  
  
"
    REFERENCE "Don't Validate Bounces From these IPs*"
    DEFVAL { "" }
    ::= {SPFDMARCSRS 374}

syncStatnoSRS  OBJECT-TYPE
    SYNTAX      OCTET STRING
    MAX-ACCESS  read-only
    STATUS      current
    DESCRIPTION
"
synchronization status for noSRS
-1 - noSRS could not be synchronized
 0 - synchronization not configured
 1 - out of sync - running master mode
 2 - in sync - running  mastermode
 3 - in sync - running slave mode
 4 - in sync - running master mode (wait to reach state 2)
"
    ::= {noSRS 5}

syncStatStrnoSRS  OBJECT-TYPE
    SYNTAX      OCTET STRING
    MAX-ACCESS  read-only
    STATUS      current
    DESCRIPTION
"
synchronization status line from file assp_sync.cfg for noSRS
 0 - synchronization not configured
 1 - out of sync - running master mode
 2 - in sync - running  mastermode
 3 - in sync - running slave mode
 4 - in sync - running master mode (wait to reach state 2)
"
    ::= {noSRS 6}

SPFNP  OBJECT-TYPE
    SYNTAX      OCTET STRING
    MAX-ACCESS  read-write
    STATUS      current
    DESCRIPTION
"
Enable Sender Policy Framework Validation for nonprocessed messages also.
"
    REFERENCE "noProcessing SPF Validation"
    DEFVAL { "" }
    ::= {SPFDMARCSRS 956}

syncStatSPFNP  OBJECT-TYPE
    SYNTAX      OCTET STRING
    MAX-ACCESS  read-only
    STATUS      current
    DESCRIPTION
"
synchronization status for SPFNP
-1 - SPFNP could not be synchronized
 0 - synchronization not configured
 1 - out of sync - running master mode
 2 - in sync - running  mastermode
 3 - in sync - running slave mode
 4 - in sync - running master mode (wait to reach state 2)
"
    ::= {SPFNP 5}

syncStatStrSPFNP  OBJECT-TYPE
    SYNTAX      OCTET STRING
    MAX-ACCESS  read-only
    STATUS      current
    DESCRIPTION
"
synchronization status line from file assp_sync.cfg for SPFNP
 0 - synchronization not configured
 1 - out of sync - running master mode
 2 - in sync - running  mastermode
 3 - in sync - running slave mode
 4 - in sync - running master mode (wait to reach state 2)
"
    ::= {SPFNP 6}

DMARCReportFrom  OBJECT-TYPE
    SYNTAX      OCTET STRING
    MAX-ACCESS  read-write
    STATUS      current
    DESCRIPTION
"
The email address to be used as FROM: address to send  reports. If blank, no DMARC reports will be sent! If only the user name is defined, assp will add the domain name that belongs to the report.
"
    REFERENCE "From Address for DMARC Reports"
    DEFVAL { "" }
    ::= {SPFDMARCSRS 973}

syncStatDMARCReportFrom  OBJECT-TYPE
    SYNTAX      OCTET STRING
    MAX-ACCESS  read-only
    STATUS      current
    DESCRIPTION
"
synchronization status for DMARCReportFrom
-1 - DMARCReportFrom could not be synchronized
 0 - synchronization not configured
 1 - out of sync - running master mode
 2 - in sync - running  mastermode
 3 - in sync - running slave mode
 4 - in sync - running master mode (wait to reach state 2)
"
    ::= {DMARCReportFrom 5}

syncStatStrDMARCReportFrom  OBJECT-TYPE
    SYNTAX      OCTET STRING
    MAX-ACCESS  read-only
    STATUS      current
    DESCRIPTION
"
synchronization status line from file assp_sync.cfg for DMARCReportFrom
 0 - synchronization not configured
 1 - out of sync - running master mode
 2 - in sync - running  mastermode
 3 - in sync - running slave mode
 4 - in sync - running master mode (wait to reach state 2)
"
    ::= {DMARCReportFrom 6}

DoSPFinHeader  OBJECT-TYPE
    SYNTAX      OCTET STRING
    MAX-ACCESS  read-write
    STATUS      current
    DESCRIPTION
"
Do an additional SPF check on the header from: address if it is in blockstrictSPFRe *** this check breakes RFC rules ***.
"
    REFERENCE "Additional SPF Check on the Header from"
    DEFVAL { "" }
    ::= {SPFDMARCSRS 982}

syncStatDoSPFinHeader  OBJECT-TYPE
    SYNTAX      OCTET STRING
    MAX-ACCESS  read-only
    STATUS      current
    DESCRIPTION
"
synchronization status for DoSPFinHeader
-1 - DoSPFinHeader could not be synchronized
 0 - synchronization not configured
 1 - out of sync - running master mode
 2 - in sync - running  mastermode
 3 - in sync - running slave mode
 4 - in sync - running master mode (wait to reach state 2)
"
    ::= {DoSPFinHeader 5}

syncStatStrDoSPFinHeader  OBJECT-TYPE
    SYNTAX      OCTET STRING
    MAX-ACCESS  read-only
    STATUS      current
    DESCRIPTION
"
synchronization status line from file assp_sync.cfg for DoSPFinHeader
 0 - synchronization not configured
 1 - out of sync - running master mode
 2 - in sync - running  mastermode
 3 - in sync - running slave mode
 4 - in sync - running master mode (wait to reach state 2)
"
    ::= {DoSPFinHeader 6}

noDMARCReportDomain  OBJECT-TYPE
    SYNTAX      OCTET STRING
    MAX-ACCESS  read-write
    STATUS      current
    DESCRIPTION
"
Put any DMARC report recipient domain or address (ruf/rua) in to this list - for example if DMARC reports could be never delivered for any reason.
 Accepts specific addresses (user@example.com), user parts (user) or entire domains (@example.com). Wildcards are supported (fribo*@example.com).
"
    REFERENCE "Don't send DMARC reports to these Addresses/Domains*"
    DEFVAL { "" }
    ::= {SPFDMARCSRS 1024}

syncStatnoDMARCReportDomain  OBJECT-TYPE
    SYNTAX      OCTET STRING
    MAX-ACCESS  read-only
    STATUS      current
    DESCRIPTION
"
synchronization status for noDMARCReportDomain
-1 - noDMARCReportDomain could not be synchronized
 0 - synchronization not configured
 1 - out of sync - running master mode
 2 - in sync - running  mastermode
 3 - in sync - running slave mode
 4 - in sync - running master mode (wait to reach state 2)
"
    ::= {noDMARCReportDomain 5}

syncStatStrnoDMARCReportDomain  OBJECT-TYPE
    SYNTAX      OCTET STRING
    MAX-ACCESS  read-only
    STATUS      current
    DESCRIPTION
"
synchronization status line from file assp_sync.cfg for noDMARCReportDomain
 0 - synchronization not configured
 1 - out of sync - running master mode
 2 - in sync - running  mastermode
 3 - in sync - running slave mode
 4 - in sync - running master mode (wait to reach state 2)
"
    ::= {noDMARCReportDomain 6}

DoDMARC  OBJECT-TYPE
    SYNTAX      OCTET STRING
    MAX-ACCESS  read-write
    STATUS      current
    DESCRIPTION
"
If enabled and ValidateSPF and DoDKIM are enabled and the sending domain has published a DMARC-record/policy, assp will act on the mail according to the senders DMARC-policy using the results of the SPF and DKIM check. It is save to leave this feature ON, it will not produce false positives!
"
    REFERENCE "Enable DMARC Check"
    DEFVAL { "1" }
    ::= {SPFDMARCSRS 1041}

syncStatDoDMARC  OBJECT-TYPE
    SYNTAX      OCTET STRING
    MAX-ACCESS  read-only
    STATUS      current
    DESCRIPTION
"
synchronization status for DoDMARC
-1 - DoDMARC could not be synchronized
 0 - synchronization not configured
 1 - out of sync - running master mode
 2 - in sync - running  mastermode
 3 - in sync - running slave mode
 4 - in sync - running master mode (wait to reach state 2)
"
    ::= {DoDMARC 5}

syncStatStrDoDMARC  OBJECT-TYPE
    SYNTAX      OCTET STRING
    MAX-ACCESS  read-only
    STATUS      current
    DESCRIPTION
"
synchronization status line from file assp_sync.cfg for DoDMARC
 0 - synchronization not configured
 1 - out of sync - running master mode
 2 - in sync - running  mastermode
 3 - in sync - running slave mode
 4 - in sync - running master mode (wait to reach state 2)
"
    ::= {DoDMARC 6}

DNSBL  OBJECT IDENTIFIER ::= {asspConfig 18}
ValidateRBL  OBJECT-TYPE
    SYNTAX      OCTET STRING
    MAX-ACCESS  read-write
    STATUS      current
    DESCRIPTION
"
This requires an installed  module in PERL.
"
    REFERENCE "Enable DNS Blacklist Validation "
    DEFVAL { "1" }
    ::= {DNSBL 375}

syncStatValidateRBL  OBJECT-TYPE
    SYNTAX      OCTET STRING
    MAX-ACCESS  read-only
    STATUS      current
    DESCRIPTION
"
synchronization status for ValidateRBL
-1 - ValidateRBL could not be synchronized
 0 - synchronization not configured
 1 - out of sync - running master mode
 2 - in sync - running  mastermode
 3 - in sync - running slave mode
 4 - in sync - running master mode (wait to reach state 2)
"
    ::= {ValidateRBL 5}

syncStatStrValidateRBL  OBJECT-TYPE
    SYNTAX      OCTET STRING
    MAX-ACCESS  read-only
    STATUS      current
    DESCRIPTION
"
synchronization status line from file assp_sync.cfg for ValidateRBL
 0 - synchronization not configured
 1 - out of sync - running master mode
 2 - in sync - running  mastermode
 3 - in sync - running slave mode
 4 - in sync - running master mode (wait to reach state 2)
"
    ::= {ValidateRBL 6}

ForceRBLCache  OBJECT-TYPE
    SYNTAX      OCTET STRING
    MAX-ACCESS  read-write
    STATUS      current
    DESCRIPTION
"
If set, ASSP will use cached DNSBL hits to block messages before other tests. testmode will override this. spamlover settings will be ignored.
"
    REFERENCE "Early DNSBL Cache Blocking"
    DEFVAL { "" }
    ::= {DNSBL 376}

syncStatForceRBLCache  OBJECT-TYPE
    SYNTAX      OCTET STRING
    MAX-ACCESS  read-only
    STATUS      current
    DESCRIPTION
"
synchronization status for ForceRBLCache
-1 - ForceRBLCache could not be synchronized
 0 - synchronization not configured
 1 - out of sync - running master mode
 2 - in sync - running  mastermode
 3 - in sync - running slave mode
 4 - in sync - running master mode (wait to reach state 2)
"
    ::= {ForceRBLCache 5}

syncStatStrForceRBLCache  OBJECT-TYPE
    SYNTAX      OCTET STRING
    MAX-ACCESS  read-only
    STATUS      current
    DESCRIPTION
"
synchronization status line from file assp_sync.cfg for ForceRBLCache
 0 - synchronization not configured
 1 - out of sync - running master mode
 2 - in sync - running  mastermode
 3 - in sync - running slave mode
 4 - in sync - running master mode (wait to reach state 2)
"
    ::= {ForceRBLCache 6}

noRBL  OBJECT-TYPE
    SYNTAX      OCTET STRING
    MAX-ACCESS  read-write
    STATUS      current
    DESCRIPTION
"
Enter IP addresses that you don't want to be DNSBL validated, separated by pipes (|). For example:  127.0.0.1|172.16..
"
    REFERENCE "Don't do DNSBL for these IPs*"
    DEFVAL { "" }
    ::= {DNSBL 377}

syncStatnoRBL  OBJECT-TYPE
    SYNTAX      OCTET STRING
    MAX-ACCESS  read-only
    STATUS      current
    DESCRIPTION
"
synchronization status for noRBL
-1 - noRBL could not be synchronized
 0 - synchronization not configured
 1 - out of sync - running master mode
 2 - in sync - running  mastermode
 3 - in sync - running slave mode
 4 - in sync - running master mode (wait to reach state 2)
"
    ::= {noRBL 5}

syncStatStrnoRBL  OBJECT-TYPE
    SYNTAX      OCTET STRING
    MAX-ACCESS  read-only
    STATUS      current
    DESCRIPTION
"
synchronization status line from file assp_sync.cfg for noRBL
 0 - synchronization not configured
 1 - out of sync - running master mode
 2 - in sync - running  mastermode
 3 - in sync - running slave mode
 4 - in sync - running master mode (wait to reach state 2)
"
    ::= {noRBL 6}

RBLWL  OBJECT-TYPE
    SYNTAX      OCTET STRING
    MAX-ACCESS  read-write
    STATUS      current
    DESCRIPTION
"
Enable DNSBL for whitelisted users also
"
    REFERENCE "Whitelisted DNSBL Validation"
    DEFVAL { "0" }
    ::= {DNSBL 378}

syncStatRBLWL  OBJECT-TYPE
    SYNTAX      OCTET STRING
    MAX-ACCESS  read-only
    STATUS      current
    DESCRIPTION
"
synchronization status for RBLWL
-1 - RBLWL could not be synchronized
 0 - synchronization not configured
 1 - out of sync - running master mode
 2 - in sync - running  mastermode
 3 - in sync - running slave mode
 4 - in sync - running master mode (wait to reach state 2)
"
    ::= {RBLWL 5}

syncStatStrRBLWL  OBJECT-TYPE
    SYNTAX      OCTET STRING
    MAX-ACCESS  read-only
    STATUS      current
    DESCRIPTION
"
synchronization status line from file assp_sync.cfg for RBLWL
 0 - synchronization not configured
 1 - out of sync - running master mode
 2 - in sync - running  mastermode
 3 - in sync - running slave mode
 4 - in sync - running master mode (wait to reach state 2)
"
    ::= {RBLWL 6}

AddRBLHeader  OBJECT-TYPE
    SYNTAX      OCTET STRING
    MAX-ACCESS  read-write
    STATUS      current
    DESCRIPTION
"
Add X-Assp-DNSBL header to messages with positive reply from DNSBL.
"
    REFERENCE "Add X-Assp-DNSBL Header"
    DEFVAL { "1" }
    ::= {DNSBL 379}

syncStatAddRBLHeader  OBJECT-TYPE
    SYNTAX      OCTET STRING
    MAX-ACCESS  read-only
    STATUS      current
    DESCRIPTION
"
synchronization status for AddRBLHeader
-1 - AddRBLHeader could not be synchronized
 0 - synchronization not configured
 1 - out of sync - running master mode
 2 - in sync - running  mastermode
 3 - in sync - running slave mode
 4 - in sync - running master mode (wait to reach state 2)
"
    ::= {AddRBLHeader 5}

syncStatStrAddRBLHeader  OBJECT-TYPE
    SYNTAX      OCTET STRING
    MAX-ACCESS  read-only
    STATUS      current
    DESCRIPTION
"
synchronization status line from file assp_sync.cfg for AddRBLHeader
 0 - synchronization not configured
 1 - out of sync - running master mode
 2 - in sync - running  mastermode
 3 - in sync - running slave mode
 4 - in sync - running master mode (wait to reach state 2)
"
    ::= {AddRBLHeader 6}

RBLError  OBJECT-TYPE
    SYNTAX      OCTET STRING
    MAX-ACCESS  read-write
    STATUS      current
    DESCRIPTION
"
SMTP reply for DNSBL failed messages. Default: '554 5.7.1 DNS Blacklisted by RBLLISTED'
  The literal RBLLISTED (case sensitive) is replaced by the actual serviceproviders(s).
"
    REFERENCE "DNSBL Failed Reply"
    DEFVAL { "554 5.7.1 DNS Blacklisted by RBLLISTED" }
    ::= {DNSBL 380}

syncStatRBLError  OBJECT-TYPE
    SYNTAX      OCTET STRING
    MAX-ACCESS  read-only
    STATUS      current
    DESCRIPTION
"
synchronization status for RBLError
-1 - RBLError could not be synchronized
 0 - synchronization not configured
 1 - out of sync - running master mode
 2 - in sync - running  mastermode
 3 - in sync - running slave mode
 4 - in sync - running master mode (wait to reach state 2)
"
    ::= {RBLError 5}

syncStatStrRBLError  OBJECT-TYPE
    SYNTAX      OCTET STRING
    MAX-ACCESS  read-only
    STATUS      current
    DESCRIPTION
"
synchronization status line from file assp_sync.cfg for RBLError
 0 - synchronization not configured
 1 - out of sync - running master mode
 2 - in sync - running  mastermode
 3 - in sync - running slave mode
 4 - in sync - running master mode (wait to reach state 2)
"
    ::= {RBLError 6}

RBLServiceProvider  OBJECT-TYPE
    SYNTAX      OCTET STRING
    MAX-ACCESS  read-write
    STATUS      current
    DESCRIPTION
"
Names of DNSBLs to use separated by '|'. You may set for every provider a weight like zen.spamhaus.org=>50|bl.spamcop.net=>25.
 Defaults are:
 zen.spamhaus.org=>1|bl.spamcop.net=>1|psbl.surriel.com=>2|ix.dnsbl.manitu.net=>2|
 l2.apews.org=>3|combined.njabl.org=>1|safe.dnsbl.sorbs.net=>1|dnsbl-1.uceprotect.net=>2|
 dnsbl-2.uceprotect.net=>2|dnsbl-3.uceprotect.net=>2|blackholes.five-ten-sg.com=>3'.
 DNSBL providers can get a 'weight' like bl.spamcop.net=>1.
 The value of the weight can be set directly like=>45 or as a divisor of RBLmaxweight. Low numbers &lt; 6 are divisors . So if RBLmaxweight = 50 (default) bl.spamcop.net=>50  would be the same as bl.spamcop.net=>1, bl.spamcop.net=>2 would be the same as bl.spamcop.net=>25.
 If the sum of weights surpasses RBLmaxweight, the DNSBL check fails.  If not, the DNSBL check is scored as 'neutral' even with RBLmaxhits reached. Setting Showmaxreplies will allow ALL replies to contribute to the total weight regardless of RBLmaxhits.
 Some RBL Service Providers, like blackholes.five-ten-sg.com, provides different return codes in a single DNS-zone: like 127.a.b.c - where a,b,c are used to identify a weight or type (or what ever) of the returned entry. If you want to care about special return codes, or if you want to use different weights for different return codes, you should use the following enhanced entry syntax:
 RBL-Service-Provider=>result-to-watch=>weight (like:)
 blackholes.five-ten-sg.com=>127.0.0.2=>3
 blackholes.five-ten-sg.com=>127.0.0.5=>4
 blackholes.five-ten-sg.com=>127.0.?.*=>5
 You can see, the wildcards * (multiple character) and ? (single character) are possible to use in the second parameter. Never mix the three possible syntax types for the same RBL Service Provider. An search for a match inside such a definition is done in reverse ASCII order, so the wildcards are used as last.
 Some RBL Service Providers, provides different return codes using a bitmask in any part of the reply. To define weights for bitmasks, place a single 'M' in front of the mask number, like
 sp.com=>127.0.0.M2=>25
 sp.com=>127.0.0.M4=>41
 sp.com=>127.0.M1.5=>56
 sp.com=>127.0.M64.*=>11
 sp.com=>127.0.0.2=>22
 sp.com=>127.0.*.*=>1
 Valid bitmasks are 1,2,4,8,16,32,64 and 128. The resulting weight will be the weight sum of all matching bitmasks (if no full qualified definition is found). For example: a return code of 127.0.0.6 for sp.com will result in a weight of 66 (25+41), a reply of 127.0.0.2 will result in 22
 Because each single bitmask indicates a set of 128 numbers you should prevent the usage of something like 127.0.M16.M1 - this will lead in to a set of (128*128) 16384 addresses, which is really too much!
 For the same service provider, first define all bitmask definitions, after that all full qualified definitions and than all definitions with wildcards, like in the example above! If your definition order is wrong, the resulting weights will be unexpected!
  
"
    REFERENCE "RBL Service Providers*"
    DEFVAL { "file:files/dnsbls.txt" }
    ::= {DNSBL 381}

syncStatRBLServiceProvider  OBJECT-TYPE
    SYNTAX      OCTET STRING
    MAX-ACCESS  read-only
    STATUS      current
    DESCRIPTION
"
synchronization status for RBLServiceProvider
-1 - RBLServiceProvider could not be synchronized
 0 - synchronization not configured
 1 - out of sync - running master mode
 2 - in sync - running  mastermode
 3 - in sync - running slave mode
 4 - in sync - running master mode (wait to reach state 2)
"
    ::= {RBLServiceProvider 5}

syncStatStrRBLServiceProvider  OBJECT-TYPE
    SYNTAX      OCTET STRING
    MAX-ACCESS  read-only
    STATUS      current
    DESCRIPTION
"
synchronization status line from file assp_sync.cfg for RBLServiceProvider
 0 - synchronization not configured
 1 - out of sync - running master mode
 2 - in sync - running  mastermode
 3 - in sync - running slave mode
 4 - in sync - running master mode (wait to reach state 2)
"
    ::= {RBLServiceProvider 6}

RBLmaxreplies  OBJECT-TYPE
    SYNTAX      OCTET STRING
    MAX-ACCESS  read-write
    STATUS      current
    DESCRIPTION
"
A reply is affirmative or negative reply from a DNSBL.
  The DNSBL module will wait for this number of replies (negative or positive) from the DNSBLs listed under Service Provider for up to the Maximum Time( RBLmaxtime ).
  This number should be equal to or less than the number of DNSBL Service Providers listed to allow for randomly unavailable DNSBLs.
"
    REFERENCE "Maximum Replies"
    DEFVAL { "7" }
    ::= {DNSBL 382}

syncStatRBLmaxreplies  OBJECT-TYPE
    SYNTAX      OCTET STRING
    MAX-ACCESS  read-only
    STATUS      current
    DESCRIPTION
"
synchronization status for RBLmaxreplies
-1 - RBLmaxreplies could not be synchronized
 0 - synchronization not configured
 1 - out of sync - running master mode
 2 - in sync - running  mastermode
 3 - in sync - running slave mode
 4 - in sync - running master mode (wait to reach state 2)
"
    ::= {RBLmaxreplies 5}

syncStatStrRBLmaxreplies  OBJECT-TYPE
    SYNTAX      OCTET STRING
    MAX-ACCESS  read-only
    STATUS      current
    DESCRIPTION
"
synchronization status line from file assp_sync.cfg for RBLmaxreplies
 0 - synchronization not configured
 1 - out of sync - running master mode
 2 - in sync - running  mastermode
 3 - in sync - running slave mode
 4 - in sync - running master mode (wait to reach state 2)
"
    ::= {RBLmaxreplies 6}

RBLmaxhits  OBJECT-TYPE
    SYNTAX      OCTET STRING
    MAX-ACCESS  read-write
    STATUS      current
    DESCRIPTION
"
A hit is an affirmative response from a DNSBL.
  The DNSBL module will check all of the DNSBLs listed under Service Provider. If the number of hits is greater or equal Maximum Hits, the email is flagged Failed. If the number of hits is greater 0 and less Maximum Hits, the email is flagged Neutral
"
    REFERENCE "Maximum Hits"
    DEFVAL { "2" }
    ::= {DNSBL 383}

syncStatRBLmaxhits  OBJECT-TYPE
    SYNTAX      OCTET STRING
    MAX-ACCESS  read-only
    STATUS      current
    DESCRIPTION
"
synchronization status for RBLmaxhits
-1 - RBLmaxhits could not be synchronized
 0 - synchronization not configured
 1 - out of sync - running master mode
 2 - in sync - running  mastermode
 3 - in sync - running slave mode
 4 - in sync - running master mode (wait to reach state 2)
"
    ::= {RBLmaxhits 5}

syncStatStrRBLmaxhits  OBJECT-TYPE
    SYNTAX      OCTET STRING
    MAX-ACCESS  read-only
    STATUS      current
    DESCRIPTION
"
synchronization status line from file assp_sync.cfg for RBLmaxhits
 0 - synchronization not configured
 1 - out of sync - running master mode
 2 - in sync - running  mastermode
 3 - in sync - running slave mode
 4 - in sync - running master mode (wait to reach state 2)
"
    ::= {RBLmaxhits 6}

RBLmaxweight  OBJECT-TYPE
    SYNTAX      OCTET STRING
    MAX-ACCESS  read-write
    STATUS      current
    DESCRIPTION
"
A weight is a number representing the trust we put into a DNSBL.
  The DNSBL module will check all of the DNSBLs listed under Service Provider. If the total of weights is greater or equal Maximum Weight, the email is flagged Failed. If the total of weights is greater 0 and less Maximum Weight, the email is flagged Neutral
"
    REFERENCE "RBL Maximum Weight"
    DEFVAL { "50" }
    ::= {DNSBL 384}

syncStatRBLmaxweight  OBJECT-TYPE
    SYNTAX      OCTET STRING
    MAX-ACCESS  read-only
    STATUS      current
    DESCRIPTION
"
synchronization status for RBLmaxweight
-1 - RBLmaxweight could not be synchronized
 0 - synchronization not configured
 1 - out of sync - running master mode
 2 - in sync - running  mastermode
 3 - in sync - running slave mode
 4 - in sync - running master mode (wait to reach state 2)
"
    ::= {RBLmaxweight 5}

syncStatStrRBLmaxweight  OBJECT-TYPE
    SYNTAX      OCTET STRING
    MAX-ACCESS  read-only
    STATUS      current
    DESCRIPTION
"
synchronization status line from file assp_sync.cfg for RBLmaxweight
 0 - synchronization not configured
 1 - out of sync - running master mode
 2 - in sync - running  mastermode
 3 - in sync - running slave mode
 4 - in sync - running master mode (wait to reach state 2)
"
    ::= {RBLmaxweight 6}

RBLmaxtime  OBJECT-TYPE
    SYNTAX      OCTET STRING
    MAX-ACCESS  read-write
    STATUS      current
    DESCRIPTION
"
This sets the maximum time in seconds to spend on each message performing DNSBL checks. Default is 15.
"
    REFERENCE "Maximum Time"
    DEFVAL { "15" }
    ::= {DNSBL 385}

syncStatRBLmaxtime  OBJECT-TYPE
    SYNTAX      OCTET STRING
    MAX-ACCESS  read-only
    STATUS      current
    DESCRIPTION
"
synchronization status for RBLmaxtime
-1 - RBLmaxtime could not be synchronized
 0 - synchronization not configured
 1 - out of sync - running master mode
 2 - in sync - running  mastermode
 3 - in sync - running slave mode
 4 - in sync - running master mode (wait to reach state 2)
"
    ::= {RBLmaxtime 5}

syncStatStrRBLmaxtime  OBJECT-TYPE
    SYNTAX      OCTET STRING
    MAX-ACCESS  read-only
    STATUS      current
    DESCRIPTION
"
synchronization status line from file assp_sync.cfg for RBLmaxtime
 0 - synchronization not configured
 1 - out of sync - running master mode
 2 - in sync - running  mastermode
 3 - in sync - running slave mode
 4 - in sync - running master mode (wait to reach state 2)
"
    ::= {RBLmaxtime 6}

RBLsocktime  OBJECT-TYPE
    SYNTAX      OCTET STRING
    MAX-ACCESS  read-write
    STATUS      current
    DESCRIPTION
"
This sets the DNSBL socket read timeout in seconds.
"
    REFERENCE "Socket Timeout"
    DEFVAL { "1" }
    ::= {DNSBL 386}

syncStatRBLsocktime  OBJECT-TYPE
    SYNTAX      OCTET STRING
    MAX-ACCESS  read-only
    STATUS      current
    DESCRIPTION
"
synchronization status for RBLsocktime
-1 - RBLsocktime could not be synchronized
 0 - synchronization not configured
 1 - out of sync - running master mode
 2 - in sync - running  mastermode
 3 - in sync - running slave mode
 4 - in sync - running master mode (wait to reach state 2)
"
    ::= {RBLsocktime 5}

syncStatStrRBLsocktime  OBJECT-TYPE
    SYNTAX      OCTET STRING
    MAX-ACCESS  read-only
    STATUS      current
    DESCRIPTION
"
synchronization status line from file assp_sync.cfg for RBLsocktime
 0 - synchronization not configured
 1 - out of sync - running master mode
 2 - in sync - running  mastermode
 3 - in sync - running slave mode
 4 - in sync - running master mode (wait to reach state 2)
"
    ::= {RBLsocktime 6}

RBLCacheExp  OBJECT-TYPE
    SYNTAX      OCTET STRING
    MAX-ACCESS  read-write
    STATUS      current
    DESCRIPTION
"
IP's in cache will be removed after this interval in hours. 0 will disable the cache. 
  
  
"
    REFERENCE "DNSBL Expiration Time"
    DEFVAL { "24" }
    ::= {DNSBL 387}

syncStatRBLCacheExp  OBJECT-TYPE
    SYNTAX      OCTET STRING
    MAX-ACCESS  read-only
    STATUS      current
    DESCRIPTION
"
synchronization status for RBLCacheExp
-1 - RBLCacheExp could not be synchronized
 0 - synchronization not configured
 1 - out of sync - running master mode
 2 - in sync - running  mastermode
 3 - in sync - running slave mode
 4 - in sync - running master mode (wait to reach state 2)
"
    ::= {RBLCacheExp 5}

syncStatStrRBLCacheExp  OBJECT-TYPE
    SYNTAX      OCTET STRING
    MAX-ACCESS  read-only
    STATUS      current
    DESCRIPTION
"
synchronization status line from file assp_sync.cfg for RBLCacheExp
 0 - synchronization not configured
 1 - out of sync - running master mode
 2 - in sync - running  mastermode
 3 - in sync - running slave mode
 4 - in sync - running master mode (wait to reach state 2)
"
    ::= {RBLCacheExp 6}

URIBL  OBJECT IDENTIFIER ::= {asspConfig 19}
ValidateURIBL  OBJECT-TYPE
    SYNTAX      OCTET STRING
    MAX-ACCESS  read-write
    STATUS      current
    DESCRIPTION
"
Enable URI Blocklist. Messages that fail URIBL validation will receive URIBLError SMTP error code. This requires an installed  module and an installed  module in PERL. 
   0 = disabled, 1 = block, 2 = monitor, 3 =  messagescore .
"
    REFERENCE "Enable URI Blocklist Validation "
    DEFVAL { "1" }
    ::= {URIBL 388}

syncStatValidateURIBL  OBJECT-TYPE
    SYNTAX      OCTET STRING
    MAX-ACCESS  read-only
    STATUS      current
    DESCRIPTION
"
synchronization status for ValidateURIBL
-1 - ValidateURIBL could not be synchronized
 0 - synchronization not configured
 1 - out of sync - running master mode
 2 - in sync - running  mastermode
 3 - in sync - running slave mode
 4 - in sync - running master mode (wait to reach state 2)
"
    ::= {ValidateURIBL 5}

syncStatStrValidateURIBL  OBJECT-TYPE
    SYNTAX      OCTET STRING
    MAX-ACCESS  read-only
    STATUS      current
    DESCRIPTION
"
synchronization status line from file assp_sync.cfg for ValidateURIBL
 0 - synchronization not configured
 1 - out of sync - running master mode
 2 - in sync - running  mastermode
 3 - in sync - running slave mode
 4 - in sync - running master mode (wait to reach state 2)
"
    ::= {ValidateURIBL 6}

URIBLWL  OBJECT-TYPE
    SYNTAX      OCTET STRING
    MAX-ACCESS  read-write
    STATUS      current
    DESCRIPTION
"
URIBL check is done ignoring all spamlovers and testmodes!
"
    REFERENCE "Do URI Blocklist Validation for Whitelisted"
    DEFVAL { "" }
    ::= {URIBL 389}

syncStatURIBLWL  OBJECT-TYPE
    SYNTAX      OCTET STRING
    MAX-ACCESS  read-only
    STATUS      current
    DESCRIPTION
"
synchronization status for URIBLWL
-1 - URIBLWL could not be synchronized
 0 - synchronization not configured
 1 - out of sync - running master mode
 2 - in sync - running  mastermode
 3 - in sync - running slave mode
 4 - in sync - running master mode (wait to reach state 2)
"
    ::= {URIBLWL 5}

syncStatStrURIBLWL  OBJECT-TYPE
    SYNTAX      OCTET STRING
    MAX-ACCESS  read-only
    STATUS      current
    DESCRIPTION
"
synchronization status line from file assp_sync.cfg for URIBLWL
 0 - synchronization not configured
 1 - out of sync - running master mode
 2 - in sync - running  mastermode
 3 - in sync - running slave mode
 4 - in sync - running master mode (wait to reach state 2)
"
    ::= {URIBLWL 6}

URIBLNP  OBJECT-TYPE
    SYNTAX      OCTET STRING
    MAX-ACCESS  read-write
    STATUS      current
    DESCRIPTION
"
URIBL check is done ignoring all spamlovers and testmodes!
"
    REFERENCE "Do URI Blocklist Validation for NoProcessing"
    DEFVAL { "" }
    ::= {URIBL 390}

syncStatURIBLNP  OBJECT-TYPE
    SYNTAX      OCTET STRING
    MAX-ACCESS  read-only
    STATUS      current
    DESCRIPTION
"
synchronization status for URIBLNP
-1 - URIBLNP could not be synchronized
 0 - synchronization not configured
 1 - out of sync - running master mode
 2 - in sync - running  mastermode
 3 - in sync - running slave mode
 4 - in sync - running master mode (wait to reach state 2)
"
    ::= {URIBLNP 5}

syncStatStrURIBLNP  OBJECT-TYPE
    SYNTAX      OCTET STRING
    MAX-ACCESS  read-only
    STATUS      current
    DESCRIPTION
"
synchronization status line from file assp_sync.cfg for URIBLNP
 0 - synchronization not configured
 1 - out of sync - running master mode
 2 - in sync - running  mastermode
 3 - in sync - running slave mode
 4 - in sync - running master mode (wait to reach state 2)
"
    ::= {URIBLNP 6}

URIBLLocal  OBJECT-TYPE
    SYNTAX      OCTET STRING
    MAX-ACCESS  read-write
    STATUS      current
    DESCRIPTION
"

"
    REFERENCE "Do URI Blocklist Validation for Local Mails"
    DEFVAL { "" }
    ::= {URIBL 391}

syncStatURIBLLocal  OBJECT-TYPE
    SYNTAX      OCTET STRING
    MAX-ACCESS  read-only
    STATUS      current
    DESCRIPTION
"
synchronization status for URIBLLocal
-1 - URIBLLocal could not be synchronized
 0 - synchronization not configured
 1 - out of sync - running master mode
 2 - in sync - running  mastermode
 3 - in sync - running slave mode
 4 - in sync - running master mode (wait to reach state 2)
"
    ::= {URIBLLocal 5}

syncStatStrURIBLLocal  OBJECT-TYPE
    SYNTAX      OCTET STRING
    MAX-ACCESS  read-only
    STATUS      current
    DESCRIPTION
"
synchronization status line from file assp_sync.cfg for URIBLLocal
 0 - synchronization not configured
 1 - out of sync - running master mode
 2 - in sync - running  mastermode
 3 - in sync - running slave mode
 4 - in sync - running master mode (wait to reach state 2)
"
    ::= {URIBLLocal 6}

URIBLISP  OBJECT-TYPE
    SYNTAX      OCTET STRING
    MAX-ACCESS  read-write
    STATUS      current
    DESCRIPTION
"

"
    REFERENCE "Do URI Blocklist Validation for ISP/Secondary"
    DEFVAL { "1" }
    ::= {URIBL 392}

syncStatURIBLISP  OBJECT-TYPE
    SYNTAX      OCTET STRING
    MAX-ACCESS  read-only
    STATUS      current
    DESCRIPTION
"
synchronization status for URIBLISP
-1 - URIBLISP could not be synchronized
 0 - synchronization not configured
 1 - out of sync - running master mode
 2 - in sync - running  mastermode
 3 - in sync - running slave mode
 4 - in sync - running master mode (wait to reach state 2)
"
    ::= {URIBLISP 5}

syncStatStrURIBLISP  OBJECT-TYPE
    SYNTAX      OCTET STRING
    MAX-ACCESS  read-only
    STATUS      current
    DESCRIPTION
"
synchronization status line from file assp_sync.cfg for URIBLISP
 0 - synchronization not configured
 1 - out of sync - running master mode
 2 - in sync - running  mastermode
 3 - in sync - running slave mode
 4 - in sync - running master mode (wait to reach state 2)
"
    ::= {URIBLISP 6}

URIBLServiceProvider  OBJECT-TYPE
    SYNTAX      OCTET STRING
    MAX-ACCESS  read-write
    STATUS      current
    DESCRIPTION
"
Domain Names of URIBLs to use separated by '|'. You may set for every provider a weight like multi.surbl.org=>50|black.uribl.com=>25.
 The value of the weight can be set directly like=>45 or as a divisor of URIBLmaxweight . Low numbers &lt; 6 are divisors . So if URIBLmaxweight = 50 (default) multi.surbl.org=>50  would be the same as multi.surbl.org=>1, multi.surbl.org=>2 would be the same as multi.surbl.org=>25.
 If the sum of weights surpasses URIBLmaxweight, the URIBL check fails.  If not, the URIBL check is scored as 'neutral'  even with URIBLmaxhits reached. Setting Showmaxreplies will allow ALL replies to contribute to the total weight regardless of URIBLmaxhits.
 Some URIBL Service Providers, like multi.surbl.org and black.uribl.com , provides different return codes in a single DNS-zone: like 127.a.b.c - where a,b,c are used to identify a weight or type (or what ever) of the returned entry. If you want to care about special return codes, or if you want to use different weights for different return codes, you should use the following enhanced entry syntax:
 URIBL-Service-Provider=>result-to-watch=>weight (like:)
 multi.surbl.org=>127.0.0.2=>2
 multi.surbl.org=>127.0.0.4=>3
 multi.surbl.org=>127.0.0.?=>4
 multi.surbl.org=>127.0.0.*=>5
 You can see, the wildcards * (multiple character) and ? (single character) are possible to use in the second parameter. Never mix the three possible syntax types for the same URIBL Service Provider. An search for a match inside such a definition is done in reverse ASCII order, so the wildcards are used as last.
 Some URIBL Service Providers, provides different return codes using a bitmask in any part of the reply. To define weights for bitmasks, place a single 'M' in front of the mask number, like
 sp.com=>127.0.0.M2=>25
 sp.com=>127.0.0.M4=>41
 sp.com=>127.0.M1.5=>56
 sp.com=>127.0.M64.*=>11
 sp.com=>127.0.0.2=>22
 sp.com=>127.0.*.*=>1
 Valid bitmasks are 1,2,4,8,16,32,64 and 128. The resulting weight will be the weight sum of all matching bitmasks (if no full qualified definition is found). For example: a return code of 127.0.0.6 for sp.com will result in a weight of 66 (25+41), a reply of 127.0.0.2 will result in 22
 Because each single bitmask indicates a set of 128 numbers you should prevent the usage of something like 127.0.M16.M1 - this will lead in to a set of (128*128) 16384 addresses, which is really too much!
 For the same service provider, first define all bitmask definitions, after that all full qualified definitions and than all definitions with wildcards, like in the example above! If your definition order is wrong, the resulting weights will be unexpected!
 Default is: multi.surbl.org|black.uribl.com
"
    REFERENCE "URIBL Service Providers*"
    DEFVAL { "file:files/uribls.txt" }
    ::= {URIBL 393}

syncStatURIBLServiceProvider  OBJECT-TYPE
    SYNTAX      OCTET STRING
    MAX-ACCESS  read-only
    STATUS      current
    DESCRIPTION
"
synchronization status for URIBLServiceProvider
-1 - URIBLServiceProvider could not be synchronized
 0 - synchronization not configured
 1 - out of sync - running master mode
 2 - in sync - running  mastermode
 3 - in sync - running slave mode
 4 - in sync - running master mode (wait to reach state 2)
"
    ::= {URIBLServiceProvider 5}

syncStatStrURIBLServiceProvider  OBJECT-TYPE
    SYNTAX      OCTET STRING
    MAX-ACCESS  read-only
    STATUS      current
    DESCRIPTION
"
synchronization status line from file assp_sync.cfg for URIBLServiceProvider
 0 - synchronization not configured
 1 - out of sync - running master mode
 2 - in sync - running  mastermode
 3 - in sync - running slave mode
 4 - in sync - running master mode (wait to reach state 2)
"
    ::= {URIBLServiceProvider 6}

URIBLCCTLDS  OBJECT-TYPE
    SYNTAX      OCTET STRING
    MAX-ACCESS  read-write
    STATUS      current
    DESCRIPTION
"
List of  and  used to determine the base domain of the uri. Two level TLDs will be checked on third level, third level TLDs will be checked on fourth level. Any not listed domain will be checked in level two.
"
    REFERENCE "URIBL Country Code TLDs*"
    DEFVAL { "file:files/URIBLCCTLDS.txt" }
    ::= {URIBL 394}

URIBLmaxuris  OBJECT-TYPE
    SYNTAX      OCTET STRING
    MAX-ACCESS  read-write
    STATUS      current
    DESCRIPTION
"
More than this number of URIs in the body will increase spam probability. Enter 0 to disable feature.
"
    REFERENCE "Maximum URIs"
    DEFVAL { "0" }
    ::= {URIBL 395}

syncStatURIBLmaxuris  OBJECT-TYPE
    SYNTAX      OCTET STRING
    MAX-ACCESS  read-only
    STATUS      current
    DESCRIPTION
"
synchronization status for URIBLmaxuris
-1 - URIBLmaxuris could not be synchronized
 0 - synchronization not configured
 1 - out of sync - running master mode
 2 - in sync - running  mastermode
 3 - in sync - running slave mode
 4 - in sync - running master mode (wait to reach state 2)
"
    ::= {URIBLmaxuris 5}

syncStatStrURIBLmaxuris  OBJECT-TYPE
    SYNTAX      OCTET STRING
    MAX-ACCESS  read-only
    STATUS      current
    DESCRIPTION
"
synchronization status line from file assp_sync.cfg for URIBLmaxuris
 0 - synchronization not configured
 1 - out of sync - running master mode
 2 - in sync - running  mastermode
 3 - in sync - running slave mode
 4 - in sync - running master mode (wait to reach state 2)
"
    ::= {URIBLmaxuris 6}

URIBLmaxdomains  OBJECT-TYPE
    SYNTAX      OCTET STRING
    MAX-ACCESS  read-write
    STATUS      current
    DESCRIPTION
"
More than this number of unique domain URIs in the body will increase spam probability. Enter 0 to disable feature.
"
    REFERENCE "Maximum Unique Domain URIs"
    DEFVAL { "0" }
    ::= {URIBL 396}

syncStatURIBLmaxdomains  OBJECT-TYPE
    SYNTAX      OCTET STRING
    MAX-ACCESS  read-only
    STATUS      current
    DESCRIPTION
"
synchronization status for URIBLmaxdomains
-1 - URIBLmaxdomains could not be synchronized
 0 - synchronization not configured
 1 - out of sync - running master mode
 2 - in sync - running  mastermode
 3 - in sync - running slave mode
 4 - in sync - running master mode (wait to reach state 2)
"
    ::= {URIBLmaxdomains 5}

syncStatStrURIBLmaxdomains  OBJECT-TYPE
    SYNTAX      OCTET STRING
    MAX-ACCESS  read-only
    STATUS      current
    DESCRIPTION
"
synchronization status line from file assp_sync.cfg for URIBLmaxdomains
 0 - synchronization not configured
 1 - out of sync - running master mode
 2 - in sync - running  mastermode
 3 - in sync - running slave mode
 4 - in sync - running master mode (wait to reach state 2)
"
    ::= {URIBLmaxdomains 6}

URIBLNoObfuscated  OBJECT-TYPE
    SYNTAX      OCTET STRING
    MAX-ACCESS  read-write
    STATUS      current
    DESCRIPTION
"
When enabled, messages with obfuscated URIs of types [integer/octal/hex IP, other things!] in the body will get increased spam probability and if weights are used, the double weight will be used.
"
    REFERENCE "Disallow Obfuscated URIs "
    DEFVAL { "1" }
    ::= {URIBL 397}

syncStatURIBLNoObfuscated  OBJECT-TYPE
    SYNTAX      OCTET STRING
    MAX-ACCESS  read-only
    STATUS      current
    DESCRIPTION
"
synchronization status for URIBLNoObfuscated
-1 - URIBLNoObfuscated could not be synchronized
 0 - synchronization not configured
 1 - out of sync - running master mode
 2 - in sync - running  mastermode
 3 - in sync - running slave mode
 4 - in sync - running master mode (wait to reach state 2)
"
    ::= {URIBLNoObfuscated 5}

syncStatStrURIBLNoObfuscated  OBJECT-TYPE
    SYNTAX      OCTET STRING
    MAX-ACCESS  read-only
    STATUS      current
    DESCRIPTION
"
synchronization status line from file assp_sync.cfg for URIBLNoObfuscated
 0 - synchronization not configured
 1 - out of sync - running master mode
 2 - in sync - running  mastermode
 3 - in sync - running slave mode
 4 - in sync - running master mode (wait to reach state 2)
"
    ::= {URIBLNoObfuscated 6}

URIBLmaxreplies  OBJECT-TYPE
    SYNTAX      OCTET STRING
    MAX-ACCESS  read-write
    STATUS      current
    DESCRIPTION
"
A reply is affirmative or negative reply from a URIBL.
   The URIBL module will wait for this number of replies (negative or positive) from the URIBLs listed under Service Provider
   for up to the Maximum Time below. This number should be equal to or less than the number of URIBL Service Providers
   listed to allow for randomly unavailable URIBLs.
"
    REFERENCE "Maximum Replies"
    DEFVAL { "2" }
    ::= {URIBL 398}

syncStatURIBLmaxreplies  OBJECT-TYPE
    SYNTAX      OCTET STRING
    MAX-ACCESS  read-only
    STATUS      current
    DESCRIPTION
"
synchronization status for URIBLmaxreplies
-1 - URIBLmaxreplies could not be synchronized
 0 - synchronization not configured
 1 - out of sync - running master mode
 2 - in sync - running  mastermode
 3 - in sync - running slave mode
 4 - in sync - running master mode (wait to reach state 2)
"
    ::= {URIBLmaxreplies 5}

syncStatStrURIBLmaxreplies  OBJECT-TYPE
    SYNTAX      OCTET STRING
    MAX-ACCESS  read-only
    STATUS      current
    DESCRIPTION
"
synchronization status line from file assp_sync.cfg for URIBLmaxreplies
 0 - synchronization not configured
 1 - out of sync - running master mode
 2 - in sync - running  mastermode
 3 - in sync - running slave mode
 4 - in sync - running master mode (wait to reach state 2)
"
    ::= {URIBLmaxreplies 6}

URIBLmaxhits  OBJECT-TYPE
    SYNTAX      OCTET STRING
    MAX-ACCESS  read-write
    STATUS      current
    DESCRIPTION
"
A hit is an affirmative response from a URIBL.
   The URIBL module will check all of the URIBLs listed under Service Provider,
   and flag the email with a URIBL failure flag if more than this number of URIBLs return a positive blacklisted response.
   This number should be less than or equal to Maximum Replies above and greater than 0.
   If the number of hits is greater or equal Maximum Hits, the email is flagged failed in every case!
   If the number of hits is greater 0 and less Maximum Hits, the email is flagged neutral.
   This behavior could be changed to your needs by using weighted values for the URIBLServiceProvider .
"
    REFERENCE "Maximum Hits"
    DEFVAL { "1" }
    ::= {URIBL 399}

syncStatURIBLmaxhits  OBJECT-TYPE
    SYNTAX      OCTET STRING
    MAX-ACCESS  read-only
    STATUS      current
    DESCRIPTION
"
synchronization status for URIBLmaxhits
-1 - URIBLmaxhits could not be synchronized
 0 - synchronization not configured
 1 - out of sync - running master mode
 2 - in sync - running  mastermode
 3 - in sync - running slave mode
 4 - in sync - running master mode (wait to reach state 2)
"
    ::= {URIBLmaxhits 5}

syncStatStrURIBLmaxhits  OBJECT-TYPE
    SYNTAX      OCTET STRING
    MAX-ACCESS  read-only
    STATUS      current
    DESCRIPTION
"
synchronization status line from file assp_sync.cfg for URIBLmaxhits
 0 - synchronization not configured
 1 - out of sync - running master mode
 2 - in sync - running  mastermode
 3 - in sync - running slave mode
 4 - in sync - running master mode (wait to reach state 2)
"
    ::= {URIBLmaxhits 6}

URIBLmaxtime  OBJECT-TYPE
    SYNTAX      OCTET STRING
    MAX-ACCESS  read-write
    STATUS      current
    DESCRIPTION
"
This sets the maximum time in seconds to spend on each message performing URIBL checks.
"
    REFERENCE "Maximum Time"
    DEFVAL { "10" }
    ::= {URIBL 400}

syncStatURIBLmaxtime  OBJECT-TYPE
    SYNTAX      OCTET STRING
    MAX-ACCESS  read-only
    STATUS      current
    DESCRIPTION
"
synchronization status for URIBLmaxtime
-1 - URIBLmaxtime could not be synchronized
 0 - synchronization not configured
 1 - out of sync - running master mode
 2 - in sync - running  mastermode
 3 - in sync - running slave mode
 4 - in sync - running master mode (wait to reach state 2)
"
    ::= {URIBLmaxtime 5}

syncStatStrURIBLmaxtime  OBJECT-TYPE
    SYNTAX      OCTET STRING
    MAX-ACCESS  read-only
    STATUS      current
    DESCRIPTION
"
synchronization status line from file assp_sync.cfg for URIBLmaxtime
 0 - synchronization not configured
 1 - out of sync - running master mode
 2 - in sync - running  mastermode
 3 - in sync - running slave mode
 4 - in sync - running master mode (wait to reach state 2)
"
    ::= {URIBLmaxtime 6}

URIBLsocktime  OBJECT-TYPE
    SYNTAX      OCTET STRING
    MAX-ACCESS  read-write
    STATUS      current
    DESCRIPTION
"
This sets the URIBL socket read timeout in seconds.
"
    REFERENCE "Socket Timeout"
    DEFVAL { "1" }
    ::= {URIBL 401}

syncStatURIBLsocktime  OBJECT-TYPE
    SYNTAX      OCTET STRING
    MAX-ACCESS  read-only
    STATUS      current
    DESCRIPTION
"
synchronization status for URIBLsocktime
-1 - URIBLsocktime could not be synchronized
 0 - synchronization not configured
 1 - out of sync - running master mode
 2 - in sync - running  mastermode
 3 - in sync - running slave mode
 4 - in sync - running master mode (wait to reach state 2)
"
    ::= {URIBLsocktime 5}

syncStatStrURIBLsocktime  OBJECT-TYPE
    SYNTAX      OCTET STRING
    MAX-ACCESS  read-only
    STATUS      current
    DESCRIPTION
"
synchronization status line from file assp_sync.cfg for URIBLsocktime
 0 - synchronization not configured
 1 - out of sync - running master mode
 2 - in sync - running  mastermode
 3 - in sync - running slave mode
 4 - in sync - running master mode (wait to reach state 2)
"
    ::= {URIBLsocktime 6}

URIBLwhitelist  OBJECT-TYPE
    SYNTAX      OCTET STRING
    MAX-ACCESS  read-write
    STATUS      current
    DESCRIPTION
"
This prevents specific domains from being checked by URIBL module. For example: doubleclick.net or file:files/URIBLwhitelist.txt. Domains already listed in noProcessingDomains and whiteListedDomains will be honored.
"
    REFERENCE "Whitelisted URIBL Domains*"
    DEFVAL { "doubleclick.net" }
    ::= {URIBL 402}

syncStatURIBLwhitelist  OBJECT-TYPE
    SYNTAX      OCTET STRING
    MAX-ACCESS  read-only
    STATUS      current
    DESCRIPTION
"
synchronization status for URIBLwhitelist
-1 - URIBLwhitelist could not be synchronized
 0 - synchronization not configured
 1 - out of sync - running master mode
 2 - in sync - running  mastermode
 3 - in sync - running slave mode
 4 - in sync - running master mode (wait to reach state 2)
"
    ::= {URIBLwhitelist 5}

syncStatStrURIBLwhitelist  OBJECT-TYPE
    SYNTAX      OCTET STRING
    MAX-ACCESS  read-only
    STATUS      current
    DESCRIPTION
"
synchronization status line from file assp_sync.cfg for URIBLwhitelist
 0 - synchronization not configured
 1 - out of sync - running master mode
 2 - in sync - running  mastermode
 3 - in sync - running slave mode
 4 - in sync - running master mode (wait to reach state 2)
"
    ::= {URIBLwhitelist 6}

noURIBL  OBJECT-TYPE
    SYNTAX      OCTET STRING
    MAX-ACCESS  read-write
    STATUS      current
    DESCRIPTION
"
Don't validate URIBL when messages come from these addresses. Accepts specific addresses (user@domain.com), user parts (user) or entire domains (@domain.com). For example: fribo@thisdomain.com|jhanna|@sillyguys.org
"
    REFERENCE "Don't Check Messages from these Addresses*"
    DEFVAL { "" }
    ::= {URIBL 403}

syncStatnoURIBL  OBJECT-TYPE
    SYNTAX      OCTET STRING
    MAX-ACCESS  read-only
    STATUS      current
    DESCRIPTION
"
synchronization status for noURIBL
-1 - noURIBL could not be synchronized
 0 - synchronization not configured
 1 - out of sync - running master mode
 2 - in sync - running  mastermode
 3 - in sync - running slave mode
 4 - in sync - running master mode (wait to reach state 2)
"
    ::= {noURIBL 5}

syncStatStrnoURIBL  OBJECT-TYPE
    SYNTAX      OCTET STRING
    MAX-ACCESS  read-only
    STATUS      current
    DESCRIPTION
"
synchronization status line from file assp_sync.cfg for noURIBL
 0 - synchronization not configured
 1 - out of sync - running master mode
 2 - in sync - running  mastermode
 3 - in sync - running slave mode
 4 - in sync - running master mode (wait to reach state 2)
"
    ::= {noURIBL 6}

AddURIBLHeader  OBJECT-TYPE
    SYNTAX      OCTET STRING
    MAX-ACCESS  read-write
    STATUS      current
    DESCRIPTION
"
Add X-Assp-Received-URIBL header to messages with positive reply from URIBL.
"
    REFERENCE "Add X-Assp-Received-URIBL Header"
    DEFVAL { "1" }
    ::= {URIBL 404}

syncStatAddURIBLHeader  OBJECT-TYPE
    SYNTAX      OCTET STRING
    MAX-ACCESS  read-only
    STATUS      current
    DESCRIPTION
"
synchronization status for AddURIBLHeader
-1 - AddURIBLHeader could not be synchronized
 0 - synchronization not configured
 1 - out of sync - running master mode
 2 - in sync - running  mastermode
 3 - in sync - running slave mode
 4 - in sync - running master mode (wait to reach state 2)
"
    ::= {AddURIBLHeader 5}

syncStatStrAddURIBLHeader  OBJECT-TYPE
    SYNTAX      OCTET STRING
    MAX-ACCESS  read-only
    STATUS      current
    DESCRIPTION
"
synchronization status line from file assp_sync.cfg for AddURIBLHeader
 0 - synchronization not configured
 1 - out of sync - running master mode
 2 - in sync - running  mastermode
 3 - in sync - running slave mode
 4 - in sync - running master mode (wait to reach state 2)
"
    ::= {AddURIBLHeader 6}

URIBLCacheInterval  OBJECT-TYPE
    SYNTAX      OCTET STRING
    MAX-ACCESS  read-write
    STATUS      current
    DESCRIPTION
"
Domains in cache will be removed after this interval in days. Empty or 0 will disable the cache. 
"
    REFERENCE "URIBL Cache Refresh Interval for Hits"
    DEFVAL { "1" }
    ::= {URIBL 405}

syncStatURIBLCacheInterval  OBJECT-TYPE
    SYNTAX      OCTET STRING
    MAX-ACCESS  read-only
    STATUS      current
    DESCRIPTION
"
synchronization status for URIBLCacheInterval
-1 - URIBLCacheInterval could not be synchronized
 0 - synchronization not configured
 1 - out of sync - running master mode
 2 - in sync - running  mastermode
 3 - in sync - running slave mode
 4 - in sync - running master mode (wait to reach state 2)
"
    ::= {URIBLCacheInterval 5}

syncStatStrURIBLCacheInterval  OBJECT-TYPE
    SYNTAX      OCTET STRING
    MAX-ACCESS  read-only
    STATUS      current
    DESCRIPTION
"
synchronization status line from file assp_sync.cfg for URIBLCacheInterval
 0 - synchronization not configured
 1 - out of sync - running master mode
 2 - in sync - running  mastermode
 3 - in sync - running slave mode
 4 - in sync - running master mode (wait to reach state 2)
"
    ::= {URIBLCacheInterval 6}

URIBLCacheIntervalMiss  OBJECT-TYPE
    SYNTAX      OCTET STRING
    MAX-ACCESS  read-write
    STATUS      current
    DESCRIPTION
"
Domains in cache with status=2 (miss) will be removed after this interval in days. Empty or 0 will prevent caching of non-hits. 
"
    REFERENCE "URIBL Cache Refresh Interval for Misses"
    DEFVAL { "0.5" }
    ::= {URIBL 406}

syncStatURIBLCacheIntervalMiss  OBJECT-TYPE
    SYNTAX      OCTET STRING
    MAX-ACCESS  read-only
    STATUS      current
    DESCRIPTION
"
synchronization status for URIBLCacheIntervalMiss
-1 - URIBLCacheIntervalMiss could not be synchronized
 0 - synchronization not configured
 1 - out of sync - running master mode
 2 - in sync - running  mastermode
 3 - in sync - running slave mode
 4 - in sync - running master mode (wait to reach state 2)
"
    ::= {URIBLCacheIntervalMiss 5}

syncStatStrURIBLCacheIntervalMiss  OBJECT-TYPE
    SYNTAX      OCTET STRING
    MAX-ACCESS  read-only
    STATUS      current
    DESCRIPTION
"
synchronization status line from file assp_sync.cfg for URIBLCacheIntervalMiss
 0 - synchronization not configured
 1 - out of sync - running master mode
 2 - in sync - running  mastermode
 3 - in sync - running slave mode
 4 - in sync - running master mode (wait to reach state 2)
"
    ::= {URIBLCacheIntervalMiss 6}

URIBLError  OBJECT-TYPE
    SYNTAX      OCTET STRING
    MAX-ACCESS  read-write
    STATUS      current
    DESCRIPTION
"
SMTP reply code to refuse failed URIBL message. The literal URIBLNAME (case sensitive) is replaced by the names of URIBLs with negative response. If this field is empty, client connection is simply dropped.
  
"
    REFERENCE "Reply Code to Refuse Failed URIBL Message"
    DEFVAL { "554 5.7.1 Blacklisted by URIBLNAME Contact the postmaster of this domain for resolution. This attempt has been logged." }
    ::= {URIBL 407}

syncStatURIBLError  OBJECT-TYPE
    SYNTAX      OCTET STRING
    MAX-ACCESS  read-only
    STATUS      current
    DESCRIPTION
"
synchronization status for URIBLError
-1 - URIBLError could not be synchronized
 0 - synchronization not configured
 1 - out of sync - running master mode
 2 - in sync - running  mastermode
 3 - in sync - running slave mode
 4 - in sync - running master mode (wait to reach state 2)
"
    ::= {URIBLError 5}

syncStatStrURIBLError  OBJECT-TYPE
    SYNTAX      OCTET STRING
    MAX-ACCESS  read-only
    STATUS      current
    DESCRIPTION
"
synchronization status line from file assp_sync.cfg for URIBLError
 0 - synchronization not configured
 1 - out of sync - running master mode
 2 - in sync - running  mastermode
 3 - in sync - running slave mode
 4 - in sync - running master mode (wait to reach state 2)
"
    ::= {URIBLError 6}

URIBLcheckDOTinURI  OBJECT-TYPE
    SYNTAX      OCTET STRING
    MAX-ACCESS  read-write
    STATUS      current
    DESCRIPTION
"
When enabled, assp will also check for the used word 'DOT' instead of a '.' in URI's like 'exampledotcom or example!d o-t_com' .
   Enable this feature only, if you don't expect any problems in your national language (using 'dot' + a toplevel domain in any words).
"
    REFERENCE "Check for 'DOT' in URI"
    DEFVAL { "" }
    ::= {URIBL 882}

syncStatURIBLcheckDOTinURI  OBJECT-TYPE
    SYNTAX      OCTET STRING
    MAX-ACCESS  read-only
    STATUS      current
    DESCRIPTION
"
synchronization status for URIBLcheckDOTinURI
-1 - URIBLcheckDOTinURI could not be synchronized
 0 - synchronization not configured
 1 - out of sync - running master mode
 2 - in sync - running  mastermode
 3 - in sync - running slave mode
 4 - in sync - running master mode (wait to reach state 2)
"
    ::= {URIBLcheckDOTinURI 5}

syncStatStrURIBLcheckDOTinURI  OBJECT-TYPE
    SYNTAX      OCTET STRING
    MAX-ACCESS  read-only
    STATUS      current
    DESCRIPTION
"
synchronization status line from file assp_sync.cfg for URIBLcheckDOTinURI
 0 - synchronization not configured
 1 - out of sync - running master mode
 2 - in sync - running  mastermode
 3 - in sync - running slave mode
 4 - in sync - running master mode (wait to reach state 2)
"
    ::= {URIBLcheckDOTinURI 6}

URIBLmaxweight  OBJECT-TYPE
    SYNTAX      OCTET STRING
    MAX-ACCESS  read-write
    STATUS      current
    DESCRIPTION
"
A weight is a number representing the trust we put into a URIBL.
  The URIBL module will check all of the URIBLs listed under URIBLServiceProvider for every URI found in an email. If the total of weights for an URI is greater or equal this Maximum Weight, the email is flagged Failed. If the total of weights is greater 0 and less Maximum Weight, the email is flagged Neutral . If not defined or set to zero only the hit count will used to detect a fail or neutral state.
"
    REFERENCE "URIBL Maximum Weight"
    DEFVAL { "50" }
    ::= {URIBL 915}

syncStatURIBLmaxweight  OBJECT-TYPE
    SYNTAX      OCTET STRING
    MAX-ACCESS  read-only
    STATUS      current
    DESCRIPTION
"
synchronization status for URIBLmaxweight
-1 - URIBLmaxweight could not be synchronized
 0 - synchronization not configured
 1 - out of sync - running master mode
 2 - in sync - running  mastermode
 3 - in sync - running slave mode
 4 - in sync - running master mode (wait to reach state 2)
"
    ::= {URIBLmaxweight 5}

syncStatStrURIBLmaxweight  OBJECT-TYPE
    SYNTAX      OCTET STRING
    MAX-ACCESS  read-only
    STATUS      current
    DESCRIPTION
"
synchronization status line from file assp_sync.cfg for URIBLmaxweight
 0 - synchronization not configured
 1 - out of sync - running master mode
 2 - in sync - running  mastermode
 3 - in sync - running slave mode
 4 - in sync - running master mode (wait to reach state 2)
"
    ::= {URIBLmaxweight 6}

URIBLIPRe  OBJECT-TYPE
    SYNTAX      OCTET STRING
    MAX-ACCESS  read-write
    STATUS      current
    DESCRIPTION
"
Every IP in an URI and every IP resolved for a hostname in an URI is checked against this list of IP's or networks. For example:145.145.145.145|145.146.|1.2.0.0/16
  This high security feature will follow the rules in URIBLWL, URIBLNP, URIBLLocal and URIBLISP - but if a match is found, it will block the email ( ignores scoring, monitoring, testmodes and spamlover ).
"
    REFERENCE "Bad URI IP's*"
    DEFVAL { "" }
    ::= {URIBL 960}

syncStatURIBLIPRe  OBJECT-TYPE
    SYNTAX      OCTET STRING
    MAX-ACCESS  read-only
    STATUS      current
    DESCRIPTION
"
synchronization status for URIBLIPRe
-1 - URIBLIPRe could not be synchronized
 0 - synchronization not configured
 1 - out of sync - running master mode
 2 - in sync - running  mastermode
 3 - in sync - running slave mode
 4 - in sync - running master mode (wait to reach state 2)
"
    ::= {URIBLIPRe 5}

syncStatStrURIBLIPRe  OBJECT-TYPE
    SYNTAX      OCTET STRING
    MAX-ACCESS  read-only
    STATUS      current
    DESCRIPTION
"
synchronization status line from file assp_sync.cfg for URIBLIPRe
 0 - synchronization not configured
 1 - out of sync - running master mode
 2 - in sync - running  mastermode
 3 - in sync - running slave mode
 4 - in sync - running master mode (wait to reach state 2)
"
    ::= {URIBLIPRe 6}

AddURIS2MyHeader  OBJECT-TYPE
    SYNTAX      OCTET STRING
    MAX-ACCESS  read-write
    STATUS      current
    DESCRIPTION
"
URI's detected with URIBLOK are added to our header lines (X-Assp-Detected-URI:).
"
    REFERENCE "Add X-Assp-Detected-URI Header"
    DEFVAL { "" }
    ::= {URIBL 975}

syncStatAddURIS2MyHeader  OBJECT-TYPE
    SYNTAX      OCTET STRING
    MAX-ACCESS  read-only
    STATUS      current
    DESCRIPTION
"
synchronization status for AddURIS2MyHeader
-1 - AddURIS2MyHeader could not be synchronized
 0 - synchronization not configured
 1 - out of sync - running master mode
 2 - in sync - running  mastermode
 3 - in sync - running slave mode
 4 - in sync - running master mode (wait to reach state 2)
"
    ::= {AddURIS2MyHeader 5}

syncStatStrAddURIS2MyHeader  OBJECT-TYPE
    SYNTAX      OCTET STRING
    MAX-ACCESS  read-only
    STATUS      current
    DESCRIPTION
"
synchronization status line from file assp_sync.cfg for AddURIS2MyHeader
 0 - synchronization not configured
 1 - out of sync - running master mode
 2 - in sync - running  mastermode
 3 - in sync - running slave mode
 4 - in sync - running master mode (wait to reach state 2)
"
    ::= {AddURIS2MyHeader 6}

AttachmentBlocking  OBJECT IDENTIFIER ::= {asspConfig 20}
DoBlockExes  OBJECT-TYPE
    SYNTAX      OCTET STRING
    MAX-ACCESS  read-write
    STATUS      current
    DESCRIPTION
"
This requires an installed  module in PERL.
"
    REFERENCE "External Attachment Blocking "
    DEFVAL { "0" }
    ::= {AttachmentBlocking 408}

syncStatDoBlockExes  OBJECT-TYPE
    SYNTAX      OCTET STRING
    MAX-ACCESS  read-only
    STATUS      current
    DESCRIPTION
"
synchronization status for DoBlockExes
-1 - DoBlockExes could not be synchronized
 0 - synchronization not configured
 1 - out of sync - running master mode
 2 - in sync - running  mastermode
 3 - in sync - running slave mode
 4 - in sync - running master mode (wait to reach state 2)
"
    ::= {DoBlockExes 5}

syncStatStrDoBlockExes  OBJECT-TYPE
    SYNTAX      OCTET STRING
    MAX-ACCESS  read-only
    STATUS      current
    DESCRIPTION
"
synchronization status line from file assp_sync.cfg for DoBlockExes
 0 - synchronization not configured
 1 - out of sync - running master mode
 2 - in sync - running  mastermode
 3 - in sync - running slave mode
 4 - in sync - running master mode (wait to reach state 2)
"
    ::= {DoBlockExes 6}

BlockExes  OBJECT-TYPE
    SYNTAX      OCTET STRING
    MAX-ACCESS  read-write
    STATUS      current
    DESCRIPTION
"
Set the level of Attachment Blocking to 1-3 for attachments that should be blocked, set level to 4  for attachments that should be allowed. Choose 0 for no attachment blocking.
"
    REFERENCE "External Attachment Blocking Level"
    DEFVAL { "0" }
    ::= {AttachmentBlocking 409}

syncStatBlockExes  OBJECT-TYPE
    SYNTAX      OCTET STRING
    MAX-ACCESS  read-only
    STATUS      current
    DESCRIPTION
"
synchronization status for BlockExes
-1 - BlockExes could not be synchronized
 0 - synchronization not configured
 1 - out of sync - running master mode
 2 - in sync - running  mastermode
 3 - in sync - running slave mode
 4 - in sync - running master mode (wait to reach state 2)
"
    ::= {BlockExes 5}

syncStatStrBlockExes  OBJECT-TYPE
    SYNTAX      OCTET STRING
    MAX-ACCESS  read-only
    STATUS      current
    DESCRIPTION
"
synchronization status line from file assp_sync.cfg for BlockExes
 0 - synchronization not configured
 1 - out of sync - running master mode
 2 - in sync - running  mastermode
 3 - in sync - running slave mode
 4 - in sync - running master mode (wait to reach state 2)
"
    ::= {BlockExes 6}

BlockWLExes  OBJECT-TYPE
    SYNTAX      OCTET STRING
    MAX-ACCESS  read-write
    STATUS      current
    DESCRIPTION
"
Set the level of Attachment Blocking to 0-4 for whitelisted &amp; local senders. Choose 0 for no attachment blocking.
"
    REFERENCE "Whitelisted &amp; Local Attachment Blocking"
    DEFVAL { "0" }
    ::= {AttachmentBlocking 410}

syncStatBlockWLExes  OBJECT-TYPE
    SYNTAX      OCTET STRING
    MAX-ACCESS  read-only
    STATUS      current
    DESCRIPTION
"
synchronization status for BlockWLExes
-1 - BlockWLExes could not be synchronized
 0 - synchronization not configured
 1 - out of sync - running master mode
 2 - in sync - running  mastermode
 3 - in sync - running slave mode
 4 - in sync - running master mode (wait to reach state 2)
"
    ::= {BlockWLExes 5}

syncStatStrBlockWLExes  OBJECT-TYPE
    SYNTAX      OCTET STRING
    MAX-ACCESS  read-only
    STATUS      current
    DESCRIPTION
"
synchronization status line from file assp_sync.cfg for BlockWLExes
 0 - synchronization not configured
 1 - out of sync - running master mode
 2 - in sync - running  mastermode
 3 - in sync - running slave mode
 4 - in sync - running master mode (wait to reach state 2)
"
    ::= {BlockWLExes 6}

BlockNPExes  OBJECT-TYPE
    SYNTAX      OCTET STRING
    MAX-ACCESS  read-write
    STATUS      current
    DESCRIPTION
"
Set the level of Attachment Blocking to 0-4 for no processing senders. Choose 0 for no attachment blocking. 
"
    REFERENCE "NoProcessing Attachment Blocking"
    DEFVAL { "0" }
    ::= {AttachmentBlocking 411}

syncStatBlockNPExes  OBJECT-TYPE
    SYNTAX      OCTET STRING
    MAX-ACCESS  read-only
    STATUS      current
    DESCRIPTION
"
synchronization status for BlockNPExes
-1 - BlockNPExes could not be synchronized
 0 - synchronization not configured
 1 - out of sync - running master mode
 2 - in sync - running  mastermode
 3 - in sync - running slave mode
 4 - in sync - running master mode (wait to reach state 2)
"
    ::= {BlockNPExes 5}

syncStatStrBlockNPExes  OBJECT-TYPE
    SYNTAX      OCTET STRING
    MAX-ACCESS  read-only
    STATUS      current
    DESCRIPTION
"
synchronization status line from file assp_sync.cfg for BlockNPExes
 0 - synchronization not configured
 1 - out of sync - running master mode
 2 - in sync - running  mastermode
 3 - in sync - running slave mode
 4 - in sync - running master mode (wait to reach state 2)
"
    ::= {BlockNPExes 6}

BadAttachL1  OBJECT-TYPE
    SYNTAX      OCTET STRING
    MAX-ACCESS  read-write
    STATUS      current
    DESCRIPTION
"
This regular expression is used to identify Level 1 attachments that should be blocked.
  Separate entries with a pipe |. The dot . is assumed to precede these, so don't include it.
  For example:
  ad[ep]|asx|ba[st]|chm|cmd|com|cpl|crt|dbx|exe|exe\-bin|hlp|ht[ab]|in[fs]|isp|js|jse|lnk|md[abez]|mht|ms[cipt]|nch|pcd|pif|prf|ps1?|reg|sc[frt]|sh[bs]|vb|vb[es]|wms|ws[cfh]
  If you've installed the ASSP_AFC Plugin (at least version 2.10) and 'exe-bin' is defined (on any level), the Plugin will detect executable files based on there binary content. Detected will be all executables, libraries and scripts for DOS and Windows (except .com files), MAC-OS and linux ELF (for all processor architectures).
"
    REFERENCE "Level 1 rejected File Extensions"
    DEFVAL { "exe\-bin|exe|scr|pif|vb[es]?|jse?|ws[cfh]?|sh[sb]?|li?nk|bat|cmd|com|ht[ab]|ps1?" }
    ::= {AttachmentBlocking 412}

syncStatBadAttachL1  OBJECT-TYPE
    SYNTAX      OCTET STRING
    MAX-ACCESS  read-only
    STATUS      current
    DESCRIPTION
"
synchronization status for BadAttachL1
-1 - BadAttachL1 could not be synchronized
 0 - synchronization not configured
 1 - out of sync - running master mode
 2 - in sync - running  mastermode
 3 - in sync - running slave mode
 4 - in sync - running master mode (wait to reach state 2)
"
    ::= {BadAttachL1 5}

syncStatStrBadAttachL1  OBJECT-TYPE
    SYNTAX      OCTET STRING
    MAX-ACCESS  read-only
    STATUS      current
    DESCRIPTION
"
synchronization status line from file assp_sync.cfg for BadAttachL1
 0 - synchronization not configured
 1 - out of sync - running master mode
 2 - in sync - running  mastermode
 3 - in sync - running slave mode
 4 - in sync - running master mode (wait to reach state 2)
"
    ::= {BadAttachL1 6}

BadAttachL2  OBJECT-TYPE
    SYNTAX      OCTET STRING
    MAX-ACCESS  read-write
    STATUS      current
    DESCRIPTION
"
This regular expression is used to identify Level 2 attachments that should be blocked.
  Level 2 already includes all rejected extensions from Level 1.  For example: (ad[ep]|asx|ba[st]|chm|cmd|com|cpl|crt|dbx|exe|hlp|ht[ab]|in[fs]|isp|js|jse|lnk|md[abez]|mht|ms[cipt]|nch|pcd|pif|prf|reg|sc[frt]|sh[bs]|vb|vb[es]|wms|ws[cfh]).zip
"
    REFERENCE "Level 2 rejected File Extensions"
    DEFVAL { "" }
    ::= {AttachmentBlocking 413}

syncStatBadAttachL2  OBJECT-TYPE
    SYNTAX      OCTET STRING
    MAX-ACCESS  read-only
    STATUS      current
    DESCRIPTION
"
synchronization status for BadAttachL2
-1 - BadAttachL2 could not be synchronized
 0 - synchronization not configured
 1 - out of sync - running master mode
 2 - in sync - running  mastermode
 3 - in sync - running slave mode
 4 - in sync - running master mode (wait to reach state 2)
"
    ::= {BadAttachL2 5}

syncStatStrBadAttachL2  OBJECT-TYPE
    SYNTAX      OCTET STRING
    MAX-ACCESS  read-only
    STATUS      current
    DESCRIPTION
"
synchronization status line from file assp_sync.cfg for BadAttachL2
 0 - synchronization not configured
 1 - out of sync - running master mode
 2 - in sync - running  mastermode
 3 - in sync - running slave mode
 4 - in sync - running master mode (wait to reach state 2)
"
    ::= {BadAttachL2 6}

BadAttachL3  OBJECT-TYPE
    SYNTAX      OCTET STRING
    MAX-ACCESS  read-write
    STATUS      current
    DESCRIPTION
"
This regular expression is used to identify Level 3 attachments that should be blocked.
  Level 3 includes Level 2 and Level 1. For example: zip|url
"
    REFERENCE "Level 3 rejected File Extensions"
    DEFVAL { "" }
    ::= {AttachmentBlocking 414}

syncStatBadAttachL3  OBJECT-TYPE
    SYNTAX      OCTET STRING
    MAX-ACCESS  read-only
    STATUS      current
    DESCRIPTION
"
synchronization status for BadAttachL3
-1 - BadAttachL3 could not be synchronized
 0 - synchronization not configured
 1 - out of sync - running master mode
 2 - in sync - running  mastermode
 3 - in sync - running slave mode
 4 - in sync - running master mode (wait to reach state 2)
"
    ::= {BadAttachL3 5}

syncStatStrBadAttachL3  OBJECT-TYPE
    SYNTAX      OCTET STRING
    MAX-ACCESS  read-only
    STATUS      current
    DESCRIPTION
"
synchronization status line from file assp_sync.cfg for BadAttachL3
 0 - synchronization not configured
 1 - out of sync - running master mode
 2 - in sync - running  mastermode
 3 - in sync - running slave mode
 4 - in sync - running master mode (wait to reach state 2)
"
    ::= {BadAttachL3 6}

GoodAttach  OBJECT-TYPE
    SYNTAX      OCTET STRING
    MAX-ACCESS  read-write
    STATUS      current
    DESCRIPTION
"
This regular expression is used to identify attachments that should be allowed. All others are blocked. Separate entries with a pipe |. The dot . is assumed to precede these, so don't include it. For example: ai|asc|bhx|dat|docx?|eps|gif|htm|html|ics|jpg|jpeg|hqx|od[tsp]|pdf|p7[mscz]|ppt|rar|rpt|rtf|snp|txt|xls|zip|7z
"
    REFERENCE "Level 4 Allowed File Extensions"
    DEFVAL { "" }
    ::= {AttachmentBlocking 415}

syncStatGoodAttach  OBJECT-TYPE
    SYNTAX      OCTET STRING
    MAX-ACCESS  read-only
    STATUS      current
    DESCRIPTION
"
synchronization status for GoodAttach
-1 - GoodAttach could not be synchronized
 0 - synchronization not configured
 1 - out of sync - running master mode
 2 - in sync - running  mastermode
 3 - in sync - running slave mode
 4 - in sync - running master mode (wait to reach state 2)
"
    ::= {GoodAttach 5}

syncStatStrGoodAttach  OBJECT-TYPE
    SYNTAX      OCTET STRING
    MAX-ACCESS  read-only
    STATUS      current
    DESCRIPTION
"
synchronization status line from file assp_sync.cfg for GoodAttach
 0 - synchronization not configured
 1 - out of sync - running master mode
 2 - in sync - running  mastermode
 3 - in sync - running slave mode
 4 - in sync - running master mode (wait to reach state 2)
"
    ::= {GoodAttach 6}

AttachmentError  OBJECT-TYPE
    SYNTAX      OCTET STRING
    MAX-ACCESS  read-write
    STATUS      current
    DESCRIPTION
"
The literal 'FILENAME' will be replaced with the name of the blocked attachment!
"
    REFERENCE "Reply Code to Refuse Rejected Attachments"
    DEFVAL { "550 5.7.1 These attachments are not allowed -- Compress before mailing." }
    ::= {AttachmentBlocking 416}

syncStatAttachmentError  OBJECT-TYPE
    SYNTAX      OCTET STRING
    MAX-ACCESS  read-only
    STATUS      current
    DESCRIPTION
"
synchronization status for AttachmentError
-1 - AttachmentError could not be synchronized
 0 - synchronization not configured
 1 - out of sync - running master mode
 2 - in sync - running  mastermode
 3 - in sync - running slave mode
 4 - in sync - running master mode (wait to reach state 2)
"
    ::= {AttachmentError 5}

syncStatStrAttachmentError  OBJECT-TYPE
    SYNTAX      OCTET STRING
    MAX-ACCESS  read-only
    STATUS      current
    DESCRIPTION
"
synchronization status line from file assp_sync.cfg for AttachmentError
 0 - synchronization not configured
 1 - out of sync - running master mode
 2 - in sync - running  mastermode
 3 - in sync - running slave mode
 4 - in sync - running master mode (wait to reach state 2)
"
    ::= {AttachmentError 6}

BlockUuencoded  OBJECT-TYPE
    SYNTAX      OCTET STRING
    MAX-ACCESS  read-write
    STATUS      current
    DESCRIPTION
"

"
    REFERENCE "Refuse Uuencoded Mails"
    DEFVAL { "1" }
    ::= {AttachmentBlocking 417}

syncStatBlockUuencoded  OBJECT-TYPE
    SYNTAX      OCTET STRING
    MAX-ACCESS  read-only
    STATUS      current
    DESCRIPTION
"
synchronization status for BlockUuencoded
-1 - BlockUuencoded could not be synchronized
 0 - synchronization not configured
 1 - out of sync - running master mode
 2 - in sync - running  mastermode
 3 - in sync - running slave mode
 4 - in sync - running master mode (wait to reach state 2)
"
    ::= {BlockUuencoded 5}

syncStatStrBlockUuencoded  OBJECT-TYPE
    SYNTAX      OCTET STRING
    MAX-ACCESS  read-only
    STATUS      current
    DESCRIPTION
"
synchronization status line from file assp_sync.cfg for BlockUuencoded
 0 - synchronization not configured
 1 - out of sync - running master mode
 2 - in sync - running  mastermode
 3 - in sync - running slave mode
 4 - in sync - running master mode (wait to reach state 2)
"
    ::= {BlockUuencoded 6}

UuencodedError  OBJECT-TYPE
    SYNTAX      OCTET STRING
    MAX-ACCESS  read-write
    STATUS      current
    DESCRIPTION
"
For example: 554 5.7.1 This mail is uuencoded and will be blocked
 
"
    REFERENCE "Reply to Refuse Uuencoded Mails"
    DEFVAL { "554 5.7.1 This message is uuencoded and will be blocked. " }
    ::= {AttachmentBlocking 418}

syncStatUuencodedError  OBJECT-TYPE
    SYNTAX      OCTET STRING
    MAX-ACCESS  read-only
    STATUS      current
    DESCRIPTION
"
synchronization status for UuencodedError
-1 - UuencodedError could not be synchronized
 0 - synchronization not configured
 1 - out of sync - running master mode
 2 - in sync - running  mastermode
 3 - in sync - running slave mode
 4 - in sync - running master mode (wait to reach state 2)
"
    ::= {UuencodedError 5}

syncStatStrUuencodedError  OBJECT-TYPE
    SYNTAX      OCTET STRING
    MAX-ACCESS  read-only
    STATUS      current
    DESCRIPTION
"
synchronization status line from file assp_sync.cfg for UuencodedError
 0 - synchronization not configured
 1 - out of sync - running master mode
 2 - in sync - running  mastermode
 3 - in sync - running slave mode
 4 - in sync - running master mode (wait to reach state 2)
"
    ::= {UuencodedError 6}

UserAttach  OBJECT-TYPE
    SYNTAX      OCTET STRING
    MAX-ACCESS  read-write
    STATUS      current
    DESCRIPTION
"
This set of regular expression is used to identify attachments that should be allowed or blocked for specified users and/or domains. Separate entries with a any of '=&gt; , ; space'. Separate multiple regex entries with pipe '|'. The dot . is assumed to precede the regex, so don't include it anywhere (except the user name).
  To define entries you have to use the 'file:...' option. Define one entry per line - comments are not allowed in a definition line.
  The syntax of an entry is as follows:
  username => good => goodAttachRegex , good-out => goodoutRegex , good-in => goodinRegex , block => blockAttachRegex , block-out => blockoutRegex , block-in => blockinRegex
  username - Mail solely to or from any of these addresses. Accepts specific addresses (user@domain.com), user parts (user) or entire domains (@domain.com) or a Group definition [GROUP]. Wildcards are supported (fribo*@domain.com).
  good => goodAttachRegex - good attachment for incoming and outgoing mails
  good-out => goodoutRegex - good attachment for outgoing mails
  good-in => goodinRegex - good attachment for incoming mails
  block => blockAttachRegex - bad attachment for incoming and outgoing mails
  block-out => blockoutRegex - bad attachment for outgoing mails
  block-in => blockinRegex - bad attachment for incoming mails
  For example:
  user@domain.tld => good => ai|asc|bhx|dat|doc|eps|gif|htm|html|ics|jpg|jpeg|hqx|od[tsp]|pdf|ppt|rar|rpt|rtf|snp|txt|xls|zip
  *@domain.tld => good => ai|asc|bhx , good-out => eps|gif , good-in => htm|html , block => pdf|ppt , block-out => rar|rpt , block-in => xls|exe\-bin
  At least one of the above option must be defined in a line - a maximum of all (six) could be defined, if this makes sense.
  If the user name matches for a sender or recipient and a (in/out) regex definition is found in this file, all level definition are overwritten for this mail.
  good, good-out and good-in - and also - block, block-out and block-in - will be logical OR combined according to the mail flow.
  Notice: if a bad attachment is found on a user based attachment check, the penalty box IP address scoring is skipped.
"
    REFERENCE "User based Good and Bad Attachments*"
    DEFVAL { "" }
    ::= {AttachmentBlocking 969}

syncStatUserAttach  OBJECT-TYPE
    SYNTAX      OCTET STRING
    MAX-ACCESS  read-only
    STATUS      current
    DESCRIPTION
"
synchronization status for UserAttach
-1 - UserAttach could not be synchronized
 0 - synchronization not configured
 1 - out of sync - running master mode
 2 - in sync - running  mastermode
 3 - in sync - running slave mode
 4 - in sync - running master mode (wait to reach state 2)
"
    ::= {UserAttach 5}

syncStatStrUserAttach  OBJECT-TYPE
    SYNTAX      OCTET STRING
    MAX-ACCESS  read-only
    STATUS      current
    DESCRIPTION
"
synchronization status line from file assp_sync.cfg for UserAttach
 0 - synchronization not configured
 1 - out of sync - running master mode
 2 - in sync - running  mastermode
 3 - in sync - running slave mode
 4 - in sync - running master mode (wait to reach state 2)
"
    ::= {UserAttach 6}

ClamAVandFileScan  OBJECT IDENTIFIER ::= {asspConfig 21}
noScan  OBJECT-TYPE
    SYNTAX      OCTET STRING
    MAX-ACCESS  read-write
    STATUS      current
    DESCRIPTION
"
Accepts specific addresses (user@domain.com), user parts (user) or entire domains (@domain.com).
"
    REFERENCE "Do Not Scan Messages from/to these Addresses*"
    DEFVAL { "" }
    ::= {ClamAVandFileScan 419}

syncStatnoScan  OBJECT-TYPE
    SYNTAX      OCTET STRING
    MAX-ACCESS  read-only
    STATUS      current
    DESCRIPTION
"
synchronization status for noScan
-1 - noScan could not be synchronized
 0 - synchronization not configured
 1 - out of sync - running master mode
 2 - in sync - running  mastermode
 3 - in sync - running slave mode
 4 - in sync - running master mode (wait to reach state 2)
"
    ::= {noScan 5}

syncStatStrnoScan  OBJECT-TYPE
    SYNTAX      OCTET STRING
    MAX-ACCESS  read-only
    STATUS      current
    DESCRIPTION
"
synchronization status line from file assp_sync.cfg for noScan
 0 - synchronization not configured
 1 - out of sync - running master mode
 2 - in sync - running  mastermode
 3 - in sync - running slave mode
 4 - in sync - running master mode (wait to reach state 2)
"
    ::= {noScan 6}

noScanIP  OBJECT-TYPE
    SYNTAX      OCTET STRING
    MAX-ACCESS  read-write
    STATUS      current
    DESCRIPTION
"
Enter IP addresses that you don't want to be scanned for virus , separated by pipes (|). For example: 145.145.145.145|145.146.
"
    REFERENCE "Do Not Scan Messages from these IP's*"
    DEFVAL { "" }
    ::= {ClamAVandFileScan 420}

syncStatnoScanIP  OBJECT-TYPE
    SYNTAX      OCTET STRING
    MAX-ACCESS  read-only
    STATUS      current
    DESCRIPTION
"
synchronization status for noScanIP
-1 - noScanIP could not be synchronized
 0 - synchronization not configured
 1 - out of sync - running master mode
 2 - in sync - running  mastermode
 3 - in sync - running slave mode
 4 - in sync - running master mode (wait to reach state 2)
"
    ::= {noScanIP 5}

syncStatStrnoScanIP  OBJECT-TYPE
    SYNTAX      OCTET STRING
    MAX-ACCESS  read-only
    STATUS      current
    DESCRIPTION
"
synchronization status line from file assp_sync.cfg for noScanIP
 0 - synchronization not configured
 1 - out of sync - running master mode
 2 - in sync - running  mastermode
 3 - in sync - running slave mode
 4 - in sync - running master mode (wait to reach state 2)
"
    ::= {noScanIP 6}

NoScanRe  OBJECT-TYPE
    SYNTAX      OCTET STRING
    MAX-ACCESS  read-write
    STATUS      current
    DESCRIPTION
"
Put anything here to identify messages which should not be checked for viruses.
"
    REFERENCE "Skip Virus RegEx*"
    DEFVAL { "" }
    ::= {ClamAVandFileScan 421}

syncStatNoScanRe  OBJECT-TYPE
    SYNTAX      OCTET STRING
    MAX-ACCESS  read-only
    STATUS      current
    DESCRIPTION
"
synchronization status for NoScanRe
-1 - NoScanRe could not be synchronized
 0 - synchronization not configured
 1 - out of sync - running master mode
 2 - in sync - running  mastermode
 3 - in sync - running slave mode
 4 - in sync - running master mode (wait to reach state 2)
"
    ::= {NoScanRe 5}

syncStatStrNoScanRe  OBJECT-TYPE
    SYNTAX      OCTET STRING
    MAX-ACCESS  read-only
    STATUS      current
    DESCRIPTION
"
synchronization status line from file assp_sync.cfg for NoScanRe
 0 - synchronization not configured
 1 - out of sync - running master mode
 2 - in sync - running  mastermode
 3 - in sync - running slave mode
 4 - in sync - running master mode (wait to reach state 2)
"
    ::= {NoScanRe 6}

SuspiciousVirus  OBJECT-TYPE
    SYNTAX      OCTET STRING
    MAX-ACCESS  read-write
    STATUS      current
    DESCRIPTION
"
If a ClamAV or FileScan result matches this expression it will be scored with the suspicious virus score ( vsValencePB ) and the message will not be blocked.
 It is possible to weight such results. Every weighted regex that contains at least one '|' has to begin and end with a '~' - inside such regexes it is not allowed to use a '~', even it is escaped - for example:  ~abc\~|def~=>23 or ~abc~|def~=>23 - instead use the octal (\126) or hex (\x7E) notation , for example ~abc\126|def~=>23 or ~abc\x7E|def~=>23 . Every weighted regex has to be followed by '=>' and the weight value. For example: Phishing\.=>1.45|~Heuristics|Email~=>50  or ~(Email|HTML|Sanesecurity)\.(Phishing|Spear|(Spam|Scam)[a-z0-9]?)\.~=>4.6|Spam=>1.1|~Spear|Scam~=>2.1 . The multiplication result of the weight and the penaltybox valence value will be used for scoring, if the absolute value of weight is less or equal 6. Otherwise the value of weight is used for scoring.
"
    REFERENCE "No-Blocking Virus Scan Scoring Regex**"
    DEFVAL { "file:files/suspiciousvirus.txt" }
    ::= {ClamAVandFileScan 422}

syncStatSuspiciousVirus  OBJECT-TYPE
    SYNTAX      OCTET STRING
    MAX-ACCESS  read-only
    STATUS      current
    DESCRIPTION
"
synchronization status for SuspiciousVirus
-1 - SuspiciousVirus could not be synchronized
 0 - synchronization not configured
 1 - out of sync - running master mode
 2 - in sync - running  mastermode
 3 - in sync - running slave mode
 4 - in sync - running master mode (wait to reach state 2)
"
    ::= {SuspiciousVirus 5}

syncStatStrSuspiciousVirus  OBJECT-TYPE
    SYNTAX      OCTET STRING
    MAX-ACCESS  read-only
    STATUS      current
    DESCRIPTION
"
synchronization status line from file assp_sync.cfg for SuspiciousVirus
 0 - synchronization not configured
 1 - out of sync - running master mode
 2 - in sync - running  mastermode
 3 - in sync - running slave mode
 4 - in sync - running master mode (wait to reach state 2)
"
    ::= {SuspiciousVirus 6}

ScanWL  OBJECT-TYPE
    SYNTAX      OCTET STRING
    MAX-ACCESS  read-write
    STATUS      current
    DESCRIPTION
"

"
    REFERENCE "Scan Whitelisted Senders"
    DEFVAL { "1" }
    ::= {ClamAVandFileScan 423}

syncStatScanWL  OBJECT-TYPE
    SYNTAX      OCTET STRING
    MAX-ACCESS  read-only
    STATUS      current
    DESCRIPTION
"
synchronization status for ScanWL
-1 - ScanWL could not be synchronized
 0 - synchronization not configured
 1 - out of sync - running master mode
 2 - in sync - running  mastermode
 3 - in sync - running slave mode
 4 - in sync - running master mode (wait to reach state 2)
"
    ::= {ScanWL 5}

syncStatStrScanWL  OBJECT-TYPE
    SYNTAX      OCTET STRING
    MAX-ACCESS  read-only
    STATUS      current
    DESCRIPTION
"
synchronization status line from file assp_sync.cfg for ScanWL
 0 - synchronization not configured
 1 - out of sync - running master mode
 2 - in sync - running  mastermode
 3 - in sync - running slave mode
 4 - in sync - running master mode (wait to reach state 2)
"
    ::= {ScanWL 6}

ScanNP  OBJECT-TYPE
    SYNTAX      OCTET STRING
    MAX-ACCESS  read-write
    STATUS      current
    DESCRIPTION
"

"
    REFERENCE "Scan No Processing Senders"
    DEFVAL { "" }
    ::= {ClamAVandFileScan 424}

syncStatScanNP  OBJECT-TYPE
    SYNTAX      OCTET STRING
    MAX-ACCESS  read-only
    STATUS      current
    DESCRIPTION
"
synchronization status for ScanNP
-1 - ScanNP could not be synchronized
 0 - synchronization not configured
 1 - out of sync - running master mode
 2 - in sync - running  mastermode
 3 - in sync - running slave mode
 4 - in sync - running master mode (wait to reach state 2)
"
    ::= {ScanNP 5}

syncStatStrScanNP  OBJECT-TYPE
    SYNTAX      OCTET STRING
    MAX-ACCESS  read-only
    STATUS      current
    DESCRIPTION
"
synchronization status line from file assp_sync.cfg for ScanNP
 0 - synchronization not configured
 1 - out of sync - running master mode
 2 - in sync - running  mastermode
 3 - in sync - running slave mode
 4 - in sync - running master mode (wait to reach state 2)
"
    ::= {ScanNP 6}

ScanLocal  OBJECT-TYPE
    SYNTAX      OCTET STRING
    MAX-ACCESS  read-write
    STATUS      current
    DESCRIPTION
"

"
    REFERENCE "Scan Local Senders"
    DEFVAL { "" }
    ::= {ClamAVandFileScan 425}

syncStatScanLocal  OBJECT-TYPE
    SYNTAX      OCTET STRING
    MAX-ACCESS  read-only
    STATUS      current
    DESCRIPTION
"
synchronization status for ScanLocal
-1 - ScanLocal could not be synchronized
 0 - synchronization not configured
 1 - out of sync - running master mode
 2 - in sync - running  mastermode
 3 - in sync - running slave mode
 4 - in sync - running master mode (wait to reach state 2)
"
    ::= {ScanLocal 5}

syncStatStrScanLocal  OBJECT-TYPE
    SYNTAX      OCTET STRING
    MAX-ACCESS  read-only
    STATUS      current
    DESCRIPTION
"
synchronization status line from file assp_sync.cfg for ScanLocal
 0 - synchronization not configured
 1 - out of sync - running master mode
 2 - in sync - running  mastermode
 3 - in sync - running slave mode
 4 - in sync - running master mode (wait to reach state 2)
"
    ::= {ScanLocal 6}

ScanCC  OBJECT-TYPE
    SYNTAX      OCTET STRING
    MAX-ACCESS  read-write
    STATUS      current
    DESCRIPTION
"

"
    REFERENCE "Scan Copied Spam and Forwarded Ham Mails"
    DEFVAL { "" }
    ::= {ClamAVandFileScan 426}

syncStatScanCC  OBJECT-TYPE
    SYNTAX      OCTET STRING
    MAX-ACCESS  read-only
    STATUS      current
    DESCRIPTION
"
synchronization status for ScanCC
-1 - ScanCC could not be synchronized
 0 - synchronization not configured
 1 - out of sync - running master mode
 2 - in sync - running  mastermode
 3 - in sync - running slave mode
 4 - in sync - running master mode (wait to reach state 2)
"
    ::= {ScanCC 5}

syncStatStrScanCC  OBJECT-TYPE
    SYNTAX      OCTET STRING
    MAX-ACCESS  read-only
    STATUS      current
    DESCRIPTION
"
synchronization status line from file assp_sync.cfg for ScanCC
 0 - synchronization not configured
 1 - out of sync - running master mode
 2 - in sync - running  mastermode
 3 - in sync - running slave mode
 4 - in sync - running master mode (wait to reach state 2)
"
    ::= {ScanCC 6}

AvError  OBJECT-TYPE
    SYNTAX      OCTET STRING
    MAX-ACCESS  read-write
    STATUS      current
    DESCRIPTION
"
Reply code to refuse infected messages. The string $infection is replaced with the name of the detected virus.
 For example: 554 5.7.1 Mail appears infected with \[$infection\] -- disinfect and resend.
"
    REFERENCE "Reply Code to Refuse Infected Messages"
    DEFVAL { "554 5.7.1 Mail appears infected with \[$infection\]." }
    ::= {ClamAVandFileScan 427}

syncStatAvError  OBJECT-TYPE
    SYNTAX      OCTET STRING
    MAX-ACCESS  read-only
    STATUS      current
    DESCRIPTION
"
synchronization status for AvError
-1 - AvError could not be synchronized
 0 - synchronization not configured
 1 - out of sync - running master mode
 2 - in sync - running  mastermode
 3 - in sync - running slave mode
 4 - in sync - running master mode (wait to reach state 2)
"
    ::= {AvError 5}

syncStatStrAvError  OBJECT-TYPE
    SYNTAX      OCTET STRING
    MAX-ACCESS  read-only
    STATUS      current
    DESCRIPTION
"
synchronization status line from file assp_sync.cfg for AvError
 0 - synchronization not configured
 1 - out of sync - running master mode
 2 - in sync - running  mastermode
 3 - in sync - running slave mode
 4 - in sync - running master mode (wait to reach state 2)
"
    ::= {AvError 6}

EmailVirusReportsTo  OBJECT-TYPE
    SYNTAX      OCTET STRING
    MAX-ACCESS  read-write
    STATUS      current
    DESCRIPTION
"
If set an email containing the Message ID, Remote IP, Message Subject, Sender email address, Recipient email address, and the virus detected will be sent to this address. For example: admin@domain.com
"
    REFERENCE "Send Virus Report To This Address"
    DEFVAL { "" }
    ::= {ClamAVandFileScan 428}

syncStatEmailVirusReportsTo  OBJECT-TYPE
    SYNTAX      OCTET STRING
    MAX-ACCESS  read-only
    STATUS      current
    DESCRIPTION
"
synchronization status for EmailVirusReportsTo
-1 - EmailVirusReportsTo could not be synchronized
 0 - synchronization not configured
 1 - out of sync - running master mode
 2 - in sync - running  mastermode
 3 - in sync - running slave mode
 4 - in sync - running master mode (wait to reach state 2)
"
    ::= {EmailVirusReportsTo 5}

syncStatStrEmailVirusReportsTo  OBJECT-TYPE
    SYNTAX      OCTET STRING
    MAX-ACCESS  read-only
    STATUS      current
    DESCRIPTION
"
synchronization status line from file assp_sync.cfg for EmailVirusReportsTo
 0 - synchronization not configured
 1 - out of sync - running master mode
 2 - in sync - running  mastermode
 3 - in sync - running slave mode
 4 - in sync - running master mode (wait to reach state 2)
"
    ::= {EmailVirusReportsTo 6}

EmailVirusReportsHeader  OBJECT-TYPE
    SYNTAX      OCTET STRING
    MAX-ACCESS  read-write
    STATUS      current
    DESCRIPTION
"
If set the full message headers will also be added to Virus Reports.
"
    REFERENCE "Add Full Header To Virus Report To Mail Address Above"
    DEFVAL { "" }
    ::= {ClamAVandFileScan 429}

syncStatEmailVirusReportsHeader  OBJECT-TYPE
    SYNTAX      OCTET STRING
    MAX-ACCESS  read-only
    STATUS      current
    DESCRIPTION
"
synchronization status for EmailVirusReportsHeader
-1 - EmailVirusReportsHeader could not be synchronized
 0 - synchronization not configured
 1 - out of sync - running master mode
 2 - in sync - running  mastermode
 3 - in sync - running slave mode
 4 - in sync - running master mode (wait to reach state 2)
"
    ::= {EmailVirusReportsHeader 5}

syncStatStrEmailVirusReportsHeader  OBJECT-TYPE
    SYNTAX      OCTET STRING
    MAX-ACCESS  read-only
    STATUS      current
    DESCRIPTION
"
synchronization status line from file assp_sync.cfg for EmailVirusReportsHeader
 0 - synchronization not configured
 1 - out of sync - running master mode
 2 - in sync - running  mastermode
 3 - in sync - running slave mode
 4 - in sync - running master mode (wait to reach state 2)
"
    ::= {EmailVirusReportsHeader 6}

EmailVirusReportsToRCPT  OBJECT-TYPE
    SYNTAX      OCTET STRING
    MAX-ACCESS  read-write
    STATUS      current
    DESCRIPTION
"
If set the intended recipient of the message will be sent a copy of the Virus Report. If 'for HAM only' is selected, the report will only be sent, in case the mail is not detected as SPAM before the virus check is done.
  
"
    REFERENCE "Send Virus Report To Recipient"
    DEFVAL { "0" }
    ::= {ClamAVandFileScan 430}

syncStatEmailVirusReportsToRCPT  OBJECT-TYPE
    SYNTAX      OCTET STRING
    MAX-ACCESS  read-only
    STATUS      current
    DESCRIPTION
"
synchronization status for EmailVirusReportsToRCPT
-1 - EmailVirusReportsToRCPT could not be synchronized
 0 - synchronization not configured
 1 - out of sync - running master mode
 2 - in sync - running  mastermode
 3 - in sync - running slave mode
 4 - in sync - running master mode (wait to reach state 2)
"
    ::= {EmailVirusReportsToRCPT 5}

syncStatStrEmailVirusReportsToRCPT  OBJECT-TYPE
    SYNTAX      OCTET STRING
    MAX-ACCESS  read-only
    STATUS      current
    DESCRIPTION
"
synchronization status line from file assp_sync.cfg for EmailVirusReportsToRCPT
 0 - synchronization not configured
 1 - out of sync - running master mode
 2 - in sync - running  mastermode
 3 - in sync - running slave mode
 4 - in sync - running master mode (wait to reach state 2)
"
    ::= {EmailVirusReportsToRCPT 6}

DoFileScan  OBJECT-TYPE
    SYNTAX      OCTET STRING
    MAX-ACCESS  read-write
    STATUS      current
    DESCRIPTION
"
If activated, the message is written to a file inside the 'FileScanDir' with an extension of 'maillogExt'. After that ASSP will call 'FileScanCMD' to detect if the temporary file is infected or not. The temporary created file(s) will be removed.
 The infected file will be stored in a special folder, if the SpamVirusLog is set to 'quarantine' and the filepath to the viruslog is set.
 Please check the setting of FileLogScan before you enable this option!
"
    REFERENCE "Use File System Virus Scanner"
    DEFVAL { "0" }
    ::= {ClamAVandFileScan 431}

syncStatDoFileScan  OBJECT-TYPE
    SYNTAX      OCTET STRING
    MAX-ACCESS  read-only
    STATUS      current
    DESCRIPTION
"
synchronization status for DoFileScan
-1 - DoFileScan could not be synchronized
 0 - synchronization not configured
 1 - out of sync - running master mode
 2 - in sync - running  mastermode
 3 - in sync - running slave mode
 4 - in sync - running master mode (wait to reach state 2)
"
    ::= {DoFileScan 5}

syncStatStrDoFileScan  OBJECT-TYPE
    SYNTAX      OCTET STRING
    MAX-ACCESS  read-only
    STATUS      current
    DESCRIPTION
"
synchronization status line from file assp_sync.cfg for DoFileScan
 0 - synchronization not configured
 1 - out of sync - running master mode
 2 - in sync - running  mastermode
 3 - in sync - running slave mode
 4 - in sync - running master mode (wait to reach state 2)
"
    ::= {DoFileScan 6}

FileScanDir  OBJECT-TYPE
    SYNTAX      OCTET STRING
    MAX-ACCESS  read-write
    STATUS      current
    DESCRIPTION
"
Define the full path to the directory where the messages are temporary stored for the file system virus scanner. This could be any directory inside your file system. The running ASSP process must have full permission to this directory and the files inside!
"
    REFERENCE "File Scan Directory"
    DEFVAL { "C:/assp/virusscan" }
    ::= {ClamAVandFileScan 432}

syncStatFileScanDir  OBJECT-TYPE
    SYNTAX      OCTET STRING
    MAX-ACCESS  read-only
    STATUS      current
    DESCRIPTION
"
synchronization status for FileScanDir
-1 - FileScanDir could not be synchronized
 0 - synchronization not configured
 1 - out of sync - running master mode
 2 - in sync - running  mastermode
 3 - in sync - running slave mode
 4 - in sync - running master mode (wait to reach state 2)
"
    ::= {FileScanDir 5}

syncStatStrFileScanDir  OBJECT-TYPE
    SYNTAX      OCTET STRING
    MAX-ACCESS  read-only
    STATUS      current
    DESCRIPTION
"
synchronization status line from file assp_sync.cfg for FileScanDir
 0 - synchronization not configured
 1 - out of sync - running master mode
 2 - in sync - running  mastermode
 3 - in sync - running slave mode
 4 - in sync - running master mode (wait to reach state 2)
"
    ::= {FileScanDir 6}

FileScanCMD  OBJECT-TYPE
    SYNTAX      OCTET STRING
    MAX-ACCESS  read-write
    STATUS      current
    DESCRIPTION
"
ASSP will call this system command and expects a returned string from this command. This returned string is checked against 'FileScanBad' and/or 'FileScanGood' to detect if the message is OK or not! If the file does not exists after the command call, the message is consider infected. ASSP expects, that the file scan is finished when the command returns!
  The literal 'FILENAME' will be replaced by the full qualified file name of the temporary file.
  The literal 'NUMBER' will be replaced by the threadnumber and could be used to name logfiles and to redirect them to STDOUT.
  The literal 'FILESCANDIR' will be replaced with the value of FileScanDir.
  Any case sensitive literal starting and ending with an asterix (*) like '*rcpt*' or '*mailfrom*' will be replaced by the quoted runtime connection variable of Con{fh}->{literal} (this->{literal}). You need to know the assp internals!
  If a code reference is defined for the internal variable &#36;main::FileScanCMDbuild_API in lib/CorrectASSPcfg.pm , assp will call '&#36;FileScanCMDbuild_API->(\&#36;cmd,&#36;this)' before running the command. The first parameter, the command (FileScanCMD), is submitted as a reference to a scalar, which must be modified in place. If you want assp not to scan the message, set this variable to undef. The second submitted parameter is the reference to the client connection parameter HASH - &#36;Con{fh} (eg. &#36;this)
  All outputs of this command to STDERR are automatic redirected to STDOUT.
  FileScan will not run, if FileScanCMD is not specified.
  If you have your online/autoprotect file scanner configured to delete infected files inside the 'FileScanDir', define 'NORUN' in this field! In this case FileScanGood and FileScanBad are ignored. If there is a need to wait some time for the autoprotect scanner, write 'NORUN-dddd', where dddd are the milliseconds to wait!
  Depending on your operating system it may possible, that you have to quote (' or ') the command, if it contains whitespaces. The replaced file name will be quoted by ASSP if needed.
"
    REFERENCE "File Scan Command"
    DEFVAL { "" }
    ::= {ClamAVandFileScan 433}

syncStatFileScanCMD  OBJECT-TYPE
    SYNTAX      OCTET STRING
    MAX-ACCESS  read-only
    STATUS      current
    DESCRIPTION
"
synchronization status for FileScanCMD
-1 - FileScanCMD could not be synchronized
 0 - synchronization not configured
 1 - out of sync - running master mode
 2 - in sync - running  mastermode
 3 - in sync - running slave mode
 4 - in sync - running master mode (wait to reach state 2)
"
    ::= {FileScanCMD 5}

syncStatStrFileScanCMD  OBJECT-TYPE
    SYNTAX      OCTET STRING
    MAX-ACCESS  read-only
    STATUS      current
    DESCRIPTION
"
synchronization status line from file assp_sync.cfg for FileScanCMD
 0 - synchronization not configured
 1 - out of sync - running master mode
 2 - in sync - running  mastermode
 3 - in sync - running slave mode
 4 - in sync - running master mode (wait to reach state 2)
"
    ::= {FileScanCMD 6}

FileScanBad  OBJECT-TYPE
    SYNTAX      OCTET STRING
    MAX-ACCESS  read-write
    STATUS      current
    DESCRIPTION
"
Put anything here to identify bad messages by the string returned from the FileScanCMD. If defined and this regular expression matches, the message is consider infected.
"
    REFERENCE "RegEx to Detect 'BAD' in Returned String*"
    DEFVAL { "" }
    ::= {ClamAVandFileScan 434}

syncStatFileScanBad  OBJECT-TYPE
    SYNTAX      OCTET STRING
    MAX-ACCESS  read-only
    STATUS      current
    DESCRIPTION
"
synchronization status for FileScanBad
-1 - FileScanBad could not be synchronized
 0 - synchronization not configured
 1 - out of sync - running master mode
 2 - in sync - running  mastermode
 3 - in sync - running slave mode
 4 - in sync - running master mode (wait to reach state 2)
"
    ::= {FileScanBad 5}

syncStatStrFileScanBad  OBJECT-TYPE
    SYNTAX      OCTET STRING
    MAX-ACCESS  read-only
    STATUS      current
    DESCRIPTION
"
synchronization status line from file assp_sync.cfg for FileScanBad
 0 - synchronization not configured
 1 - out of sync - running master mode
 2 - in sync - running  mastermode
 3 - in sync - running slave mode
 4 - in sync - running master mode (wait to reach state 2)
"
    ::= {FileScanBad 6}

FileScanGood  OBJECT-TYPE
    SYNTAX      OCTET STRING
    MAX-ACCESS  read-write
    STATUS      current
    DESCRIPTION
"
Put anything here to identify good messages by the string returned from the FileScanCMD. If defined and this regular expression matches and 'FileScanBad' does not, the message is consider not infected.
  If both FileScanBad and FileScanGood are defined, FileScanBad has not to match and FileScanGood has to match, to consider a mail not infected!
"
    REFERENCE "RegEx to Detect 'GOOD' in Returned String*"
    DEFVAL { "" }
    ::= {ClamAVandFileScan 435}

syncStatFileScanGood  OBJECT-TYPE
    SYNTAX      OCTET STRING
    MAX-ACCESS  read-only
    STATUS      current
    DESCRIPTION
"
synchronization status for FileScanGood
-1 - FileScanGood could not be synchronized
 0 - synchronization not configured
 1 - out of sync - running master mode
 2 - in sync - running  mastermode
 3 - in sync - running slave mode
 4 - in sync - running master mode (wait to reach state 2)
"
    ::= {FileScanGood 5}

syncStatStrFileScanGood  OBJECT-TYPE
    SYNTAX      OCTET STRING
    MAX-ACCESS  read-only
    STATUS      current
    DESCRIPTION
"
synchronization status line from file assp_sync.cfg for FileScanGood
 0 - synchronization not configured
 1 - out of sync - running master mode
 2 - in sync - running  mastermode
 3 - in sync - running slave mode
 4 - in sync - running master mode (wait to reach state 2)
"
    ::= {FileScanGood 6}

FileScanRespRe  OBJECT-TYPE
    SYNTAX      OCTET STRING
    MAX-ACCESS  read-write
    STATUS      current
    DESCRIPTION
"
A regular expression that will be used over the text returned from the FileScanCMD. The result of this regex is used as virus name ($infection) in AvError. For example: infected by .+? \.\&lt;hr \/\&gt;
"
    REFERENCE "FileScan Responds Regex*"
    DEFVAL { "" }
    ::= {ClamAVandFileScan 436}

syncStatFileScanRespRe  OBJECT-TYPE
    SYNTAX      OCTET STRING
    MAX-ACCESS  read-only
    STATUS      current
    DESCRIPTION
"
synchronization status for FileScanRespRe
-1 - FileScanRespRe could not be synchronized
 0 - synchronization not configured
 1 - out of sync - running master mode
 2 - in sync - running  mastermode
 3 - in sync - running slave mode
 4 - in sync - running master mode (wait to reach state 2)
"
    ::= {FileScanRespRe 5}

syncStatStrFileScanRespRe  OBJECT-TYPE
    SYNTAX      OCTET STRING
    MAX-ACCESS  read-only
    STATUS      current
    DESCRIPTION
"
synchronization status line from file assp_sync.cfg for FileScanRespRe
 0 - synchronization not configured
 1 - out of sync - running master mode
 2 - in sync - running  mastermode
 3 - in sync - running slave mode
 4 - in sync - running master mode (wait to reach state 2)
"
    ::= {FileScanRespRe 6}

UseAvClamd  OBJECT-TYPE
    SYNTAX      OCTET STRING
    MAX-ACCESS  read-write
    STATUS      current
    DESCRIPTION
"
If activated, the message is checked by ClamAV, this requires an installed File::Scan::ClamAV Perl module and a running Clamd . It is not recommended to use ClamAV on heavy-load systems, because of resulting system overload, stucking workers or timeouts.
 The infected file will be stored in a special folder, if the SpamVirusLog is set to 'quarantine' and the filepath to the viruslog is set.
 Please check the setting of ClamAVLogScan before you enable this option!
"
    REFERENCE "Use ClamAV"
    DEFVAL { "0" }
    ::= {ClamAVandFileScan 437}

syncStatUseAvClamd  OBJECT-TYPE
    SYNTAX      OCTET STRING
    MAX-ACCESS  read-only
    STATUS      current
    DESCRIPTION
"
synchronization status for UseAvClamd
-1 - UseAvClamd could not be synchronized
 0 - synchronization not configured
 1 - out of sync - running master mode
 2 - in sync - running  mastermode
 3 - in sync - running slave mode
 4 - in sync - running master mode (wait to reach state 2)
"
    ::= {UseAvClamd 5}

syncStatStrUseAvClamd  OBJECT-TYPE
    SYNTAX      OCTET STRING
    MAX-ACCESS  read-only
    STATUS      current
    DESCRIPTION
"
synchronization status line from file assp_sync.cfg for UseAvClamd
 0 - synchronization not configured
 1 - out of sync - running master mode
 2 - in sync - running  mastermode
 3 - in sync - running slave mode
 4 - in sync - running master mode (wait to reach state 2)
"
    ::= {UseAvClamd 6}

AvClamdPort  OBJECT-TYPE
    SYNTAX      OCTET STRING
    MAX-ACCESS  read-write
    STATUS      current
    DESCRIPTION
"
A socket specified in the clamav.conf file - LocalSocket. For example /tmp/clamd. If the socket has been setup as a TCP/IP socket (see the TCPSocket option in the clamav.conf file), then specify the TCP socket. For example: 3310 
"
    REFERENCE "Port or file socket for ClamAV"
    DEFVAL { "" }
    ::= {ClamAVandFileScan 438}

syncStatAvClamdPort  OBJECT-TYPE
    SYNTAX      OCTET STRING
    MAX-ACCESS  read-only
    STATUS      current
    DESCRIPTION
"
synchronization status for AvClamdPort
-1 - AvClamdPort could not be synchronized
 0 - synchronization not configured
 1 - out of sync - running master mode
 2 - in sync - running  mastermode
 3 - in sync - running slave mode
 4 - in sync - running master mode (wait to reach state 2)
"
    ::= {AvClamdPort 5}

syncStatStrAvClamdPort  OBJECT-TYPE
    SYNTAX      OCTET STRING
    MAX-ACCESS  read-only
    STATUS      current
    DESCRIPTION
"
synchronization status line from file assp_sync.cfg for AvClamdPort
 0 - synchronization not configured
 1 - out of sync - running master mode
 2 - in sync - running  mastermode
 3 - in sync - running slave mode
 4 - in sync - running master mode (wait to reach state 2)
"
    ::= {AvClamdPort 6}

ClamAVBytes  OBJECT-TYPE
    SYNTAX      OCTET STRING
    MAX-ACCESS  read-write
    STATUS      current
    DESCRIPTION
"
The number of bytes per message or file that will be submited to ClamAV and FileScan for virus scanning. Values of 100000 or larger are not recommended, because while a thread is waiting for the scanner result, it could not get new connections.
"
    REFERENCE "ClamAV Bytes"
    DEFVAL { "60000" }
    ::= {ClamAVandFileScan 439}

syncStatClamAVBytes  OBJECT-TYPE
    SYNTAX      OCTET STRING
    MAX-ACCESS  read-only
    STATUS      current
    DESCRIPTION
"
synchronization status for ClamAVBytes
-1 - ClamAVBytes could not be synchronized
 0 - synchronization not configured
 1 - out of sync - running master mode
 2 - in sync - running  mastermode
 3 - in sync - running slave mode
 4 - in sync - running master mode (wait to reach state 2)
"
    ::= {ClamAVBytes 5}

syncStatStrClamAVBytes  OBJECT-TYPE
    SYNTAX      OCTET STRING
    MAX-ACCESS  read-only
    STATUS      current
    DESCRIPTION
"
synchronization status line from file assp_sync.cfg for ClamAVBytes
 0 - synchronization not configured
 1 - out of sync - running master mode
 2 - in sync - running  mastermode
 3 - in sync - running slave mode
 4 - in sync - running master mode (wait to reach state 2)
"
    ::= {ClamAVBytes 6}

ClamAVtimeout  OBJECT-TYPE
    SYNTAX      OCTET STRING
    MAX-ACCESS  read-write
    STATUS      current
    DESCRIPTION
"
ClamAV will timeout after this many seconds. default: 10 seconds.
 
"
    REFERENCE "ClamAV Timeout"
    DEFVAL { "10" }
    ::= {ClamAVandFileScan 440}

syncStatClamAVtimeout  OBJECT-TYPE
    SYNTAX      OCTET STRING
    MAX-ACCESS  read-only
    STATUS      current
    DESCRIPTION
"
synchronization status for ClamAVtimeout
-1 - ClamAVtimeout could not be synchronized
 0 - synchronization not configured
 1 - out of sync - running master mode
 2 - in sync - running  mastermode
 3 - in sync - running slave mode
 4 - in sync - running master mode (wait to reach state 2)
"
    ::= {ClamAVtimeout 5}

syncStatStrClamAVtimeout  OBJECT-TYPE
    SYNTAX      OCTET STRING
    MAX-ACCESS  read-only
    STATUS      current
    DESCRIPTION
"
synchronization status line from file assp_sync.cfg for ClamAVtimeout
 0 - synchronization not configured
 1 - out of sync - running master mode
 2 - in sync - running  mastermode
 3 - in sync - running slave mode
 4 - in sync - running master mode (wait to reach state 2)
"
    ::= {ClamAVtimeout 6}

FileLogScan  OBJECT-TYPE
    SYNTAX      OCTET STRING
    MAX-ACCESS  read-write
    STATUS      current
    DESCRIPTION
"
If virus check is enabled ( DoFileScan ), every file/mail (except reports - eg. n10000123456$maillogExt) in the 'resendmail' folder and if selected, every collected file is scanned for virus before it is sent or stored.
 If a virus is found, the file/mail is not (re)sent (it will get the extension '.virus'). Infected collected files are moved in to the SpamVirusLog folder.
 If 'scan resend folder and collected files' is selected, it could be possible, that the virus scanner ( FileScanCMD ) forces a very high system workload.
 If you are not sure what to set here, leave the setting at the default 'scan resend folder only'!
 Under normal conditions the scan will be done by the SMTP-worker, if assp is under a havy workload, the scan request will be transfered to the High-Workers (10000/10001).
"
    REFERENCE "Scan Resent and Stored Files for Virus with FileScan"
    DEFVAL { "1" }
    ::= {ClamAVandFileScan 976}

syncStatFileLogScan  OBJECT-TYPE
    SYNTAX      OCTET STRING
    MAX-ACCESS  read-only
    STATUS      current
    DESCRIPTION
"
synchronization status for FileLogScan
-1 - FileLogScan could not be synchronized
 0 - synchronization not configured
 1 - out of sync - running master mode
 2 - in sync - running  mastermode
 3 - in sync - running slave mode
 4 - in sync - running master mode (wait to reach state 2)
"
    ::= {FileLogScan 5}

syncStatStrFileLogScan  OBJECT-TYPE
    SYNTAX      OCTET STRING
    MAX-ACCESS  read-only
    STATUS      current
    DESCRIPTION
"
synchronization status line from file assp_sync.cfg for FileLogScan
 0 - synchronization not configured
 1 - out of sync - running master mode
 2 - in sync - running  mastermode
 3 - in sync - running slave mode
 4 - in sync - running master mode (wait to reach state 2)
"
    ::= {FileLogScan 6}

ClamAVLogScan  OBJECT-TYPE
    SYNTAX      OCTET STRING
    MAX-ACCESS  read-write
    STATUS      current
    DESCRIPTION
"
If virus check is enabled ( UseAvClamd ), every file/mail (except reports - eg. n10000123456$maillogExt) in the 'resendmail' folder and if selected, every collected file is scanned for virus before it is sent or stored.
 If a virus is found, the file/mail is not (re)sent (it will get the extension '.virus'). Infected collected files are moved in to the SpamVirusLog folder.
 If 'scan resend folder and collected files' is selected, it could be possible, that the virus scanner (clamd) forces a very high system workload.
 If you are not sure what to set here, leave the setting at the default 'scan resend folder only'!
 Under normal conditions the scan will be done by the SMTP-worker, if assp is under a havy workload, the scan request will be transfered to the High-Workers (10000/10001).
"
    REFERENCE "Scan Resent and Stored Files for Virus with ClamAV"
    DEFVAL { "1" }
    ::= {ClamAVandFileScan 1040}

syncStatClamAVLogScan  OBJECT-TYPE
    SYNTAX      OCTET STRING
    MAX-ACCESS  read-only
    STATUS      current
    DESCRIPTION
"
synchronization status for ClamAVLogScan
-1 - ClamAVLogScan could not be synchronized
 0 - synchronization not configured
 1 - out of sync - running master mode
 2 - in sync - running  mastermode
 3 - in sync - running slave mode
 4 - in sync - running master mode (wait to reach state 2)
"
    ::= {ClamAVLogScan 5}

syncStatStrClamAVLogScan  OBJECT-TYPE
    SYNTAX      OCTET STRING
    MAX-ACCESS  read-only
    STATUS      current
    DESCRIPTION
"
synchronization status line from file assp_sync.cfg for ClamAVLogScan
 0 - synchronization not configured
 1 - out of sync - running master mode
 2 - in sync - running  mastermode
 3 - in sync - running slave mode
 4 - in sync - running master mode (wait to reach state 2)
"
    ::= {ClamAVLogScan 6}

RegexFilterSpambomb  OBJECT IDENTIFIER ::= {asspConfig 22}
DoTransliterate  OBJECT-TYPE
    SYNTAX      OCTET STRING
    MAX-ACCESS  read-write
    STATUS      current
    DESCRIPTION
"
If enabled, ASSP tries to transliterate non-Roman characters in an email it to Roman characters. These transliterations are than additionally used in the bomb checks.
 For example - the (character) sequence '&#24180;&#20809;&#36890;&#20449;&#20135;&#19994;&#20250;&#22238;&#24402;&#39640;&#22686;&#38271;&#36712;&#36947;' will be transliterated to 'Nian Guang Tong Xin Chan Ye Hui Hui Gui Gao Zeng Chang Gui Dao' .
 To transliterate something, use the 'Mail Analyzer'.
 To make this feature working, the Perl module  must be installed.
"
    REFERENCE "Transliterate non-Roman characters in to Roman"
    DEFVAL { "" }
    ::= {RegexFilterSpambomb 99}

syncStatDoTransliterate  OBJECT-TYPE
    SYNTAX      OCTET STRING
    MAX-ACCESS  read-only
    STATUS      current
    DESCRIPTION
"
synchronization status for DoTransliterate
-1 - DoTransliterate could not be synchronized
 0 - synchronization not configured
 1 - out of sync - running master mode
 2 - in sync - running  mastermode
 3 - in sync - running slave mode
 4 - in sync - running master mode (wait to reach state 2)
"
    ::= {DoTransliterate 5}

syncStatStrDoTransliterate  OBJECT-TYPE
    SYNTAX      OCTET STRING
    MAX-ACCESS  read-only
    STATUS      current
    DESCRIPTION
"
synchronization status line from file assp_sync.cfg for DoTransliterate
 0 - synchronization not configured
 1 - out of sync - running master mode
 2 - in sync - running  mastermode
 3 - in sync - running slave mode
 4 - in sync - running master mode (wait to reach state 2)
"
    ::= {DoTransliterate 6}

bombReWL  OBJECT-TYPE
    SYNTAX      OCTET STRING
    MAX-ACCESS  read-write
    STATUS      current
    DESCRIPTION
"

"
    REFERENCE "Do Bomb/Script Regular Expressions Checks for Whitelisted"
    DEFVAL { "" }
    ::= {RegexFilterSpambomb 441}

syncStatbombReWL  OBJECT-TYPE
    SYNTAX      OCTET STRING
    MAX-ACCESS  read-only
    STATUS      current
    DESCRIPTION
"
synchronization status for bombReWL
-1 - bombReWL could not be synchronized
 0 - synchronization not configured
 1 - out of sync - running master mode
 2 - in sync - running  mastermode
 3 - in sync - running slave mode
 4 - in sync - running master mode (wait to reach state 2)
"
    ::= {bombReWL 5}

syncStatStrbombReWL  OBJECT-TYPE
    SYNTAX      OCTET STRING
    MAX-ACCESS  read-only
    STATUS      current
    DESCRIPTION
"
synchronization status line from file assp_sync.cfg for bombReWL
 0 - synchronization not configured
 1 - out of sync - running master mode
 2 - in sync - running  mastermode
 3 - in sync - running slave mode
 4 - in sync - running master mode (wait to reach state 2)
"
    ::= {bombReWL 6}

bombReNP  OBJECT-TYPE
    SYNTAX      OCTET STRING
    MAX-ACCESS  read-write
    STATUS      current
    DESCRIPTION
"

"
    REFERENCE "Do Bomb/Script Regular Expressions Checks for NoProcessing"
    DEFVAL { "" }
    ::= {RegexFilterSpambomb 442}

syncStatbombReNP  OBJECT-TYPE
    SYNTAX      OCTET STRING
    MAX-ACCESS  read-only
    STATUS      current
    DESCRIPTION
"
synchronization status for bombReNP
-1 - bombReNP could not be synchronized
 0 - synchronization not configured
 1 - out of sync - running master mode
 2 - in sync - running  mastermode
 3 - in sync - running slave mode
 4 - in sync - running master mode (wait to reach state 2)
"
    ::= {bombReNP 5}

syncStatStrbombReNP  OBJECT-TYPE
    SYNTAX      OCTET STRING
    MAX-ACCESS  read-only
    STATUS      current
    DESCRIPTION
"
synchronization status line from file assp_sync.cfg for bombReNP
 0 - synchronization not configured
 1 - out of sync - running master mode
 2 - in sync - running  mastermode
 3 - in sync - running slave mode
 4 - in sync - running master mode (wait to reach state 2)
"
    ::= {bombReNP 6}

bombReLocal  OBJECT-TYPE
    SYNTAX      OCTET STRING
    MAX-ACCESS  read-write
    STATUS      current
    DESCRIPTION
"

"
    REFERENCE "Do Bomb/Script Regular Expressions Checks for Local Messages"
    DEFVAL { "" }
    ::= {RegexFilterSpambomb 443}

syncStatbombReLocal  OBJECT-TYPE
    SYNTAX      OCTET STRING
    MAX-ACCESS  read-only
    STATUS      current
    DESCRIPTION
"
synchronization status for bombReLocal
-1 - bombReLocal could not be synchronized
 0 - synchronization not configured
 1 - out of sync - running master mode
 2 - in sync - running  mastermode
 3 - in sync - running slave mode
 4 - in sync - running master mode (wait to reach state 2)
"
    ::= {bombReLocal 5}

syncStatStrbombReLocal  OBJECT-TYPE
    SYNTAX      OCTET STRING
    MAX-ACCESS  read-only
    STATUS      current
    DESCRIPTION
"
synchronization status line from file assp_sync.cfg for bombReLocal
 0 - synchronization not configured
 1 - out of sync - running master mode
 2 - in sync - running  mastermode
 3 - in sync - running slave mode
 4 - in sync - running master mode (wait to reach state 2)
"
    ::= {bombReLocal 6}

bombReISPIP  OBJECT-TYPE
    SYNTAX      OCTET STRING
    MAX-ACCESS  read-write
    STATUS      current
    DESCRIPTION
"

"
    REFERENCE "Do Bomb/Script Regular Expressions Checks for ISPIP"
    DEFVAL { "1" }
    ::= {RegexFilterSpambomb 444}

syncStatbombReISPIP  OBJECT-TYPE
    SYNTAX      OCTET STRING
    MAX-ACCESS  read-only
    STATUS      current
    DESCRIPTION
"
synchronization status for bombReISPIP
-1 - bombReISPIP could not be synchronized
 0 - synchronization not configured
 1 - out of sync - running master mode
 2 - in sync - running  mastermode
 3 - in sync - running slave mode
 4 - in sync - running master mode (wait to reach state 2)
"
    ::= {bombReISPIP 5}

syncStatStrbombReISPIP  OBJECT-TYPE
    SYNTAX      OCTET STRING
    MAX-ACCESS  read-only
    STATUS      current
    DESCRIPTION
"
synchronization status line from file assp_sync.cfg for bombReISPIP
 0 - synchronization not configured
 1 - out of sync - running master mode
 2 - in sync - running  mastermode
 3 - in sync - running slave mode
 4 - in sync - running master mode (wait to reach state 2)
"
    ::= {bombReISPIP 6}

bombMaxPenaltyVal  OBJECT-TYPE
    SYNTAX      OCTET STRING
    MAX-ACCESS  read-write
    STATUS      current
    DESCRIPTION
"
Depending on the configuration, it could be possible that a message gets a very high penalty value on a bomb-check. This value limits the maximum penalty per mail for every single bomb-check that is enabled.
"
    REFERENCE "Maximum Penalty on Bombs per Mail per Check"
    DEFVAL { "70" }
    ::= {RegexFilterSpambomb 445}

syncStatbombMaxPenaltyVal  OBJECT-TYPE
    SYNTAX      OCTET STRING
    MAX-ACCESS  read-only
    STATUS      current
    DESCRIPTION
"
synchronization status for bombMaxPenaltyVal
-1 - bombMaxPenaltyVal could not be synchronized
 0 - synchronization not configured
 1 - out of sync - running master mode
 2 - in sync - running  mastermode
 3 - in sync - running slave mode
 4 - in sync - running master mode (wait to reach state 2)
"
    ::= {bombMaxPenaltyVal 5}

syncStatStrbombMaxPenaltyVal  OBJECT-TYPE
    SYNTAX      OCTET STRING
    MAX-ACCESS  read-only
    STATUS      current
    DESCRIPTION
"
synchronization status line from file assp_sync.cfg for bombMaxPenaltyVal
 0 - synchronization not configured
 1 - out of sync - running master mode
 2 - in sync - running  mastermode
 3 - in sync - running slave mode
 4 - in sync - running master mode (wait to reach state 2)
"
    ::= {bombMaxPenaltyVal 6}

maxBombSearchTime  OBJECT-TYPE
    SYNTAX      OCTET STRING
    MAX-ACCESS  read-write
    STATUS      current
    DESCRIPTION
"
Maximum time in seconds that is spend on every configured bomb check. This time check is done, after every found bomb. So it is possible that the bomb search takes longer as the defined value, if no bomb is found or a single search takes more time. Default is 5.
  
  Even if any of the following bomb parameters is set to 'block', but the sum of the resulting weighted penalty value is less than the corresponding 'Penalty Box Valence Value' (because of lower weights) - only scoring will be done!
  A description of how of weighting regular expressions is done and working, could be found at the bottom this web page.
"
    REFERENCE "Maximum time spend on Bomb Search"
    DEFVAL { "5" }
    ::= {RegexFilterSpambomb 446}

syncStatmaxBombSearchTime  OBJECT-TYPE
    SYNTAX      OCTET STRING
    MAX-ACCESS  read-only
    STATUS      current
    DESCRIPTION
"
synchronization status for maxBombSearchTime
-1 - maxBombSearchTime could not be synchronized
 0 - synchronization not configured
 1 - out of sync - running master mode
 2 - in sync - running  mastermode
 3 - in sync - running slave mode
 4 - in sync - running master mode (wait to reach state 2)
"
    ::= {maxBombSearchTime 5}

syncStatStrmaxBombSearchTime  OBJECT-TYPE
    SYNTAX      OCTET STRING
    MAX-ACCESS  read-only
    STATUS      current
    DESCRIPTION
"
synchronization status line from file assp_sync.cfg for maxBombSearchTime
 0 - synchronization not configured
 1 - out of sync - running master mode
 2 - in sync - running  mastermode
 3 - in sync - running slave mode
 4 - in sync - running master mode (wait to reach state 2)
"
    ::= {maxBombSearchTime 6}

DoBombHeaderRe  OBJECT-TYPE
    SYNTAX      OCTET STRING
    MAX-ACCESS  read-write
    STATUS      current
    DESCRIPTION
"
If activated, each message-header is checked  against bombSenderRe, bombHeaderRe, bombSubjectRe and bombCharSets Regular Expressions. If you use sendAllSpam, be aware that only the header will be shown in the spamcopy.
  The scoring value is the sum of all valences(weights) of all found bombs - bombValencePB .
"
    REFERENCE "Use BombHeader Regular Expressions on Header Part"
    DEFVAL { "1" }
    ::= {RegexFilterSpambomb 447}

syncStatDoBombHeaderRe  OBJECT-TYPE
    SYNTAX      OCTET STRING
    MAX-ACCESS  read-only
    STATUS      current
    DESCRIPTION
"
synchronization status for DoBombHeaderRe
-1 - DoBombHeaderRe could not be synchronized
 0 - synchronization not configured
 1 - out of sync - running master mode
 2 - in sync - running  mastermode
 3 - in sync - running slave mode
 4 - in sync - running master mode (wait to reach state 2)
"
    ::= {DoBombHeaderRe 5}

syncStatStrDoBombHeaderRe  OBJECT-TYPE
    SYNTAX      OCTET STRING
    MAX-ACCESS  read-only
    STATUS      current
    DESCRIPTION
"
synchronization status line from file assp_sync.cfg for DoBombHeaderRe
 0 - synchronization not configured
 1 - out of sync - running master mode
 2 - in sync - running  mastermode
 3 - in sync - running slave mode
 4 - in sync - running master mode (wait to reach state 2)
"
    ::= {DoBombHeaderRe 6}

bombSenderRe  OBJECT-TYPE
    SYNTAX      OCTET STRING
    MAX-ACCESS  read-write
    STATUS      current
    DESCRIPTION
"
Part of DoBombHeaderRe: expression to identify sender (mailfrom,ip,helo).
"
    REFERENCE "Envelope Blocking Regular Expression **"
    DEFVAL { "emailserver3\.com|\d\d\d\d\d\d\@tom\.com" }
    ::= {RegexFilterSpambomb 448}

syncStatbombSenderRe  OBJECT-TYPE
    SYNTAX      OCTET STRING
    MAX-ACCESS  read-only
    STATUS      current
    DESCRIPTION
"
synchronization status for bombSenderRe
-1 - bombSenderRe could not be synchronized
 0 - synchronization not configured
 1 - out of sync - running master mode
 2 - in sync - running  mastermode
 3 - in sync - running slave mode
 4 - in sync - running master mode (wait to reach state 2)
"
    ::= {bombSenderRe 5}

syncStatStrbombSenderRe  OBJECT-TYPE
    SYNTAX      OCTET STRING
    MAX-ACCESS  read-only
    STATUS      current
    DESCRIPTION
"
synchronization status line from file assp_sync.cfg for bombSenderRe
 0 - synchronization not configured
 1 - out of sync - running master mode
 2 - in sync - running  mastermode
 3 - in sync - running slave mode
 4 - in sync - running master mode (wait to reach state 2)
"
    ::= {bombSenderRe 6}

bombHeaderRe  OBJECT-TYPE
    SYNTAX      OCTET STRING
    MAX-ACCESS  read-write
    STATUS      current
    DESCRIPTION
"
Part of DoBombHeaderRe: header will be checked against this Regex if DoBombHeaderRe is enabled. For example file:files/bombheaderre.txt
"
    REFERENCE "Regular Expression to Identify Spam in Header Part**"
    DEFVAL { "file:files/bombheaderre.txt" }
    ::= {RegexFilterSpambomb 449}

syncStatbombHeaderRe  OBJECT-TYPE
    SYNTAX      OCTET STRING
    MAX-ACCESS  read-only
    STATUS      current
    DESCRIPTION
"
synchronization status for bombHeaderRe
-1 - bombHeaderRe could not be synchronized
 0 - synchronization not configured
 1 - out of sync - running master mode
 2 - in sync - running  mastermode
 3 - in sync - running slave mode
 4 - in sync - running master mode (wait to reach state 2)
"
    ::= {bombHeaderRe 5}

syncStatStrbombHeaderRe  OBJECT-TYPE
    SYNTAX      OCTET STRING
    MAX-ACCESS  read-only
    STATUS      current
    DESCRIPTION
"
synchronization status line from file assp_sync.cfg for bombHeaderRe
 0 - synchronization not configured
 1 - out of sync - running master mode
 2 - in sync - running  mastermode
 3 - in sync - running slave mode
 4 - in sync - running master mode (wait to reach state 2)
"
    ::= {bombHeaderRe 6}

bombSubjectRe  OBJECT-TYPE
    SYNTAX      OCTET STRING
    MAX-ACCESS  read-write
    STATUS      current
    DESCRIPTION
"
Part of DoBombHeaderRe : the mail header will be checked against this Regex if DoBombHeaderRe is enabled. If DoBombHeaderRe is enabled, the mail subject will be automaticaly checked against RFC2047 (for NON printable characters in the undecoded MIME content).
"
    REFERENCE "Regular Expression to Identify Spam in Subject**"
    DEFVAL { "" }
    ::= {RegexFilterSpambomb 450}

syncStatbombSubjectRe  OBJECT-TYPE
    SYNTAX      OCTET STRING
    MAX-ACCESS  read-only
    STATUS      current
    DESCRIPTION
"
synchronization status for bombSubjectRe
-1 - bombSubjectRe could not be synchronized
 0 - synchronization not configured
 1 - out of sync - running master mode
 2 - in sync - running  mastermode
 3 - in sync - running slave mode
 4 - in sync - running master mode (wait to reach state 2)
"
    ::= {bombSubjectRe 5}

syncStatStrbombSubjectRe  OBJECT-TYPE
    SYNTAX      OCTET STRING
    MAX-ACCESS  read-only
    STATUS      current
    DESCRIPTION
"
synchronization status line from file assp_sync.cfg for bombSubjectRe
 0 - synchronization not configured
 1 - out of sync - running master mode
 2 - in sync - running  mastermode
 3 - in sync - running slave mode
 4 - in sync - running master mode (wait to reach state 2)
"
    ::= {bombSubjectRe 6}

bombCharSets  OBJECT-TYPE
    SYNTAX      OCTET STRING
    MAX-ACCESS  read-write
    STATUS      current
    DESCRIPTION
"
Part of DoBombHeaderRe: header will be checked against this Regex if DoBombHeaderRe is enabled. The literal UNKNOWN will detect all wrong defined MIME character sets.
  Part of DoBombRe : every MIME-part header will be checked against this Regex if DoBombRe is enabled.
 For example:
 charset=(?:BIG5|CHINESEBIG|GB2312|KS_C_5601|KOI8-R|EUC-KR|ISO-2022-JP|ISO-2022-KR|ISO-2022-CN|CP1251|UNKNOWN). 
"
    REFERENCE "Regular Expression to Identify Foreign Charsets**"
    DEFVAL { "charset=(?:BIG5|CHINESEBIG|GB2312|KS_C_5601|KOI8-R|EUC-KR|ISO-2022-JP|ISO-2022-KR|ISO-2022-CN|CP1251|UNKNOWN)" }
    ::= {RegexFilterSpambomb 451}

syncStatbombCharSets  OBJECT-TYPE
    SYNTAX      OCTET STRING
    MAX-ACCESS  read-only
    STATUS      current
    DESCRIPTION
"
synchronization status for bombCharSets
-1 - bombCharSets could not be synchronized
 0 - synchronization not configured
 1 - out of sync - running master mode
 2 - in sync - running  mastermode
 3 - in sync - running slave mode
 4 - in sync - running master mode (wait to reach state 2)
"
    ::= {bombCharSets 5}

syncStatStrbombCharSets  OBJECT-TYPE
    SYNTAX      OCTET STRING
    MAX-ACCESS  read-only
    STATUS      current
    DESCRIPTION
"
synchronization status line from file assp_sync.cfg for bombCharSets
 0 - synchronization not configured
 1 - out of sync - running master mode
 2 - in sync - running  mastermode
 3 - in sync - running slave mode
 4 - in sync - running master mode (wait to reach state 2)
"
    ::= {bombCharSets 6}

bombHeaderReMaxHits  OBJECT-TYPE
    SYNTAX      OCTET STRING
    MAX-ACCESS  read-write
    STATUS      current
    DESCRIPTION
"
A hit is a found Bomb in header and sender - bombSenderRe , bombHeaderRe , bombSubjectRe , bombCharSets .
  If the number of hits is greater or equal Maximum Hits, the email is flagged Failed (possibly blocked and/or scored).
  If the number of hits is greater 0 and less Maximum Hits, the email is flagged Neutral (possibly scored)
"
    REFERENCE "Maximum Hits for Bombs in Header and Sender"
    DEFVAL { "1" }
    ::= {RegexFilterSpambomb 452}

syncStatbombHeaderReMaxHits  OBJECT-TYPE
    SYNTAX      OCTET STRING
    MAX-ACCESS  read-only
    STATUS      current
    DESCRIPTION
"
synchronization status for bombHeaderReMaxHits
-1 - bombHeaderReMaxHits could not be synchronized
 0 - synchronization not configured
 1 - out of sync - running master mode
 2 - in sync - running  mastermode
 3 - in sync - running slave mode
 4 - in sync - running master mode (wait to reach state 2)
"
    ::= {bombHeaderReMaxHits 5}

syncStatStrbombHeaderReMaxHits  OBJECT-TYPE
    SYNTAX      OCTET STRING
    MAX-ACCESS  read-only
    STATUS      current
    DESCRIPTION
"
synchronization status line from file assp_sync.cfg for bombHeaderReMaxHits
 0 - synchronization not configured
 1 - out of sync - running master mode
 2 - in sync - running  mastermode
 3 - in sync - running slave mode
 4 - in sync - running master mode (wait to reach state 2)
"
    ::= {bombHeaderReMaxHits 6}

DoBombRe  OBJECT-TYPE
    SYNTAX      OCTET STRING
    MAX-ACCESS  read-write
    STATUS      current
    DESCRIPTION
"
If activated, each message is checked  against bombRe and BombData Regular Expressions.
  The scoring value is the sum of all valences(weights) of all found bombs - bombValencePB .
"
    REFERENCE "Use Bomb Regular Expressions"
    DEFVAL { "1" }
    ::= {RegexFilterSpambomb 453}

syncStatDoBombRe  OBJECT-TYPE
    SYNTAX      OCTET STRING
    MAX-ACCESS  read-only
    STATUS      current
    DESCRIPTION
"
synchronization status for DoBombRe
-1 - DoBombRe could not be synchronized
 0 - synchronization not configured
 1 - out of sync - running master mode
 2 - in sync - running  mastermode
 3 - in sync - running slave mode
 4 - in sync - running master mode (wait to reach state 2)
"
    ::= {DoBombRe 5}

syncStatStrDoBombRe  OBJECT-TYPE
    SYNTAX      OCTET STRING
    MAX-ACCESS  read-only
    STATUS      current
    DESCRIPTION
"
synchronization status line from file assp_sync.cfg for DoBombRe
 0 - synchronization not configured
 1 - out of sync - running master mode
 2 - in sync - running  mastermode
 3 - in sync - running slave mode
 4 - in sync - running master mode (wait to reach state 2)
"
    ::= {DoBombRe 6}

bombRe  OBJECT-TYPE
    SYNTAX      OCTET STRING
    MAX-ACCESS  read-write
    STATUS      current
    DESCRIPTION
"
Header and Data will be checked against this Regular Expression if DoBombRe is enabled.  For example:IMG [^&gt;]*src=['&quot;]cid|&lt;BODY[^&gt;]*&gt;(&lt;[^&gt;]+&gt;|\n|\r)*&lt;IMG[^&gt;]+&gt;(&lt;[^&gt;]+&gt;|\n|\r)*&lt;/BODY&gt;
 If you want to search for attachment names, define a line with 'attachment:the_attachment_name'.
"
    REFERENCE "Regular Expression for Header and Data Part**"
    DEFVAL { "file:files/bombre.txt" }
    ::= {RegexFilterSpambomb 454}

syncStatbombRe  OBJECT-TYPE
    SYNTAX      OCTET STRING
    MAX-ACCESS  read-only
    STATUS      current
    DESCRIPTION
"
synchronization status for bombRe
-1 - bombRe could not be synchronized
 0 - synchronization not configured
 1 - out of sync - running master mode
 2 - in sync - running  mastermode
 3 - in sync - running slave mode
 4 - in sync - running master mode (wait to reach state 2)
"
    ::= {bombRe 5}

syncStatStrbombRe  OBJECT-TYPE
    SYNTAX      OCTET STRING
    MAX-ACCESS  read-only
    STATUS      current
    DESCRIPTION
"
synchronization status line from file assp_sync.cfg for bombRe
 0 - synchronization not configured
 1 - out of sync - running master mode
 2 - in sync - running  mastermode
 3 - in sync - running slave mode
 4 - in sync - running master mode (wait to reach state 2)
"
    ::= {bombRe 6}

bombReMaxHits  OBJECT-TYPE
    SYNTAX      OCTET STRING
    MAX-ACCESS  read-write
    STATUS      current
    DESCRIPTION
"
A hit is a found Bomb in header and data - bombRe .
  If the number of hits is greater or equal Maximum Hits, the email is flagged Failed (possibly blocked and/or scored).
  If the number of hits is greater 0 and less Maximum Hits, the email is flagged Neutral (possibly scored)
"
    REFERENCE "Maximum Hits for Bombs in Header and Data"
    DEFVAL { "1" }
    ::= {RegexFilterSpambomb 455}

syncStatbombReMaxHits  OBJECT-TYPE
    SYNTAX      OCTET STRING
    MAX-ACCESS  read-only
    STATUS      current
    DESCRIPTION
"
synchronization status for bombReMaxHits
-1 - bombReMaxHits could not be synchronized
 0 - synchronization not configured
 1 - out of sync - running master mode
 2 - in sync - running  mastermode
 3 - in sync - running slave mode
 4 - in sync - running master mode (wait to reach state 2)
"
    ::= {bombReMaxHits 5}

syncStatStrbombReMaxHits  OBJECT-TYPE
    SYNTAX      OCTET STRING
    MAX-ACCESS  read-only
    STATUS      current
    DESCRIPTION
"
synchronization status line from file assp_sync.cfg for bombReMaxHits
 0 - synchronization not configured
 1 - out of sync - running master mode
 2 - in sync - running  mastermode
 3 - in sync - running slave mode
 4 - in sync - running master mode (wait to reach state 2)
"
    ::= {bombReMaxHits 6}

bombDataRe  OBJECT-TYPE
    SYNTAX      OCTET STRING
    MAX-ACCESS  read-write
    STATUS      current
    DESCRIPTION
"
Data part will be checked against the Regular Expression  if DoBombRe is enabled. For example:IMG [^&gt;]*src=['&quot;]cid|&lt;BODY[^&gt;]*&gt;(&lt;[^&gt;]+&gt;|\n|\r)*&lt;IMG[^&gt;]+&gt;(&lt;[^&gt;]+&gt;|\n|\r)*&lt;/BODY&gt;
  If you want to search for attachment names, define a line with 'attachment:the_attachment_name'.
"
    REFERENCE "BombData Regular Expression for Data Part**"
    DEFVAL { "" }
    ::= {RegexFilterSpambomb 456}

syncStatbombDataRe  OBJECT-TYPE
    SYNTAX      OCTET STRING
    MAX-ACCESS  read-only
    STATUS      current
    DESCRIPTION
"
synchronization status for bombDataRe
-1 - bombDataRe could not be synchronized
 0 - synchronization not configured
 1 - out of sync - running master mode
 2 - in sync - running  mastermode
 3 - in sync - running slave mode
 4 - in sync - running master mode (wait to reach state 2)
"
    ::= {bombDataRe 5}

syncStatStrbombDataRe  OBJECT-TYPE
    SYNTAX      OCTET STRING
    MAX-ACCESS  read-only
    STATUS      current
    DESCRIPTION
"
synchronization status line from file assp_sync.cfg for bombDataRe
 0 - synchronization not configured
 1 - out of sync - running master mode
 2 - in sync - running  mastermode
 3 - in sync - running slave mode
 4 - in sync - running master mode (wait to reach state 2)
"
    ::= {bombDataRe 6}

bombDataReMaxHits  OBJECT-TYPE
    SYNTAX      OCTET STRING
    MAX-ACCESS  read-write
    STATUS      current
    DESCRIPTION
"
A hit is a found Bomb in data - bombDataRe .
  If the number of hits is greater or equal Maximum Hits, the email is flagged Failed (possibly blocked and/or scored).
  If the number of hits is greater 0 and less Maximum Hits, the email is flagged Neutral (possibly scored)
"
    REFERENCE "Maximum Hits for Bombs in Data"
    DEFVAL { "1" }
    ::= {RegexFilterSpambomb 457}

syncStatbombDataReMaxHits  OBJECT-TYPE
    SYNTAX      OCTET STRING
    MAX-ACCESS  read-only
    STATUS      current
    DESCRIPTION
"
synchronization status for bombDataReMaxHits
-1 - bombDataReMaxHits could not be synchronized
 0 - synchronization not configured
 1 - out of sync - running master mode
 2 - in sync - running  mastermode
 3 - in sync - running slave mode
 4 - in sync - running master mode (wait to reach state 2)
"
    ::= {bombDataReMaxHits 5}

syncStatStrbombDataReMaxHits  OBJECT-TYPE
    SYNTAX      OCTET STRING
    MAX-ACCESS  read-only
    STATUS      current
    DESCRIPTION
"
synchronization status line from file assp_sync.cfg for bombDataReMaxHits
 0 - synchronization not configured
 1 - out of sync - running master mode
 2 - in sync - running  mastermode
 3 - in sync - running slave mode
 4 - in sync - running master mode (wait to reach state 2)
"
    ::= {bombDataReMaxHits 6}

bombSuspiciousRe  OBJECT-TYPE
    SYNTAX      OCTET STRING
    MAX-ACCESS  read-write
    STATUS      current
    DESCRIPTION
"
Sender, Header and Data will be checked for scoring only. Put here anything which might be suspicious. bombSuspiciousValencePB will be used to increase the score. For example:unsubscribe
"
    REFERENCE "Suspicious Expression for Scoring Only**"
    DEFVAL { "" }
    ::= {RegexFilterSpambomb 458}

syncStatbombSuspiciousRe  OBJECT-TYPE
    SYNTAX      OCTET STRING
    MAX-ACCESS  read-only
    STATUS      current
    DESCRIPTION
"
synchronization status for bombSuspiciousRe
-1 - bombSuspiciousRe could not be synchronized
 0 - synchronization not configured
 1 - out of sync - running master mode
 2 - in sync - running  mastermode
 3 - in sync - running slave mode
 4 - in sync - running master mode (wait to reach state 2)
"
    ::= {bombSuspiciousRe 5}

syncStatStrbombSuspiciousRe  OBJECT-TYPE
    SYNTAX      OCTET STRING
    MAX-ACCESS  read-only
    STATUS      current
    DESCRIPTION
"
synchronization status line from file assp_sync.cfg for bombSuspiciousRe
 0 - synchronization not configured
 1 - out of sync - running master mode
 2 - in sync - running  mastermode
 3 - in sync - running slave mode
 4 - in sync - running master mode (wait to reach state 2)
"
    ::= {bombSuspiciousRe 6}

noBombScript  OBJECT-TYPE
    SYNTAX      OCTET STRING
    MAX-ACCESS  read-write
    STATUS      current
    DESCRIPTION
"
Don't detect spam bombs or scripts in messages from these addresses. Accepts specific addresses (user@domain.com), user parts (user) or entire domains (@domain.com).
"
    REFERENCE "Don't Check Messages from these Addresses*"
    DEFVAL { "" }
    ::= {RegexFilterSpambomb 459}

syncStatnoBombScript  OBJECT-TYPE
    SYNTAX      OCTET STRING
    MAX-ACCESS  read-only
    STATUS      current
    DESCRIPTION
"
synchronization status for noBombScript
-1 - noBombScript could not be synchronized
 0 - synchronization not configured
 1 - out of sync - running master mode
 2 - in sync - running  mastermode
 3 - in sync - running slave mode
 4 - in sync - running master mode (wait to reach state 2)
"
    ::= {noBombScript 5}

syncStatStrnoBombScript  OBJECT-TYPE
    SYNTAX      OCTET STRING
    MAX-ACCESS  read-only
    STATUS      current
    DESCRIPTION
"
synchronization status line from file assp_sync.cfg for noBombScript
 0 - synchronization not configured
 1 - out of sync - running master mode
 2 - in sync - running  mastermode
 3 - in sync - running slave mode
 4 - in sync - running master mode (wait to reach state 2)
"
    ::= {noBombScript 6}

DoTestRe  OBJECT-TYPE
    SYNTAX      OCTET STRING
    MAX-ACCESS  read-write
    STATUS      current
    DESCRIPTION
"
If activated, each message is checked  against the Test Regular Expression below. This provides a way to test regex strings on live mail.
"
    REFERENCE "Do Test Regular Expression"
    DEFVAL { "0" }
    ::= {RegexFilterSpambomb 460}

syncStatDoTestRe  OBJECT-TYPE
    SYNTAX      OCTET STRING
    MAX-ACCESS  read-only
    STATUS      current
    DESCRIPTION
"
synchronization status for DoTestRe
-1 - DoTestRe could not be synchronized
 0 - synchronization not configured
 1 - out of sync - running master mode
 2 - in sync - running  mastermode
 3 - in sync - running slave mode
 4 - in sync - running master mode (wait to reach state 2)
"
    ::= {DoTestRe 5}

syncStatStrDoTestRe  OBJECT-TYPE
    SYNTAX      OCTET STRING
    MAX-ACCESS  read-only
    STATUS      current
    DESCRIPTION
"
synchronization status line from file assp_sync.cfg for DoTestRe
 0 - synchronization not configured
 1 - out of sync - running master mode
 2 - in sync - running  mastermode
 3 - in sync - running slave mode
 4 - in sync - running master mode (wait to reach state 2)
"
    ::= {DoTestRe 6}

testRe  OBJECT-TYPE
    SYNTAX      OCTET STRING
    MAX-ACCESS  read-write
    STATUS      current
    DESCRIPTION
"
Use this to test your regular expressions. Test valence is teValencePB .
"
    REFERENCE "Test Regular Expression**"
    DEFVAL { "" }
    ::= {RegexFilterSpambomb 461}

syncStattestRe  OBJECT-TYPE
    SYNTAX      OCTET STRING
    MAX-ACCESS  read-only
    STATUS      current
    DESCRIPTION
"
synchronization status for testRe
-1 - testRe could not be synchronized
 0 - synchronization not configured
 1 - out of sync - running master mode
 2 - in sync - running  mastermode
 3 - in sync - running slave mode
 4 - in sync - running master mode (wait to reach state 2)
"
    ::= {testRe 5}

syncStatStrtestRe  OBJECT-TYPE
    SYNTAX      OCTET STRING
    MAX-ACCESS  read-only
    STATUS      current
    DESCRIPTION
"
synchronization status line from file assp_sync.cfg for testRe
 0 - synchronization not configured
 1 - out of sync - running master mode
 2 - in sync - running  mastermode
 3 - in sync - running slave mode
 4 - in sync - running master mode (wait to reach state 2)
"
    ::= {testRe 6}

bombError  OBJECT-TYPE
    SYNTAX      OCTET STRING
    MAX-ACCESS  read-write
    STATUS      current
    DESCRIPTION
"
SMTP error message to reject spam bombs. For example: 554 5.7.1 Delivery not authorized, message refused -- send report to mailto:postmaster@mydomain.tld or call +12.34.56.78.90
"
    REFERENCE "Spam Bomb Error"
    DEFVAL { "554 5.7.1 Delivery not authorized, message refused -- ." }
    ::= {RegexFilterSpambomb 462}

syncStatbombError  OBJECT-TYPE
    SYNTAX      OCTET STRING
    MAX-ACCESS  read-only
    STATUS      current
    DESCRIPTION
"
synchronization status for bombError
-1 - bombError could not be synchronized
 0 - synchronization not configured
 1 - out of sync - running master mode
 2 - in sync - running  mastermode
 3 - in sync - running slave mode
 4 - in sync - running master mode (wait to reach state 2)
"
    ::= {bombError 5}

syncStatStrbombError  OBJECT-TYPE
    SYNTAX      OCTET STRING
    MAX-ACCESS  read-only
    STATUS      current
    DESCRIPTION
"
synchronization status line from file assp_sync.cfg for bombError
 0 - synchronization not configured
 1 - out of sync - running master mode
 2 - in sync - running  mastermode
 3 - in sync - running slave mode
 4 - in sync - running master mode (wait to reach state 2)
"
    ::= {bombError 6}

bombErrorReason  OBJECT-TYPE
    SYNTAX      OCTET STRING
    MAX-ACCESS  read-write
    STATUS      current
    DESCRIPTION
"
Add matching expression to Spam Bomb Error
"
    REFERENCE "Add Reason"
    DEFVAL { "1" }
    ::= {RegexFilterSpambomb 463}

syncStatbombErrorReason  OBJECT-TYPE
    SYNTAX      OCTET STRING
    MAX-ACCESS  read-only
    STATUS      current
    DESCRIPTION
"
synchronization status for bombErrorReason
-1 - bombErrorReason could not be synchronized
 0 - synchronization not configured
 1 - out of sync - running master mode
 2 - in sync - running  mastermode
 3 - in sync - running slave mode
 4 - in sync - running master mode (wait to reach state 2)
"
    ::= {bombErrorReason 5}

syncStatStrbombErrorReason  OBJECT-TYPE
    SYNTAX      OCTET STRING
    MAX-ACCESS  read-only
    STATUS      current
    DESCRIPTION
"
synchronization status line from file assp_sync.cfg for bombErrorReason
 0 - synchronization not configured
 1 - out of sync - running master mode
 2 - in sync - running  mastermode
 3 - in sync - running slave mode
 4 - in sync - running master mode (wait to reach state 2)
"
    ::= {bombErrorReason 6}

DoBlackRe  OBJECT-TYPE
    SYNTAX      OCTET STRING
    MAX-ACCESS  read-write
    STATUS      current
    DESCRIPTION
"
Each incoming message is checked  against the BlackRe to Identify Spams. No Optout. 
  The scoring value is the sum of all valences(weights) of all found bombs - blackValencePB .
"
    REFERENCE "Use Black Regular Expression to Identify Spam Strictly"
    DEFVAL { "0" }
    ::= {RegexFilterSpambomb 464}

syncStatDoBlackRe  OBJECT-TYPE
    SYNTAX      OCTET STRING
    MAX-ACCESS  read-only
    STATUS      current
    DESCRIPTION
"
synchronization status for DoBlackRe
-1 - DoBlackRe could not be synchronized
 0 - synchronization not configured
 1 - out of sync - running master mode
 2 - in sync - running  mastermode
 3 - in sync - running slave mode
 4 - in sync - running master mode (wait to reach state 2)
"
    ::= {DoBlackRe 5}

syncStatStrDoBlackRe  OBJECT-TYPE
    SYNTAX      OCTET STRING
    MAX-ACCESS  read-only
    STATUS      current
    DESCRIPTION
"
synchronization status line from file assp_sync.cfg for DoBlackRe
 0 - synchronization not configured
 1 - out of sync - running master mode
 2 - in sync - running  mastermode
 3 - in sync - running slave mode
 4 - in sync - running master mode (wait to reach state 2)
"
    ::= {DoBlackRe 6}

blackRe  OBJECT-TYPE
    SYNTAX      OCTET STRING
    MAX-ACCESS  read-write
    STATUS      current
    DESCRIPTION
"
If an incoming email matches this Perl regular expression it will be strictly considered spam . For example: \breplica watches\b|\bMegaDik\b|\bcock\b|\bpenis\b|\bpills\b|\bOriginal Viagra\b|\bbetter sex life\b|\baverage penis\b|\benlargement\b|\borgasm\b|\berections\b|\bViagra\b|\bbig dick\b|\bsperma\b|\bSexual\b|\bErectionsk\b|\bStamina\b|\bsildenafil\b|\bcitrate\b|\bErectile\b
"
    REFERENCE "BlackRe - Regular Expression to Identify Spam Strictly**"
    DEFVAL { "file:files/blackre.txt" }
    ::= {RegexFilterSpambomb 465}

syncStatblackRe  OBJECT-TYPE
    SYNTAX      OCTET STRING
    MAX-ACCESS  read-only
    STATUS      current
    DESCRIPTION
"
synchronization status for blackRe
-1 - blackRe could not be synchronized
 0 - synchronization not configured
 1 - out of sync - running master mode
 2 - in sync - running  mastermode
 3 - in sync - running slave mode
 4 - in sync - running master mode (wait to reach state 2)
"
    ::= {blackRe 5}

syncStatStrblackRe  OBJECT-TYPE
    SYNTAX      OCTET STRING
    MAX-ACCESS  read-only
    STATUS      current
    DESCRIPTION
"
synchronization status line from file assp_sync.cfg for blackRe
 0 - synchronization not configured
 1 - out of sync - running master mode
 2 - in sync - running  mastermode
 3 - in sync - running slave mode
 4 - in sync - running master mode (wait to reach state 2)
"
    ::= {blackRe 6}

blackReMaxHits  OBJECT-TYPE
    SYNTAX      OCTET STRING
    MAX-ACCESS  read-write
    STATUS      current
    DESCRIPTION
"
A hit is a found Bomb for Identify Spam Strictly. - blackRe 
  If the number of hits is greater or equal Maximum Hits, the email is flagged Failed (possibly blocked and/or scored).
  If the number of hits is greater 0 and less Maximum Hits, the email is flagged Neutral (possibly scored)
"
    REFERENCE "Maximum Hits for Identify Spam Strictly"
    DEFVAL { "1" }
    ::= {RegexFilterSpambomb 466}

syncStatblackReMaxHits  OBJECT-TYPE
    SYNTAX      OCTET STRING
    MAX-ACCESS  read-only
    STATUS      current
    DESCRIPTION
"
synchronization status for blackReMaxHits
-1 - blackReMaxHits could not be synchronized
 0 - synchronization not configured
 1 - out of sync - running master mode
 2 - in sync - running  mastermode
 3 - in sync - running slave mode
 4 - in sync - running master mode (wait to reach state 2)
"
    ::= {blackReMaxHits 5}

syncStatStrblackReMaxHits  OBJECT-TYPE
    SYNTAX      OCTET STRING
    MAX-ACCESS  read-only
    STATUS      current
    DESCRIPTION
"
synchronization status line from file assp_sync.cfg for blackReMaxHits
 0 - synchronization not configured
 1 - out of sync - running master mode
 2 - in sync - running  mastermode
 3 - in sync - running slave mode
 4 - in sync - running master mode (wait to reach state 2)
"
    ::= {blackReMaxHits 6}

DoScriptRe  OBJECT-TYPE
    SYNTAX      OCTET STRING
    MAX-ACCESS  read-write
    STATUS      current
    DESCRIPTION
"
Each message is checked  against the Expression to Identify Mobile Scripts.
  The scoring value is the sum of all valences(weights) of all found bombs - scriptValencePB .
"
    REFERENCE "Use Regular Expression to Identify Mobile Scripts"
    DEFVAL { "0" }
    ::= {RegexFilterSpambomb 467}

syncStatDoScriptRe  OBJECT-TYPE
    SYNTAX      OCTET STRING
    MAX-ACCESS  read-only
    STATUS      current
    DESCRIPTION
"
synchronization status for DoScriptRe
-1 - DoScriptRe could not be synchronized
 0 - synchronization not configured
 1 - out of sync - running master mode
 2 - in sync - running  mastermode
 3 - in sync - running slave mode
 4 - in sync - running master mode (wait to reach state 2)
"
    ::= {DoScriptRe 5}

syncStatStrDoScriptRe  OBJECT-TYPE
    SYNTAX      OCTET STRING
    MAX-ACCESS  read-only
    STATUS      current
    DESCRIPTION
"
synchronization status line from file assp_sync.cfg for DoScriptRe
 0 - synchronization not configured
 1 - out of sync - running master mode
 2 - in sync - running  mastermode
 3 - in sync - running slave mode
 4 - in sync - running master mode (wait to reach state 2)
"
    ::= {DoScriptRe 6}

scriptRe  OBJECT-TYPE
    SYNTAX      OCTET STRING
    MAX-ACCESS  read-write
    STATUS      current
    DESCRIPTION
"
Spam mails may contain mobile scripting code, eg activex and java or php. You can use this feature to block those messages.
  Leave this blank to disable the feature. For example: \&lt;applet|\&lt;embed|\&lt;iframe|\&lt;object|\&lt;script|\&lt;?php|onmouseover|onload|onfocus|onblure|onclick|javascript:
"
    REFERENCE "Regular Expression to Identify Mobile Scripts**"
    DEFVAL { "" }
    ::= {RegexFilterSpambomb 468}

syncStatscriptRe  OBJECT-TYPE
    SYNTAX      OCTET STRING
    MAX-ACCESS  read-only
    STATUS      current
    DESCRIPTION
"
synchronization status for scriptRe
-1 - scriptRe could not be synchronized
 0 - synchronization not configured
 1 - out of sync - running master mode
 2 - in sync - running  mastermode
 3 - in sync - running slave mode
 4 - in sync - running master mode (wait to reach state 2)
"
    ::= {scriptRe 5}

syncStatStrscriptRe  OBJECT-TYPE
    SYNTAX      OCTET STRING
    MAX-ACCESS  read-only
    STATUS      current
    DESCRIPTION
"
synchronization status line from file assp_sync.cfg for scriptRe
 0 - synchronization not configured
 1 - out of sync - running master mode
 2 - in sync - running  mastermode
 3 - in sync - running slave mode
 4 - in sync - running master mode (wait to reach state 2)
"
    ::= {scriptRe 6}

scriptReMaxHits  OBJECT-TYPE
    SYNTAX      OCTET STRING
    MAX-ACCESS  read-write
    STATUS      current
    DESCRIPTION
"
A hit is a found mobile scripting code for Identify Mobile Scripts - scriptRe .
  If the number of hits is greater or equal Maximum Hits, the email is flagged Failed (possibly blocked and/or scored).
  If the number of hits is greater 0 and less Maximum Hits, the email is flagged Neutral (possibly scored)
"
    REFERENCE "Maximum Hits for Identify Mobile Scripts"
    DEFVAL { "1" }
    ::= {RegexFilterSpambomb 469}

syncStatscriptReMaxHits  OBJECT-TYPE
    SYNTAX      OCTET STRING
    MAX-ACCESS  read-only
    STATUS      current
    DESCRIPTION
"
synchronization status for scriptReMaxHits
-1 - scriptReMaxHits could not be synchronized
 0 - synchronization not configured
 1 - out of sync - running master mode
 2 - in sync - running  mastermode
 3 - in sync - running slave mode
 4 - in sync - running master mode (wait to reach state 2)
"
    ::= {scriptReMaxHits 5}

syncStatStrscriptReMaxHits  OBJECT-TYPE
    SYNTAX      OCTET STRING
    MAX-ACCESS  read-only
    STATUS      current
    DESCRIPTION
"
synchronization status line from file assp_sync.cfg for scriptReMaxHits
 0 - synchronization not configured
 1 - out of sync - running master mode
 2 - in sync - running  mastermode
 3 - in sync - running slave mode
 4 - in sync - running master mode (wait to reach state 2)
"
    ::= {scriptReMaxHits 6}

scriptError  OBJECT-TYPE
    SYNTAX      OCTET STRING
    MAX-ACCESS  read-write
    STATUS      current
    DESCRIPTION
"
SMTP error message to reject scripts. For example: 554 5.7.1 Your email appears to be spam -- send an error report to mailto:postmaster@mydomain.tld or call +12.34.56.78.90
  
"
    REFERENCE "Script Error"
    DEFVAL { "554 5.7.1 Your email contains html scripting code -- please resend as plain text." }
    ::= {RegexFilterSpambomb 470}

syncStatscriptError  OBJECT-TYPE
    SYNTAX      OCTET STRING
    MAX-ACCESS  read-only
    STATUS      current
    DESCRIPTION
"
synchronization status for scriptError
-1 - scriptError could not be synchronized
 0 - synchronization not configured
 1 - out of sync - running master mode
 2 - in sync - running  mastermode
 3 - in sync - running slave mode
 4 - in sync - running master mode (wait to reach state 2)
"
    ::= {scriptError 5}

syncStatStrscriptError  OBJECT-TYPE
    SYNTAX      OCTET STRING
    MAX-ACCESS  read-only
    STATUS      current
    DESCRIPTION
"
synchronization status line from file assp_sync.cfg for scriptError
 0 - synchronization not configured
 1 - out of sync - running master mode
 2 - in sync - running  mastermode
 3 - in sync - running slave mode
 4 - in sync - running master mode (wait to reach state 2)
"
    ::= {scriptError 6}

preHeaderRe  OBJECT-TYPE
    SYNTAX      OCTET STRING
    MAX-ACCESS  read-write
    STATUS      current
    DESCRIPTION
"
Until the complete mail header is received, assp is processing the handshake and header content line per line, but the first mail content check is done after the complete mail header is received.
 It is possible, that some content (malformed headers, forbidden characters or character combinations) could cause assp to die or to run in to a unrecoverable exception.
 Use this regular expression to identify such incoming mails based on a line per line check, at the moment where a single line is received.
 This setting does not affect any other and is not affected by any other configuration setting, except that this check is only done for incoming mails.
 If a match is found, assp will immediately send a '421 <myName> closing transmission' reply to the client and will immediately terminate the connection.
  Default setting is file:files/preheaderre.txt
"
    REFERENCE "Regular Expression to early Identify Spam in Handshake and Header Part*"
    DEFVAL { "file:files/preheaderre.txt" }
    ::= {RegexFilterSpambomb 889}

syncStatpreHeaderRe  OBJECT-TYPE
    SYNTAX      OCTET STRING
    MAX-ACCESS  read-only
    STATUS      current
    DESCRIPTION
"
synchronization status for preHeaderRe
-1 - preHeaderRe could not be synchronized
 0 - synchronization not configured
 1 - out of sync - running master mode
 2 - in sync - running  mastermode
 3 - in sync - running slave mode
 4 - in sync - running master mode (wait to reach state 2)
"
    ::= {preHeaderRe 5}

syncStatStrpreHeaderRe  OBJECT-TYPE
    SYNTAX      OCTET STRING
    MAX-ACCESS  read-only
    STATUS      current
    DESCRIPTION
"
synchronization status line from file assp_sync.cfg for preHeaderRe
 0 - synchronization not configured
 1 - out of sync - running master mode
 2 - in sync - running  mastermode
 3 - in sync - running slave mode
 4 - in sync - running master mode (wait to reach state 2)
"
    ::= {preHeaderRe 6}

maxSubjectLength  OBJECT-TYPE
    SYNTAX      OCTET STRING
    MAX-ACCESS  read-write
    STATUS      current
    DESCRIPTION
"
If set to a value greater than 0, assp will check the length of the Subject of the mail. If the Subject length exceeds this value, the message score will be increased by 'bombValencePB' and the string that is checked in 'bombSubjectRe' will be trunked to this length. It is possible to define a special weight using the syntax 'length=>value', in this case the defined absolute value will be used instead of 'bombValencePB' to increase the message score. If the subject is too long and this weight is equal or higher than 'bombMaxPenaltyVal' no further bomb checks will be done on the subject.
"
    REFERENCE "Maximum allowed Subject Length"
    DEFVAL { "200=>100" }
    ::= {RegexFilterSpambomb 936}

syncStatmaxSubjectLength  OBJECT-TYPE
    SYNTAX      OCTET STRING
    MAX-ACCESS  read-only
    STATUS      current
    DESCRIPTION
"
synchronization status for maxSubjectLength
-1 - maxSubjectLength could not be synchronized
 0 - synchronization not configured
 1 - out of sync - running master mode
 2 - in sync - running  mastermode
 3 - in sync - running slave mode
 4 - in sync - running master mode (wait to reach state 2)
"
    ::= {maxSubjectLength 5}

syncStatStrmaxSubjectLength  OBJECT-TYPE
    SYNTAX      OCTET STRING
    MAX-ACCESS  read-only
    STATUS      current
    DESCRIPTION
"
synchronization status line from file assp_sync.cfg for maxSubjectLength
 0 - synchronization not configured
 1 - out of sync - running master mode
 2 - in sync - running  mastermode
 3 - in sync - running slave mode
 4 - in sync - running master mode (wait to reach state 2)
"
    ::= {maxSubjectLength 6}

AllowInternalsInRegex  OBJECT-TYPE
    SYNTAX      OCTET STRING
    MAX-ACCESS  read-write
    STATUS      current
    DESCRIPTION
"
Allow internal variables to be used in regular expressions - replaces something like \${$EmailDomainRe} with the value of $EmailDomainRe
"
    REFERENCE "Allow Internal Variables in Regex"
    DEFVAL { "" }
    ::= {RegexFilterSpambomb 977}

syncStatAllowInternalsInRegex  OBJECT-TYPE
    SYNTAX      OCTET STRING
    MAX-ACCESS  read-only
    STATUS      current
    DESCRIPTION
"
synchronization status for AllowInternalsInRegex
-1 - AllowInternalsInRegex could not be synchronized
 0 - synchronization not configured
 1 - out of sync - running master mode
 2 - in sync - running  mastermode
 3 - in sync - running slave mode
 4 - in sync - running master mode (wait to reach state 2)
"
    ::= {AllowInternalsInRegex 5}

syncStatStrAllowInternalsInRegex  OBJECT-TYPE
    SYNTAX      OCTET STRING
    MAX-ACCESS  read-only
    STATUS      current
    DESCRIPTION
"
synchronization status line from file assp_sync.cfg for AllowInternalsInRegex
 0 - synchronization not configured
 1 - out of sync - running master mode
 2 - in sync - running  mastermode
 3 - in sync - running slave mode
 4 - in sync - running master mode (wait to reach state 2)
"
    ::= {AllowInternalsInRegex 6}

bombSkipHeaderTagRe  OBJECT-TYPE
    SYNTAX      OCTET STRING
    MAX-ACCESS  read-write
    STATUS      current
    DESCRIPTION
"
Regular Expression to define header tags, that will be skipped for bombSuspiciousRe, bombHeaderRe, bombRe and blackRe - like 'DKIM-Signature|Domainkey-Signature' - the always followed collon (:) is added by assp. For example file:files/bombskipheadertagre.txt
"
    REFERENCE "Regular Expression to Identify skipped Tags in Header Part*"
    DEFVAL { "file:files/bombskipheadertagre.txt" }
    ::= {RegexFilterSpambomb 998}

syncStatbombSkipHeaderTagRe  OBJECT-TYPE
    SYNTAX      OCTET STRING
    MAX-ACCESS  read-only
    STATUS      current
    DESCRIPTION
"
synchronization status for bombSkipHeaderTagRe
-1 - bombSkipHeaderTagRe could not be synchronized
 0 - synchronization not configured
 1 - out of sync - running master mode
 2 - in sync - running  mastermode
 3 - in sync - running slave mode
 4 - in sync - running master mode (wait to reach state 2)
"
    ::= {bombSkipHeaderTagRe 5}

syncStatStrbombSkipHeaderTagRe  OBJECT-TYPE
    SYNTAX      OCTET STRING
    MAX-ACCESS  read-only
    STATUS      current
    DESCRIPTION
"
synchronization status line from file assp_sync.cfg for bombSkipHeaderTagRe
 0 - synchronization not configured
 1 - out of sync - running master mode
 2 - in sync - running  mastermode
 3 - in sync - running slave mode
 4 - in sync - running master mode (wait to reach state 2)
"
    ::= {bombSkipHeaderTagRe 6}

BayesianandHiddenMarkovModelHMMOptions  OBJECT IDENTIFIER ::= {asspConfig 23}
DoHMM  OBJECT-TYPE
    SYNTAX      OCTET STRING
    MAX-ACCESS  read-write
    STATUS      current
    DESCRIPTION
"
If activated, the message is checked based on a   for global and private entries.  Private HMM entries have a five times higher weight than global entries. This needs a fully functional HMMdb database built by rebuildspamdb. For starters it is best practice to put this in monitoring mode and build the HMM collection with the help of DSNBL ,URIBL and spamaddresses. Scoring is done with HMMValencePB for external mails, HMMlocalValencePB is used for outgoing and internal mails - both values are multiplied with the detected hmmProbability. It is possible to score (in and out) with a bonus for HAM with HMMhamValencePB ( HMMhamValencePB * ( 1 - baysProbability )).
  The perl module  version 0.34 or higher and BerkeleyDB version 4.5 or higher is required (to store temporary data) to use this feature and 'useBerkeleyDB' must be set to ON.
  If this option is disabled, the rebuildspamdb task will NOT build a valid HMM database!
  Compared to the Bayesian option, the Hidden Markov Model will produce results that are much more exact. How ever, it is possible, that HMM gets no result on very small messages, for this reason it is recommended to use both Bayesian and HMM. If you enable both checks, check your settings for baysValencePB, HMMValencePB, bayslocalValencePB and HMMlocalValencePB - eg. divide them by 2. or set the bayes values to 1/3 and the HMM values to 2/3.
  NOTICE that using this option requires a very fast database server behind, if HMMusesBDB is set to OFF. The Bayesian- and HMM check together can produce 4000 and much more SQL querys per second.
  Keep in mind, that all backups and exports of the HMM database could require several 100MB of diskspace, if the file count in the corpus is very large.
"
    REFERENCE "Hidden Markov Model Check "
    DEFVAL { "0" }
    ::= {BayesianandHiddenMarkovModelHMMOptions 123}

syncStatDoHMM  OBJECT-TYPE
    SYNTAX      OCTET STRING
    MAX-ACCESS  read-only
    STATUS      current
    DESCRIPTION
"
synchronization status for DoHMM
-1 - DoHMM could not be synchronized
 0 - synchronization not configured
 1 - out of sync - running master mode
 2 - in sync - running  mastermode
 3 - in sync - running slave mode
 4 - in sync - running master mode (wait to reach state 2)
"
    ::= {DoHMM 5}

syncStatStrDoHMM  OBJECT-TYPE
    SYNTAX      OCTET STRING
    MAX-ACCESS  read-only
    STATUS      current
    DESCRIPTION
"
synchronization status line from file assp_sync.cfg for DoHMM
 0 - synchronization not configured
 1 - out of sync - running master mode
 2 - in sync - running  mastermode
 3 - in sync - running slave mode
 4 - in sync - running master mode (wait to reach state 2)
"
    ::= {DoHMM 6}

HMMusesBDB  OBJECT-TYPE
    SYNTAX      OCTET STRING
    MAX-ACCESS  read-write
    STATUS      current
    DESCRIPTION
"
If enabled (default), the Hidden Markov Model database uses BerkeleyDB - notice: in this case no database import, backup or export are provided for the HMMdb. This value is completely ignored, if DBdriver is set to 'BerkeleyDB' and spamdb is set to 'DB:'. Switch this parameter to OFF, if you want to use the same database engine for the HMMdb like spamdb is configured. 
  Changing this value requires a restart of assp. Possibly a forced rebuildspamdb is required after the restart.
"
    REFERENCE "Use BerkeleyDB for the Hidden Markov Model database"
    DEFVAL { "1" }
    ::= {BayesianandHiddenMarkovModelHMMOptions 124}

syncStatHMMusesBDB  OBJECT-TYPE
    SYNTAX      OCTET STRING
    MAX-ACCESS  read-only
    STATUS      current
    DESCRIPTION
"
synchronization status for HMMusesBDB
-1 - HMMusesBDB could not be synchronized
 0 - synchronization not configured
 1 - out of sync - running master mode
 2 - in sync - running  mastermode
 3 - in sync - running slave mode
 4 - in sync - running master mode (wait to reach state 2)
"
    ::= {HMMusesBDB 5}

syncStatStrHMMusesBDB  OBJECT-TYPE
    SYNTAX      OCTET STRING
    MAX-ACCESS  read-only
    STATUS      current
    DESCRIPTION
"
synchronization status line from file assp_sync.cfg for HMMusesBDB
 0 - synchronization not configured
 1 - out of sync - running master mode
 2 - in sync - running  mastermode
 3 - in sync - running slave mode
 4 - in sync - running master mode (wait to reach state 2)
"
    ::= {HMMusesBDB 6}

DoBayesian  OBJECT-TYPE
    SYNTAX      OCTET STRING
    MAX-ACCESS  read-write
    STATUS      current
    DESCRIPTION
"
If activated, the message is checked based on Bayesian factors in spamdb for global and private entries. Private spamdb entries have a five times higher weight than global entries. This needs a fully functional spamdb built by rebuildspamdb. For starters it is best practice to put this inactive and build the spamdb collection with the help of DSNBL ,URIBL and spamaddresses. Scoring is done with baysValencePB for external mails, bayslocalValencePB is used for outgoing and internal mails - both values are multiplied with the detected baysProbability . It is possible to score (in and out) with a bonus for HAM with bayshamValencePB ( bayshamValencePB * ( 1 - baysProbability )).
  Both, the Bayesian-check and the Hidden-Markov-Model-check (below), are using Perl version depending (Perl 5.12 and higher)  features to recognize any possible character. How ever, some east asian languages (and some others) have graphemes, that contains multiple . If you need (or want) assp to process all text as a sequence of , the Perl module  is required.
"
    REFERENCE "Bayesian Check "
    DEFVAL { "0" }
    ::= {BayesianandHiddenMarkovModelHMMOptions 471}

syncStatDoBayesian  OBJECT-TYPE
    SYNTAX      OCTET STRING
    MAX-ACCESS  read-only
    STATUS      current
    DESCRIPTION
"
synchronization status for DoBayesian
-1 - DoBayesian could not be synchronized
 0 - synchronization not configured
 1 - out of sync - running master mode
 2 - in sync - running  mastermode
 3 - in sync - running slave mode
 4 - in sync - running master mode (wait to reach state 2)
"
    ::= {DoBayesian 5}

syncStatStrDoBayesian  OBJECT-TYPE
    SYNTAX      OCTET STRING
    MAX-ACCESS  read-only
    STATUS      current
    DESCRIPTION
"
synchronization status line from file assp_sync.cfg for DoBayesian
 0 - synchronization not configured
 1 - out of sync - running master mode
 2 - in sync - running  mastermode
 3 - in sync - running slave mode
 4 - in sync - running master mode (wait to reach state 2)
"
    ::= {DoBayesian 6}

BayesMaxProcessTime  OBJECT-TYPE
    SYNTAX      OCTET STRING
    MAX-ACCESS  read-write
    STATUS      current
    DESCRIPTION
"
The Bayesian- and HMM Checks are the most memory and CPU consuming tasks that ASSP is doing on a message. If such tasks running to long on one message, other messages could run in to SMTPIdleTimeout. Define here the maximum time in seconds that ASSP should spend on Bayesian Checks for one message. Default is 60.
"
    REFERENCE "Bayesian and HMM Check Timeout "
    DEFVAL { "15" }
    ::= {BayesianandHiddenMarkovModelHMMOptions 472}

syncStatBayesMaxProcessTime  OBJECT-TYPE
    SYNTAX      OCTET STRING
    MAX-ACCESS  read-only
    STATUS      current
    DESCRIPTION
"
synchronization status for BayesMaxProcessTime
-1 - BayesMaxProcessTime could not be synchronized
 0 - synchronization not configured
 1 - out of sync - running master mode
 2 - in sync - running  mastermode
 3 - in sync - running slave mode
 4 - in sync - running master mode (wait to reach state 2)
"
    ::= {BayesMaxProcessTime 5}

syncStatStrBayesMaxProcessTime  OBJECT-TYPE
    SYNTAX      OCTET STRING
    MAX-ACCESS  read-only
    STATUS      current
    DESCRIPTION
"
synchronization status line from file assp_sync.cfg for BayesMaxProcessTime
 0 - synchronization not configured
 1 - out of sync - running master mode
 2 - in sync - running  mastermode
 3 - in sync - running slave mode
 4 - in sync - running master mode (wait to reach state 2)
"
    ::= {BayesMaxProcessTime 6}

noBayesian  OBJECT-TYPE
    SYNTAX      OCTET STRING
    MAX-ACCESS  read-write
    STATUS      current
    DESCRIPTION
"
Mail from/to any of these addresses are ignored by Bayesian- and HMM check, mails will not be stored in spam/notspam collection. Accepts specific addresses (user@domain.com), user parts (user) or entire domains (@domain.com)
"
    REFERENCE "Skip Bayesian and HMM Check*"
    DEFVAL { "" }
    ::= {BayesianandHiddenMarkovModelHMMOptions 473}

syncStatnoBayesian  OBJECT-TYPE
    SYNTAX      OCTET STRING
    MAX-ACCESS  read-only
    STATUS      current
    DESCRIPTION
"
synchronization status for noBayesian
-1 - noBayesian could not be synchronized
 0 - synchronization not configured
 1 - out of sync - running master mode
 2 - in sync - running  mastermode
 3 - in sync - running slave mode
 4 - in sync - running master mode (wait to reach state 2)
"
    ::= {noBayesian 5}

syncStatStrnoBayesian  OBJECT-TYPE
    SYNTAX      OCTET STRING
    MAX-ACCESS  read-only
    STATUS      current
    DESCRIPTION
"
synchronization status line from file assp_sync.cfg for noBayesian
 0 - synchronization not configured
 1 - out of sync - running master mode
 2 - in sync - running  mastermode
 3 - in sync - running slave mode
 4 - in sync - running master mode (wait to reach state 2)
"
    ::= {noBayesian 6}

baysProbability  OBJECT-TYPE
    SYNTAX      OCTET STRING
    MAX-ACCESS  read-write
    STATUS      current
    DESCRIPTION
"
 Messages with spam-probability below or equal this threshold are considered Ham. Recommended '0.6'.
 An resulting Spam-Probability above this value is multiplied with baysValencePB_local or baysValencePB to get the penaltybox scoring value for the IP- and message score. In other words, the penaltybox scoring value is weighted by the Spam-Probability in case Spam is detected.
 An resulting Spam-Probability below this value but higher than ( 1 - baysProbability ) is stated as 'UNSURE' . In this case the half score will be added to the message score but not to the IP score and the message will not be blocked.
 The following default Bayesian math (prob = p1 / (p1 + p2)) is used to calculate the SpamProb value for 'n' found Bayesian-Word-Pairs or HMM-Sequences, each with a spam-weight 'p' - where 0&lt;p&lt;1 :
 'SpamProb' = (p<sub>1</sub> * p<sub>2</sub> * ... * p<sub>n</sub>) / ( p<sub>1</sub> * p<sub>2</sub> * ... * p<sub>n</sub>  + (1 - p<sub>1</sub>) * (1 - p<sub>2</sub> ) * ... * (1 - p<sub>n</sub>))
"
    REFERENCE "Bayesian and HMM Probability Threshold "
    DEFVAL { "0.6" }
    ::= {BayesianandHiddenMarkovModelHMMOptions 474}

syncStatbaysProbability  OBJECT-TYPE
    SYNTAX      OCTET STRING
    MAX-ACCESS  read-only
    STATUS      current
    DESCRIPTION
"
synchronization status for baysProbability
-1 - baysProbability could not be synchronized
 0 - synchronization not configured
 1 - out of sync - running master mode
 2 - in sync - running  mastermode
 3 - in sync - running slave mode
 4 - in sync - running master mode (wait to reach state 2)
"
    ::= {baysProbability 5}

syncStatStrbaysProbability  OBJECT-TYPE
    SYNTAX      OCTET STRING
    MAX-ACCESS  read-only
    STATUS      current
    DESCRIPTION
"
synchronization status line from file assp_sync.cfg for baysProbability
 0 - synchronization not configured
 1 - out of sync - running master mode
 2 - in sync - running  mastermode
 3 - in sync - running slave mode
 4 - in sync - running master mode (wait to reach state 2)
"
    ::= {baysProbability 6}

baysConf  OBJECT-TYPE
    SYNTAX      OCTET STRING
    MAX-ACCESS  read-write
    STATUS      current
    DESCRIPTION
"
 Spam-Mails having a confidence below this threshold are passed in TestMode .
 Spam-Mails having a confidence above this threshold are blocked. Set this only above 0 if you are familiar with the bayesian statistics used in ASSP.
 Messages that are processed by the bayesian and HMM check get a spam-probability score and a confidence score. The confidence score in assp is a quality indicator. A confidence near 0 would mean the probability score is like a wild guess. A confidence score near 1 would mean that it's pretty sure that the bayesian analysis result is correct. The confidence threshold is an allowance to process a Bayesian/HMM Spam as-if in Bayesian TestMode, if the message's *confidence* score is lower than the confidence threshold.
 Set this level to a specfic value, let's say .001 (which is a good one for starting), then:
 - messages with spam-probability higher than 0.6 and a confidence of less than 0.001 would come through as in test mode
 - messages with spam-probability higher than 0.6 and a confidence of more than 0.001 would be blocked
 - messages with spam-probability less than 0.6 would pass
 The 0.6 threshold can be set in baysProbability .
 Carefully set this parameter above 0, if the bayesian corpus norm (shown by the rebuildspamdb log) is less than 0.6 or higher than 1.4 .
 The following math is used to calculate the SpamProbConfidence value for 'n' found Bayesian-Word-Pairs or HMM-Sequences, each with a spam-weight 'p' - where 0&lt;p&lt;1 :
 extreme_confidence_count = |(0 &lt; p<sub>1...n</sub> &lt; 0.01)| - |(0.99 &lt; p<sub>1...n</sub> &lt; 1)|
 extreme_confidence_count = 0 - if ( extreme_confidence_count &lt; 0 and SpamProb &gt; 0.5) or ( extreme_confidence_count &gt; 0 and SpamProb &lt;= 0.5) == TRUE; 
 extreme_confidence_count = abs( extreme_confidence_count )
 mail_confidence = abs((P<sub>1</sub> * P<sub>2</sub> * ... * P<sub>k</sub>) - ((1 - P<sub>1</sub>) * (1 - P<sub>2</sub> ) * ... * (1 - P<sub>k</sub>))) - for all elements P<sub>1...k</sub> in (0.01 &lt; p<sub>1...n</sub> &lt; 0.99)
 corpus_confidence = 1 / ((abs(1 - corpus_norm) + 1)<sup>int(abs(1 - corpus_norm) * 10)</sup>) - the exponent is limited to a maximum of 4
 SpamProbConfidence = 0.01<sup>extreme_confidence_count</sup> * mail_confidence * corpus_confidence * (n / maxBayesValues)<sup>2</sup>
 The SpamProbConfidence is limited to a maximum of 1.0 . 
 All extreme values 'p' having a spam weight less than 0.01 or higher than 0.99 with a corresponding extreme value like (0.009 &lt;-&gt; 0.999) are ignored for the mail_confidence calculation.
  empty or zero = disabled.
"
    REFERENCE "Bayesian and HMM Confidence Threshold"
    DEFVAL { "0" }
    ::= {BayesianandHiddenMarkovModelHMMOptions 475}

syncStatbaysConf  OBJECT-TYPE
    SYNTAX      OCTET STRING
    MAX-ACCESS  read-only
    STATUS      current
    DESCRIPTION
"
synchronization status for baysConf
-1 - baysConf could not be synchronized
 0 - synchronization not configured
 1 - out of sync - running master mode
 2 - in sync - running  mastermode
 3 - in sync - running slave mode
 4 - in sync - running master mode (wait to reach state 2)
"
    ::= {baysConf 5}

syncStatStrbaysConf  OBJECT-TYPE
    SYNTAX      OCTET STRING
    MAX-ACCESS  read-only
    STATUS      current
    DESCRIPTION
"
synchronization status line from file assp_sync.cfg for baysConf
 0 - synchronization not configured
 1 - out of sync - running master mode
 2 - in sync - running  mastermode
 3 - in sync - running slave mode
 4 - in sync - running master mode (wait to reach state 2)
"
    ::= {baysConf 6}

baysConfidenceHalfScore  OBJECT-TYPE
    SYNTAX      OCTET STRING
    MAX-ACCESS  read-write
    STATUS      current
    DESCRIPTION
"
Spam-Mails having a confidence below the threshold, will get half of the normal penalty score for Bayesian and HMM hits.
"
    REFERENCE "Reduce Scoring for Low Confidence"
    DEFVAL { "1" }
    ::= {BayesianandHiddenMarkovModelHMMOptions 476}

syncStatbaysConfidenceHalfScore  OBJECT-TYPE
    SYNTAX      OCTET STRING
    MAX-ACCESS  read-only
    STATUS      current
    DESCRIPTION
"
synchronization status for baysConfidenceHalfScore
-1 - baysConfidenceHalfScore could not be synchronized
 0 - synchronization not configured
 1 - out of sync - running master mode
 2 - in sync - running  mastermode
 3 - in sync - running slave mode
 4 - in sync - running master mode (wait to reach state 2)
"
    ::= {baysConfidenceHalfScore 5}

syncStatStrbaysConfidenceHalfScore  OBJECT-TYPE
    SYNTAX      OCTET STRING
    MAX-ACCESS  read-only
    STATUS      current
    DESCRIPTION
"
synchronization status line from file assp_sync.cfg for baysConfidenceHalfScore
 0 - synchronization not configured
 1 - out of sync - running master mode
 2 - in sync - running  mastermode
 3 - in sync - running slave mode
 4 - in sync - running master mode (wait to reach state 2)
"
    ::= {baysConfidenceHalfScore 6}

AddSpamProbHeader  OBJECT-TYPE
    SYNTAX      OCTET STRING
    MAX-ACCESS  read-write
    STATUS      current
    DESCRIPTION
"
Adds a line to the email header 'X-Assp-Spam-Prob: 0.0123' and/or 'X-Assp-HMM-Spam-Prob: 0.0123' Probability ranges from 0 to +1 where &gt; 0.6 = spam.
"
    REFERENCE "Add Bayes and HMM Probability Header"
    DEFVAL { "" }
    ::= {BayesianandHiddenMarkovModelHMMOptions 478}

syncStatAddSpamProbHeader  OBJECT-TYPE
    SYNTAX      OCTET STRING
    MAX-ACCESS  read-only
    STATUS      current
    DESCRIPTION
"
synchronization status for AddSpamProbHeader
-1 - AddSpamProbHeader could not be synchronized
 0 - synchronization not configured
 1 - out of sync - running master mode
 2 - in sync - running  mastermode
 3 - in sync - running slave mode
 4 - in sync - running master mode (wait to reach state 2)
"
    ::= {AddSpamProbHeader 5}

syncStatStrAddSpamProbHeader  OBJECT-TYPE
    SYNTAX      OCTET STRING
    MAX-ACCESS  read-only
    STATUS      current
    DESCRIPTION
"
synchronization status line from file assp_sync.cfg for AddSpamProbHeader
 0 - synchronization not configured
 1 - out of sync - running master mode
 2 - in sync - running  mastermode
 3 - in sync - running slave mode
 4 - in sync - running master mode (wait to reach state 2)
"
    ::= {AddSpamProbHeader 6}

AddConfidenceHeader  OBJECT-TYPE
    SYNTAX      OCTET STRING
    MAX-ACCESS  read-write
    STATUS      current
    DESCRIPTION
"
Adds a line to the email header 'X-Assp-Bayes-Confidence: 0.0123' and/or 'X-Assp-HMM-Confidence: 0.0123'.
  
  
"
    REFERENCE "Add Bayes and HMM Confidence Header"
    DEFVAL { "" }
    ::= {BayesianandHiddenMarkovModelHMMOptions 479}

syncStatAddConfidenceHeader  OBJECT-TYPE
    SYNTAX      OCTET STRING
    MAX-ACCESS  read-only
    STATUS      current
    DESCRIPTION
"
synchronization status for AddConfidenceHeader
-1 - AddConfidenceHeader could not be synchronized
 0 - synchronization not configured
 1 - out of sync - running master mode
 2 - in sync - running  mastermode
 3 - in sync - running slave mode
 4 - in sync - running master mode (wait to reach state 2)
"
    ::= {AddConfidenceHeader 5}

syncStatStrAddConfidenceHeader  OBJECT-TYPE
    SYNTAX      OCTET STRING
    MAX-ACCESS  read-only
    STATUS      current
    DESCRIPTION
"
synchronization status line from file assp_sync.cfg for AddConfidenceHeader
 0 - synchronization not configured
 1 - out of sync - running master mode
 2 - in sync - running  mastermode
 3 - in sync - running slave mode
 4 - in sync - running master mode (wait to reach state 2)
"
    ::= {AddConfidenceHeader 6}

BayesWL  OBJECT-TYPE
    SYNTAX      OCTET STRING
    MAX-ACCESS  read-write
    STATUS      current
    DESCRIPTION
"

"
    REFERENCE "Bayesian/HMM Check on Whitelisted NON Local Senders/Messages"
    DEFVAL { "" }
    ::= {BayesianandHiddenMarkovModelHMMOptions 612}

syncStatBayesWL  OBJECT-TYPE
    SYNTAX      OCTET STRING
    MAX-ACCESS  read-only
    STATUS      current
    DESCRIPTION
"
synchronization status for BayesWL
-1 - BayesWL could not be synchronized
 0 - synchronization not configured
 1 - out of sync - running master mode
 2 - in sync - running  mastermode
 3 - in sync - running slave mode
 4 - in sync - running master mode (wait to reach state 2)
"
    ::= {BayesWL 5}

syncStatStrBayesWL  OBJECT-TYPE
    SYNTAX      OCTET STRING
    MAX-ACCESS  read-only
    STATUS      current
    DESCRIPTION
"
synchronization status line from file assp_sync.cfg for BayesWL
 0 - synchronization not configured
 1 - out of sync - running master mode
 2 - in sync - running  mastermode
 3 - in sync - running slave mode
 4 - in sync - running master mode (wait to reach state 2)
"
    ::= {BayesWL 6}

BayesNP  OBJECT-TYPE
    SYNTAX      OCTET STRING
    MAX-ACCESS  read-write
    STATUS      current
    DESCRIPTION
"

"
    REFERENCE "Bayesian/HMM Check on NoProcessing Messages"
    DEFVAL { "" }
    ::= {BayesianandHiddenMarkovModelHMMOptions 742}

syncStatBayesNP  OBJECT-TYPE
    SYNTAX      OCTET STRING
    MAX-ACCESS  read-only
    STATUS      current
    DESCRIPTION
"
synchronization status for BayesNP
-1 - BayesNP could not be synchronized
 0 - synchronization not configured
 1 - out of sync - running master mode
 2 - in sync - running  mastermode
 3 - in sync - running slave mode
 4 - in sync - running master mode (wait to reach state 2)
"
    ::= {BayesNP 5}

syncStatStrBayesNP  OBJECT-TYPE
    SYNTAX      OCTET STRING
    MAX-ACCESS  read-only
    STATUS      current
    DESCRIPTION
"
synchronization status line from file assp_sync.cfg for BayesNP
 0 - synchronization not configured
 1 - out of sync - running master mode
 2 - in sync - running  mastermode
 3 - in sync - running slave mode
 4 - in sync - running master mode (wait to reach state 2)
"
    ::= {BayesNP 6}

maxBayesValues  OBJECT-TYPE
    SYNTAX      OCTET STRING
    MAX-ACCESS  read-write
    STATUS      current
    DESCRIPTION
"
Maximum count of most significant values used to calculate the Bayesian/HMM-Spam-Probability and the confidence of that probability.
 The Bayesian/HMM Spam Probability will be fine with 30 and will get more exact, than higher this value is - until a value of 60.
 The confidence of the Bayesian/HMM Spam Probability will get better, than higher this value is.
 Values above 60 are possible, but could lead in to a performance penalty, without getting a better spam detection.
 Default is '60', minimum is '30'.
"
    REFERENCE "Maximum most significant results used per mail to calculate Bayesian- and HMM-Probability"
    DEFVAL { "60" }
    ::= {BayesianandHiddenMarkovModelHMMOptions 789}

syncStatmaxBayesValues  OBJECT-TYPE
    SYNTAX      OCTET STRING
    MAX-ACCESS  read-only
    STATUS      current
    DESCRIPTION
"
synchronization status for maxBayesValues
-1 - maxBayesValues could not be synchronized
 0 - synchronization not configured
 1 - out of sync - running master mode
 2 - in sync - running  mastermode
 3 - in sync - running slave mode
 4 - in sync - running master mode (wait to reach state 2)
"
    ::= {maxBayesValues 5}

syncStatStrmaxBayesValues  OBJECT-TYPE
    SYNTAX      OCTET STRING
    MAX-ACCESS  read-only
    STATUS      current
    DESCRIPTION
"
synchronization status line from file assp_sync.cfg for maxBayesValues
 0 - synchronization not configured
 1 - out of sync - running master mode
 2 - in sync - running  mastermode
 3 - in sync - running slave mode
 4 - in sync - running master mode (wait to reach state 2)
"
    ::= {maxBayesValues 6}

BayesianlocalOnly  OBJECT-TYPE
    SYNTAX      OCTET STRING
    MAX-ACCESS  read-write
    STATUS      current
    DESCRIPTION
"
Only mail from any of these local addresses are processed by the Bayesian- and HMM checks, except they are also defined in noBayesian_local . BayesLocal must be switched on to make this option working. Accepts specific addresses (user@domain.com), user parts (user) or entire domains (@domain.com)
"
    REFERENCE "Do Bayesian and HMM Check ONLY for this local senders*"
    DEFVAL { "" }
    ::= {BayesianandHiddenMarkovModelHMMOptions 901}

syncStatBayesianlocalOnly  OBJECT-TYPE
    SYNTAX      OCTET STRING
    MAX-ACCESS  read-only
    STATUS      current
    DESCRIPTION
"
synchronization status for BayesianlocalOnly
-1 - BayesianlocalOnly could not be synchronized
 0 - synchronization not configured
 1 - out of sync - running master mode
 2 - in sync - running  mastermode
 3 - in sync - running slave mode
 4 - in sync - running master mode (wait to reach state 2)
"
    ::= {BayesianlocalOnly 5}

syncStatStrBayesianlocalOnly  OBJECT-TYPE
    SYNTAX      OCTET STRING
    MAX-ACCESS  read-only
    STATUS      current
    DESCRIPTION
"
synchronization status line from file assp_sync.cfg for BayesianlocalOnly
 0 - synchronization not configured
 1 - out of sync - running master mode
 2 - in sync - running  mastermode
 3 - in sync - running slave mode
 4 - in sync - running master mode (wait to reach state 2)
"
    ::= {BayesianlocalOnly 6}

noBayesianlocal  OBJECT-TYPE
    SYNTAX      OCTET STRING
    MAX-ACCESS  read-write
    STATUS      current
    DESCRIPTION
"
Mail from any of these local addresses are ignored by Bayesian- and HMM checks, mails will not be stored in spam/notspam collection. Accepts specific addresses (user@domain.com), user parts (user) or entire domains (@domain.com)
"
    REFERENCE "Skip Bayesian and HMM Check for this local senders*"
    DEFVAL { "" }
    ::= {BayesianandHiddenMarkovModelHMMOptions 957}

syncStatnoBayesianlocal  OBJECT-TYPE
    SYNTAX      OCTET STRING
    MAX-ACCESS  read-only
    STATUS      current
    DESCRIPTION
"
synchronization status for noBayesianlocal
-1 - noBayesianlocal could not be synchronized
 0 - synchronization not configured
 1 - out of sync - running master mode
 2 - in sync - running  mastermode
 3 - in sync - running slave mode
 4 - in sync - running master mode (wait to reach state 2)
"
    ::= {noBayesianlocal 5}

syncStatStrnoBayesianlocal  OBJECT-TYPE
    SYNTAX      OCTET STRING
    MAX-ACCESS  read-only
    STATUS      current
    DESCRIPTION
"
synchronization status line from file assp_sync.cfg for noBayesianlocal
 0 - synchronization not configured
 1 - out of sync - running master mode
 2 - in sync - running  mastermode
 3 - in sync - running slave mode
 4 - in sync - running master mode (wait to reach state 2)
"
    ::= {noBayesianlocal 6}

DoPrivatSpamdb  OBJECT-TYPE
    SYNTAX      OCTET STRING
    MAX-ACCESS  read-write
    STATUS      current
    DESCRIPTION
"
If enabled, private entries (based on the local recipient and/or the report sender email address) will be added to the Bayesian and HMM databases. These private entries have a three times higher priority for users (full email address) and two times higher priority for domains (domain part of the email address) than global entries. To enable this option 'spamdb' must be set to use a database 'DB:' first!
 Setting this option to ON, will increase the record count for the spamdb and the HMM databases dramaticaly!
"
    REFERENCE "Use also private entries for the Bayesian Spamdb and Hidden Markov Model databases"
    DEFVAL { "3" }
    ::= {BayesianandHiddenMarkovModelHMMOptions 963}

syncStatDoPrivatSpamdb  OBJECT-TYPE
    SYNTAX      OCTET STRING
    MAX-ACCESS  read-only
    STATUS      current
    DESCRIPTION
"
synchronization status for DoPrivatSpamdb
-1 - DoPrivatSpamdb could not be synchronized
 0 - synchronization not configured
 1 - out of sync - running master mode
 2 - in sync - running  mastermode
 3 - in sync - running slave mode
 4 - in sync - running master mode (wait to reach state 2)
"
    ::= {DoPrivatSpamdb 5}

syncStatStrDoPrivatSpamdb  OBJECT-TYPE
    SYNTAX      OCTET STRING
    MAX-ACCESS  read-only
    STATUS      current
    DESCRIPTION
"
synchronization status line from file assp_sync.cfg for DoPrivatSpamdb
 0 - synchronization not configured
 1 - out of sync - running master mode
 2 - in sync - running  mastermode
 3 - in sync - running slave mode
 4 - in sync - running master mode (wait to reach state 2)
"
    ::= {DoPrivatSpamdb 6}

ignoreDBVersionMissMatch  OBJECT-TYPE
    SYNTAX      OCTET STRING
    MAX-ACCESS  read-write
    STATUS      current
    DESCRIPTION
"
The status of assp is changed to 'not healthy' if the current version of any of Spamdb or HMMdb is not equal to the required database version. Such a missmatch is automaticaly corrected with the next successfull rebuildspamdb. How ever, if you are unable to solve this problem for any reason, you should set this value to keep the status of assp 'healthy'.
"
    REFERENCE "Ignore a database version missmatch"
    DEFVAL { "0" }
    ::= {BayesianandHiddenMarkovModelHMMOptions 994}

syncStatignoreDBVersionMissMatch  OBJECT-TYPE
    SYNTAX      OCTET STRING
    MAX-ACCESS  read-only
    STATUS      current
    DESCRIPTION
"
synchronization status for ignoreDBVersionMissMatch
-1 - ignoreDBVersionMissMatch could not be synchronized
 0 - synchronization not configured
 1 - out of sync - running master mode
 2 - in sync - running  mastermode
 3 - in sync - running slave mode
 4 - in sync - running master mode (wait to reach state 2)
"
    ::= {ignoreDBVersionMissMatch 5}

syncStatStrignoreDBVersionMissMatch  OBJECT-TYPE
    SYNTAX      OCTET STRING
    MAX-ACCESS  read-only
    STATUS      current
    DESCRIPTION
"
synchronization status line from file assp_sync.cfg for ignoreDBVersionMissMatch
 0 - synchronization not configured
 1 - out of sync - running master mode
 2 - in sync - running  mastermode
 3 - in sync - running slave mode
 4 - in sync - running master mode (wait to reach state 2)
"
    ::= {ignoreDBVersionMissMatch 6}

BayesAfterHMM  OBJECT-TYPE
    SYNTAX      OCTET STRING
    MAX-ACCESS  read-write
    STATUS      current
    DESCRIPTION
"
This value is ignored if DoHMM is not enabled or set to monitor. The Bayesian check will only run, if the spam/ham probability of the HMM check is in a given value range or the HMM check has given too few results.
   Leave this blank to run the Bayesian check every time, independant from any HMM result (default).
   To set this value, define a probability value range like 0.3-0.7 (eg.).
"
    REFERENCE "Do Bayesian depends on HMM results"
    DEFVAL { "" }
    ::= {BayesianandHiddenMarkovModelHMMOptions 1013}

syncStatBayesAfterHMM  OBJECT-TYPE
    SYNTAX      OCTET STRING
    MAX-ACCESS  read-only
    STATUS      current
    DESCRIPTION
"
synchronization status for BayesAfterHMM
-1 - BayesAfterHMM could not be synchronized
 0 - synchronization not configured
 1 - out of sync - running master mode
 2 - in sync - running  mastermode
 3 - in sync - running slave mode
 4 - in sync - running master mode (wait to reach state 2)
"
    ::= {BayesAfterHMM 5}

syncStatStrBayesAfterHMM  OBJECT-TYPE
    SYNTAX      OCTET STRING
    MAX-ACCESS  read-only
    STATUS      current
    DESCRIPTION
"
synchronization status line from file assp_sync.cfg for BayesAfterHMM
 0 - synchronization not configured
 1 - out of sync - running master mode
 2 - in sync - running  mastermode
 3 - in sync - running slave mode
 4 - in sync - running master mode (wait to reach state 2)
"
    ::= {BayesAfterHMM 6}

BayesLocal  OBJECT-TYPE
    SYNTAX      OCTET STRING
    MAX-ACCESS  read-write
    STATUS      current
    DESCRIPTION
"

"
    REFERENCE "Bayesian/HMM Check on Local Senders"
    DEFVAL { "" }
    ::= {BayesianandHiddenMarkovModelHMMOptions 1036}

syncStatBayesLocal  OBJECT-TYPE
    SYNTAX      OCTET STRING
    MAX-ACCESS  read-only
    STATUS      current
    DESCRIPTION
"
synchronization status for BayesLocal
-1 - BayesLocal could not be synchronized
 0 - synchronization not configured
 1 - out of sync - running master mode
 2 - in sync - running  mastermode
 3 - in sync - running slave mode
 4 - in sync - running master mode (wait to reach state 2)
"
    ::= {BayesLocal 5}

syncStatStrBayesLocal  OBJECT-TYPE
    SYNTAX      OCTET STRING
    MAX-ACCESS  read-only
    STATUS      current
    DESCRIPTION
"
synchronization status line from file assp_sync.cfg for BayesLocal
 0 - synchronization not configured
 1 - out of sync - running master mode
 2 - in sync - running  mastermode
 3 - in sync - running slave mode
 4 - in sync - running master mode (wait to reach state 2)
"
    ::= {BayesLocal 6}

BackscatterDetection  OBJECT IDENTIFIER ::= {asspConfig 24}
DoMSGIDsig  OBJECT-TYPE
    SYNTAX      OCTET STRING
    MAX-ACCESS  read-write
    STATUS      current
    DESCRIPTION
"
If activated, the message-ID of each outgoing message will be signed with a unique Tag and every incoming mail will be checked against this Tag. This tagging mode is called FBMTV 'Forwarder(s) Bounce Message-ID Tag Validation' and it is worldwide unique to ASSP. This Tag is build nearly the same way, as BATVTag is build for the sender address. This Tag will be removed from any incoming email, to recover the original references in the mail header! If anything is changed on this option inside the mail, no DKIM-check will be done! Before activating DoMSGIDsig, please configure MSGIDpreTag and MSGIDsec!
   If activated and a bounced mail from null sender or postmaster contains no valid signature the configured action is taken.
   If activated and any other mail contains a valid signature (eg. because it is an answer/reply to a tagged mail), this mail will be flagged as noprocessing and whitelisted !
  This check requires an installed  module in Perl.
"
    REFERENCE "Do Message-ID tagging and validating (FBMTV)"
    DEFVAL { "0" }
    ::= {BackscatterDetection 480}

syncStatDoMSGIDsig  OBJECT-TYPE
    SYNTAX      OCTET STRING
    MAX-ACCESS  read-only
    STATUS      current
    DESCRIPTION
"
synchronization status for DoMSGIDsig
-1 - DoMSGIDsig could not be synchronized
 0 - synchronization not configured
 1 - out of sync - running master mode
 2 - in sync - running  mastermode
 3 - in sync - running slave mode
 4 - in sync - running master mode (wait to reach state 2)
"
    ::= {DoMSGIDsig 5}

syncStatStrDoMSGIDsig  OBJECT-TYPE
    SYNTAX      OCTET STRING
    MAX-ACCESS  read-only
    STATUS      current
    DESCRIPTION
"
synchronization status line from file assp_sync.cfg for DoMSGIDsig
 0 - synchronization not configured
 1 - out of sync - running master mode
 2 - in sync - running  mastermode
 3 - in sync - running slave mode
 4 - in sync - running master mode (wait to reach state 2)
"
    ::= {DoMSGIDsig 6}

MSGIDpreTag  OBJECT-TYPE
    SYNTAX      OCTET STRING
    MAX-ACCESS  read-write
    STATUS      current
    DESCRIPTION
"
To use Message-ID signing and to create the MSGID-Tags, a pre-Tag is needed. This Tag must be 2-5 characters [a-z,A-Z,0-9] long. Default is 'sig'.
"
    REFERENCE "Message-ID pre-Tag for MSGID-TAG-generation"
    DEFVAL { "sig" }
    ::= {BackscatterDetection 481}

syncStatMSGIDpreTag  OBJECT-TYPE
    SYNTAX      OCTET STRING
    MAX-ACCESS  read-only
    STATUS      current
    DESCRIPTION
"
synchronization status for MSGIDpreTag
-1 - MSGIDpreTag could not be synchronized
 0 - synchronization not configured
 1 - out of sync - running master mode
 2 - in sync - running  mastermode
 3 - in sync - running slave mode
 4 - in sync - running master mode (wait to reach state 2)
"
    ::= {MSGIDpreTag 5}

syncStatStrMSGIDpreTag  OBJECT-TYPE
    SYNTAX      OCTET STRING
    MAX-ACCESS  read-only
    STATUS      current
    DESCRIPTION
"
synchronization status line from file assp_sync.cfg for MSGIDpreTag
 0 - synchronization not configured
 1 - out of sync - running master mode
 2 - in sync - running  mastermode
 3 - in sync - running slave mode
 4 - in sync - running master mode (wait to reach state 2)
"
    ::= {MSGIDpreTag 6}

MSGIDSec  OBJECT-TYPE
    SYNTAX      OCTET STRING
    MAX-ACCESS  read-write
    STATUS      current
    DESCRIPTION
"
To use Message-ID signing and to generate the MSGID-Tags, at leased one secret key is needed, up to ten keys are possible.
  The notation is : generationnumber[0-9]=secretKey. For example(do not use!)</font>: 0=jk09Z|1=oPLmn4g|....   . Multiple paires are separated by pipes (|). Default is  0=key0|1=key1|2=key2|3=key3|4=key4|5=key5|6=key6|7=key7|8=key8|9=key9 . Do not defines spaces, tabs and '=' as part of the keys(secrets)! 
  <font color=red>Values that contains any default are not valid, please change them, to prevent detecting strange ASSP-signatures as valid local signatures!</font>For this reason, please define your secrets as unique as possible! The secrets are used randomly to build the Message-ID-Tags.
"
    REFERENCE "Message-ID Secrets for MSGID-TAG-generation*"
    DEFVAL { "0=key0|1=key1|2=key2|3=key3|4=key4|5=key5|6=key6|7=key7|8=key8|9=key9" }
    ::= {BackscatterDetection 482}

syncStatMSGIDSec  OBJECT-TYPE
    SYNTAX      OCTET STRING
    MAX-ACCESS  read-only
    STATUS      current
    DESCRIPTION
"
synchronization status for MSGIDSec
-1 - MSGIDSec could not be synchronized
 0 - synchronization not configured
 1 - out of sync - running master mode
 2 - in sync - running  mastermode
 3 - in sync - running slave mode
 4 - in sync - running master mode (wait to reach state 2)
"
    ::= {MSGIDSec 5}

syncStatStrMSGIDSec  OBJECT-TYPE
    SYNTAX      OCTET STRING
    MAX-ACCESS  read-only
    STATUS      current
    DESCRIPTION
"
synchronization status line from file assp_sync.cfg for MSGIDSec
 0 - synchronization not configured
 1 - out of sync - running master mode
 2 - in sync - running  mastermode
 3 - in sync - running slave mode
 4 - in sync - running master mode (wait to reach state 2)
"
    ::= {MSGIDSec 6}

MSGIDsigAddresses  OBJECT-TYPE
    SYNTAX      OCTET STRING
    MAX-ACCESS  read-write
    STATUS      current
    DESCRIPTION
"
Mail to any of these addresses will be tagged and checked by FBMTV. Accepts specific addresses (user@domain.com), user parts (user) or entire domains (@domain.com). If empty, FBMTV is done for all addresses.
"
    REFERENCE "Do FBMTV For These Addresses Only*"
    DEFVAL { "" }
    ::= {BackscatterDetection 483}

syncStatMSGIDsigAddresses  OBJECT-TYPE
    SYNTAX      OCTET STRING
    MAX-ACCESS  read-only
    STATUS      current
    DESCRIPTION
"
synchronization status for MSGIDsigAddresses
-1 - MSGIDsigAddresses could not be synchronized
 0 - synchronization not configured
 1 - out of sync - running master mode
 2 - in sync - running  mastermode
 3 - in sync - running slave mode
 4 - in sync - running master mode (wait to reach state 2)
"
    ::= {MSGIDsigAddresses 5}

syncStatStrMSGIDsigAddresses  OBJECT-TYPE
    SYNTAX      OCTET STRING
    MAX-ACCESS  read-only
    STATUS      current
    DESCRIPTION
"
synchronization status line from file assp_sync.cfg for MSGIDsigAddresses
 0 - synchronization not configured
 1 - out of sync - running master mode
 2 - in sync - running  mastermode
 3 - in sync - running slave mode
 4 - in sync - running master mode (wait to reach state 2)
"
    ::= {MSGIDsigAddresses 6}

DoBATV  OBJECT-TYPE
    SYNTAX      OCTET STRING
    MAX-ACCESS  read-write
    STATUS      current
    DESCRIPTION
"
If enabled any sender address of outgoing mails is mangled with a . Any incoming bounced mail is checked for a valid BATV-Tag. All valid (local) BATV-Tags will be removed from incoming mails - so whitelisting, delaying an all other recipient and sender based checks will use the normal addresses. If the BATV-check is successful, no MSGID-signing-check and DNS-Backscatter-check will be done! If any BATVTag was removed, no DKIM-check will be done! BATV-address-replacement is done, before the recipient replacement rules are processed!
  This check requires an installed  module in Perl.
"
    REFERENCE "Do BATV taging and validating"
    DEFVAL { "0" }
    ::= {BackscatterDetection 484}

syncStatDoBATV  OBJECT-TYPE
    SYNTAX      OCTET STRING
    MAX-ACCESS  read-only
    STATUS      current
    DESCRIPTION
"
synchronization status for DoBATV
-1 - DoBATV could not be synchronized
 0 - synchronization not configured
 1 - out of sync - running master mode
 2 - in sync - running  mastermode
 3 - in sync - running slave mode
 4 - in sync - running master mode (wait to reach state 2)
"
    ::= {DoBATV 5}

syncStatStrDoBATV  OBJECT-TYPE
    SYNTAX      OCTET STRING
    MAX-ACCESS  read-only
    STATUS      current
    DESCRIPTION
"
synchronization status line from file assp_sync.cfg for DoBATV
 0 - synchronization not configured
 1 - out of sync - running master mode
 2 - in sync - running  mastermode
 3 - in sync - running slave mode
 4 - in sync - running master mode (wait to reach state 2)
"
    ::= {DoBATV 6}

BATVSec  OBJECT-TYPE
    SYNTAX      OCTET STRING
    MAX-ACCESS  read-write
    STATUS      current
    DESCRIPTION
"
To use  and to create the BATV-Tags, at leased one secret key is needed, up to ten keys are possible.
  The notation is : generationnumber[0-9]=secretKey. For example: 0=key0|1=KEYX45rt|....   . Multiple paires are separated by pipes (|). Default is  0=key0|1=key1|2=key2|3=key3|4=key4|5=key5|6=key6|7=key7|8=key8|9=key9 . Do not defines spaces, tabs and '=' as part of the keys(secrets)! The secrets are use randomly to build the BATV-Tags.
"
    REFERENCE "BATV Secrets for BATV-TAG-generation*"
    DEFVAL { "0=key0|1=key1|2=key2|3=key3|4=key4|5=key5|6=key6|7=key7|8=key8|9=key9" }
    ::= {BackscatterDetection 485}

syncStatBATVSec  OBJECT-TYPE
    SYNTAX      OCTET STRING
    MAX-ACCESS  read-only
    STATUS      current
    DESCRIPTION
"
synchronization status for BATVSec
-1 - BATVSec could not be synchronized
 0 - synchronization not configured
 1 - out of sync - running master mode
 2 - in sync - running  mastermode
 3 - in sync - running slave mode
 4 - in sync - running master mode (wait to reach state 2)
"
    ::= {BATVSec 5}

syncStatStrBATVSec  OBJECT-TYPE
    SYNTAX      OCTET STRING
    MAX-ACCESS  read-only
    STATUS      current
    DESCRIPTION
"
synchronization status line from file assp_sync.cfg for BATVSec
 0 - synchronization not configured
 1 - out of sync - running master mode
 2 - in sync - running  mastermode
 3 - in sync - running slave mode
 4 - in sync - running master mode (wait to reach state 2)
"
    ::= {BATVSec 6}

removeBATVTag  OBJECT-TYPE
    SYNTAX      OCTET STRING
    MAX-ACCESS  read-write
    STATUS      current
    DESCRIPTION
"
Any strange BATV-signature will be removed from the sender address and the real sender address will be used! Using this together with remindBATVTag keeps your clients addressbooks (also whitelist, delaydb ...) clean from BATV-Tags. This will also work, if DoBATV is disabled. If you do not use remindBATVTag and the MTA behind ASSP sends a bounced mail back - this mail will fail on BATV on the recipients site. If any BATVTag was removed, no DKIM-check will be done!
"
    REFERENCE "remove strange BATV-Tags from incoming mails"
    DEFVAL { "0" }
    ::= {BackscatterDetection 486}

syncStatremoveBATVTag  OBJECT-TYPE
    SYNTAX      OCTET STRING
    MAX-ACCESS  read-only
    STATUS      current
    DESCRIPTION
"
synchronization status for removeBATVTag
-1 - removeBATVTag could not be synchronized
 0 - synchronization not configured
 1 - out of sync - running master mode
 2 - in sync - running  mastermode
 3 - in sync - running slave mode
 4 - in sync - running master mode (wait to reach state 2)
"
    ::= {removeBATVTag 5}

syncStatStrremoveBATVTag  OBJECT-TYPE
    SYNTAX      OCTET STRING
    MAX-ACCESS  read-only
    STATUS      current
    DESCRIPTION
"
synchronization status line from file assp_sync.cfg for removeBATVTag
 0 - synchronization not configured
 1 - out of sync - running master mode
 2 - in sync - running  mastermode
 3 - in sync - running slave mode
 4 - in sync - running master mode (wait to reach state 2)
"
    ::= {removeBATVTag 6}

remindBATVTag  OBJECT-TYPE
    SYNTAX      OCTET STRING
    MAX-ACCESS  read-write
    STATUS      current
    DESCRIPTION
"
If defined, any incoming stange BATV-signature will be stored and any recipient of outgoing bounce mails will be checked against this list. If there is found a valid (not older than 7 days) BATV-Tag for that recipient, it will be mangled in to the recipient address. This will also work, if DoBATV is disabled.
"
    REFERENCE "store incoming strange BATV-Tags to remind them for outgoing bounce mails"
    DEFVAL { "0" }
    ::= {BackscatterDetection 487}

syncStatremindBATVTag  OBJECT-TYPE
    SYNTAX      OCTET STRING
    MAX-ACCESS  read-only
    STATUS      current
    DESCRIPTION
"
synchronization status for remindBATVTag
-1 - remindBATVTag could not be synchronized
 0 - synchronization not configured
 1 - out of sync - running master mode
 2 - in sync - running  mastermode
 3 - in sync - running slave mode
 4 - in sync - running master mode (wait to reach state 2)
"
    ::= {remindBATVTag 5}

syncStatStrremindBATVTag  OBJECT-TYPE
    SYNTAX      OCTET STRING
    MAX-ACCESS  read-only
    STATUS      current
    DESCRIPTION
"
synchronization status line from file assp_sync.cfg for remindBATVTag
 0 - synchronization not configured
 1 - out of sync - running master mode
 2 - in sync - running  mastermode
 3 - in sync - running slave mode
 4 - in sync - running master mode (wait to reach state 2)
"
    ::= {remindBATVTag 6}

DoBackSctr  OBJECT-TYPE
    SYNTAX      OCTET STRING
    MAX-ACCESS  read-write
    STATUS      current
    DESCRIPTION
"
If activated, the IP-address of each message received for null sender,bounced or postmaster will be checked against the list below.
   DNS base checks requires an installed  module in Perl.
   For more information about backscatter detection please read .
"
    REFERENCE "Do DNS-Backscatter Detection"
    DEFVAL { "0" }
    ::= {BackscatterDetection 488}

syncStatDoBackSctr  OBJECT-TYPE
    SYNTAX      OCTET STRING
    MAX-ACCESS  read-only
    STATUS      current
    DESCRIPTION
"
synchronization status for DoBackSctr
-1 - DoBackSctr could not be synchronized
 0 - synchronization not configured
 1 - out of sync - running master mode
 2 - in sync - running  mastermode
 3 - in sync - running slave mode
 4 - in sync - running master mode (wait to reach state 2)
"
    ::= {DoBackSctr 5}

syncStatStrDoBackSctr  OBJECT-TYPE
    SYNTAX      OCTET STRING
    MAX-ACCESS  read-only
    STATUS      current
    DESCRIPTION
"
synchronization status line from file assp_sync.cfg for DoBackSctr
 0 - synchronization not configured
 1 - out of sync - running master mode
 2 - in sync - running  mastermode
 3 - in sync - running slave mode
 4 - in sync - running master mode (wait to reach state 2)
"
    ::= {DoBackSctr 6}

BackDNSInterval  OBJECT-TYPE
    SYNTAX      OCTET STRING
    MAX-ACCESS  read-write
    STATUS      current
    DESCRIPTION
"
IP's in cache will be removed after this interval in days. 0 will disable the cache and the usage of downloadBackDNSFile and localBackDNSFile. 
"
    REFERENCE "Backscatter-DNS Cache Refresh Interval"
    DEFVAL { "7" }
    ::= {BackscatterDetection 489}

syncStatBackDNSInterval  OBJECT-TYPE
    SYNTAX      OCTET STRING
    MAX-ACCESS  read-only
    STATUS      current
    DESCRIPTION
"
synchronization status for BackDNSInterval
-1 - BackDNSInterval could not be synchronized
 0 - synchronization not configured
 1 - out of sync - running master mode
 2 - in sync - running  mastermode
 3 - in sync - running slave mode
 4 - in sync - running master mode (wait to reach state 2)
"
    ::= {BackDNSInterval 5}

syncStatStrBackDNSInterval  OBJECT-TYPE
    SYNTAX      OCTET STRING
    MAX-ACCESS  read-only
    STATUS      current
    DESCRIPTION
"
synchronization status line from file assp_sync.cfg for BackDNSInterval
 0 - synchronization not configured
 1 - out of sync - running master mode
 2 - in sync - running  mastermode
 3 - in sync - running slave mode
 4 - in sync - running master mode (wait to reach state 2)
"
    ::= {BackDNSInterval 6}

BackSctrServiceProvider  OBJECT-TYPE
    SYNTAX      OCTET STRING
    MAX-ACCESS  read-write
    STATUS      current
    DESCRIPTION
"
ServiceProvider for DNS check on Backscatterer. Possible value is ips.backscatterer.org for DNS check.
"
    REFERENCE "ServiceProvider for Backscatterer Detection*"
    DEFVAL { "ips.backscatterer.org" }
    ::= {BackscatterDetection 490}

syncStatBackSctrServiceProvider  OBJECT-TYPE
    SYNTAX      OCTET STRING
    MAX-ACCESS  read-only
    STATUS      current
    DESCRIPTION
"
synchronization status for BackSctrServiceProvider
-1 - BackSctrServiceProvider could not be synchronized
 0 - synchronization not configured
 1 - out of sync - running master mode
 2 - in sync - running  mastermode
 3 - in sync - running slave mode
 4 - in sync - running master mode (wait to reach state 2)
"
    ::= {BackSctrServiceProvider 5}

syncStatStrBackSctrServiceProvider  OBJECT-TYPE
    SYNTAX      OCTET STRING
    MAX-ACCESS  read-only
    STATUS      current
    DESCRIPTION
"
synchronization status line from file assp_sync.cfg for BackSctrServiceProvider
 0 - synchronization not configured
 1 - out of sync - running master mode
 2 - in sync - running  mastermode
 3 - in sync - running slave mode
 4 - in sync - running master mode (wait to reach state 2)
"
    ::= {BackSctrServiceProvider 6}

downloadBackDNSFile  OBJECT-TYPE
    SYNTAX      OCTET STRING
    MAX-ACCESS  read-write
    STATUS      current
    DESCRIPTION
"
If selected, the complete IP-list is downloaded to a local file. If useDB4IntCache is set, the list is stored in a BerkeleyDB database (BackDNS2). Otherwise the records will be stored in the pbdb cache BackDNS . The download will be skipped, if useDB4IntCache is not set and mysqlSlaveMode is set. IP's are checked on this file first, if the IP is not found on this list, a DNS query is done. It is recommended to use this option for ISP's and users with more than 1000 bounced mails a day. See wget-mirrors.uceprotect.net/rbldnsd-all/ips.backscatterer.org.gz
"
    REFERENCE "Download the Backscatterer DNS-IP-List"
    DEFVAL { "0" }
    ::= {BackscatterDetection 491}

syncStatdownloadBackDNSFile  OBJECT-TYPE
    SYNTAX      OCTET STRING
    MAX-ACCESS  read-only
    STATUS      current
    DESCRIPTION
"
synchronization status for downloadBackDNSFile
-1 - downloadBackDNSFile could not be synchronized
 0 - synchronization not configured
 1 - out of sync - running master mode
 2 - in sync - running  mastermode
 3 - in sync - running slave mode
 4 - in sync - running master mode (wait to reach state 2)
"
    ::= {downloadBackDNSFile 5}

syncStatStrdownloadBackDNSFile  OBJECT-TYPE
    SYNTAX      OCTET STRING
    MAX-ACCESS  read-only
    STATUS      current
    DESCRIPTION
"
synchronization status line from file assp_sync.cfg for downloadBackDNSFile
 0 - synchronization not configured
 1 - out of sync - running master mode
 2 - in sync - running  mastermode
 3 - in sync - running slave mode
 4 - in sync - running master mode (wait to reach state 2)
"
    ::= {downloadBackDNSFile 6}

localBackDNSFile  OBJECT-TYPE
    SYNTAX      OCTET STRING
    MAX-ACCESS  read-write
    STATUS      current
    DESCRIPTION
"
The name of the local file that is used for this IP-list. The content of this file is filled in to the 'Backscatter-DNS Cache' ( BackDNSInterval ). IP's from this list will be removed after one day from the cache.
  The following configurations are valid for all Backscatter Detection Options!</font>
"
    REFERENCE "Local File for the Backscatterer DNS-IP-List"
    DEFVAL { "file:files/backdnslist.txt" }
    ::= {BackscatterDetection 492}

Back250OKISP  OBJECT-TYPE
    SYNTAX      OCTET STRING
    MAX-ACCESS  read-write
    STATUS      current
    DESCRIPTION
"
If any Backscatter check fails for a bounced mail that is coming from an ISPIP, ASSP will send '250 OK' to the ISP, but will discard the mail, if the check is configured to block!
"
    REFERENCE "Send 250 OK to ISP if any Backscatter Detection fails"
    DEFVAL { "0" }
    ::= {BackscatterDetection 493}

syncStatBack250OKISP  OBJECT-TYPE
    SYNTAX      OCTET STRING
    MAX-ACCESS  read-only
    STATUS      current
    DESCRIPTION
"
synchronization status for Back250OKISP
-1 - Back250OKISP could not be synchronized
 0 - synchronization not configured
 1 - out of sync - running master mode
 2 - in sync - running  mastermode
 3 - in sync - running slave mode
 4 - in sync - running master mode (wait to reach state 2)
"
    ::= {Back250OKISP 5}

syncStatStrBack250OKISP  OBJECT-TYPE
    SYNTAX      OCTET STRING
    MAX-ACCESS  read-only
    STATUS      current
    DESCRIPTION
"
synchronization status line from file assp_sync.cfg for Back250OKISP
 0 - synchronization not configured
 1 - out of sync - running master mode
 2 - in sync - running  mastermode
 3 - in sync - running slave mode
 4 - in sync - running master mode (wait to reach state 2)
"
    ::= {Back250OKISP 6}

BackWL  OBJECT-TYPE
    SYNTAX      OCTET STRING
    MAX-ACCESS  read-write
    STATUS      current
    DESCRIPTION
"
Tagging will be always done, if not excluded by address or domain!
"
    REFERENCE "Do Backscatter Detection checks for Whitelisted mail"
    DEFVAL { "" }
    ::= {BackscatterDetection 494}

syncStatBackWL  OBJECT-TYPE
    SYNTAX      OCTET STRING
    MAX-ACCESS  read-only
    STATUS      current
    DESCRIPTION
"
synchronization status for BackWL
-1 - BackWL could not be synchronized
 0 - synchronization not configured
 1 - out of sync - running master mode
 2 - in sync - running  mastermode
 3 - in sync - running slave mode
 4 - in sync - running master mode (wait to reach state 2)
"
    ::= {BackWL 5}

syncStatStrBackWL  OBJECT-TYPE
    SYNTAX      OCTET STRING
    MAX-ACCESS  read-only
    STATUS      current
    DESCRIPTION
"
synchronization status line from file assp_sync.cfg for BackWL
 0 - synchronization not configured
 1 - out of sync - running master mode
 2 - in sync - running  mastermode
 3 - in sync - running slave mode
 4 - in sync - running master mode (wait to reach state 2)
"
    ::= {BackWL 6}

BackNP  OBJECT-TYPE
    SYNTAX      OCTET STRING
    MAX-ACCESS  read-write
    STATUS      current
    DESCRIPTION
"
Tagging will be always done, if not excluded by address or domain!
"
    REFERENCE "Do Backscatter Detection checks for No Processing mail"
    DEFVAL { "" }
    ::= {BackscatterDetection 495}

syncStatBackNP  OBJECT-TYPE
    SYNTAX      OCTET STRING
    MAX-ACCESS  read-only
    STATUS      current
    DESCRIPTION
"
synchronization status for BackNP
-1 - BackNP could not be synchronized
 0 - synchronization not configured
 1 - out of sync - running master mode
 2 - in sync - running  mastermode
 3 - in sync - running slave mode
 4 - in sync - running master mode (wait to reach state 2)
"
    ::= {BackNP 5}

syncStatStrBackNP  OBJECT-TYPE
    SYNTAX      OCTET STRING
    MAX-ACCESS  read-only
    STATUS      current
    DESCRIPTION
"
synchronization status line from file assp_sync.cfg for BackNP
 0 - synchronization not configured
 1 - out of sync - running master mode
 2 - in sync - running  mastermode
 3 - in sync - running slave mode
 4 - in sync - running master mode (wait to reach state 2)
"
    ::= {BackNP 6}

noBackSctrAddresses  OBJECT-TYPE
    SYNTAX      OCTET STRING
    MAX-ACCESS  read-write
    STATUS      current
    DESCRIPTION
"
Mail to and from any of these addresses will not be tagged and checked by any backscatter option. Accepts specific addresses (user@domain.com), user parts (user) or entire domains (@domain.com).
"
    REFERENCE "Do not any Backscatter detection for this Addresses *"
    DEFVAL { "" }
    ::= {BackscatterDetection 496}

syncStatnoBackSctrAddresses  OBJECT-TYPE
    SYNTAX      OCTET STRING
    MAX-ACCESS  read-only
    STATUS      current
    DESCRIPTION
"
synchronization status for noBackSctrAddresses
-1 - noBackSctrAddresses could not be synchronized
 0 - synchronization not configured
 1 - out of sync - running master mode
 2 - in sync - running  mastermode
 3 - in sync - running slave mode
 4 - in sync - running master mode (wait to reach state 2)
"
    ::= {noBackSctrAddresses 5}

syncStatStrnoBackSctrAddresses  OBJECT-TYPE
    SYNTAX      OCTET STRING
    MAX-ACCESS  read-only
    STATUS      current
    DESCRIPTION
"
synchronization status line from file assp_sync.cfg for noBackSctrAddresses
 0 - synchronization not configured
 1 - out of sync - running master mode
 2 - in sync - running  mastermode
 3 - in sync - running slave mode
 4 - in sync - running master mode (wait to reach state 2)
"
    ::= {noBackSctrAddresses 6}

noBackSctrIP  OBJECT-TYPE
    SYNTAX      OCTET STRING
    MAX-ACCESS  read-write
    STATUS      current
    DESCRIPTION
"
Enter IP's that you want to exclude from FBMTV and Backscatter check, separated by pipes (|). 
  
"
    REFERENCE "Exclude these IP's from any Backscatter detection*"
    DEFVAL { "" }
    ::= {BackscatterDetection 497}

syncStatnoBackSctrIP  OBJECT-TYPE
    SYNTAX      OCTET STRING
    MAX-ACCESS  read-only
    STATUS      current
    DESCRIPTION
"
synchronization status for noBackSctrIP
-1 - noBackSctrIP could not be synchronized
 0 - synchronization not configured
 1 - out of sync - running master mode
 2 - in sync - running  mastermode
 3 - in sync - running slave mode
 4 - in sync - running master mode (wait to reach state 2)
"
    ::= {noBackSctrIP 5}

syncStatStrnoBackSctrIP  OBJECT-TYPE
    SYNTAX      OCTET STRING
    MAX-ACCESS  read-only
    STATUS      current
    DESCRIPTION
"
synchronization status line from file assp_sync.cfg for noBackSctrIP
 0 - synchronization not configured
 1 - out of sync - running master mode
 2 - in sync - running  mastermode
 3 - in sync - running slave mode
 4 - in sync - running master mode (wait to reach state 2)
"
    ::= {noBackSctrIP 6}

noMSGIDsigRe  OBJECT-TYPE
    SYNTAX      OCTET STRING
    MAX-ACCESS  read-write
    STATUS      current
    DESCRIPTION
"
Use this to skip the Message-ID tagging depending on the content of the email. If the content of the email matches this regular expression (checking MaxBytes only), FBMTV will not be done. For example: 'I am out of office' .
"
    REFERENCE "Skip Message-ID signing, mail content dependant*"
    DEFVAL { "" }
    ::= {BackscatterDetection 890}

syncStatnoMSGIDsigRe  OBJECT-TYPE
    SYNTAX      OCTET STRING
    MAX-ACCESS  read-only
    STATUS      current
    DESCRIPTION
"
synchronization status for noMSGIDsigRe
-1 - noMSGIDsigRe could not be synchronized
 0 - synchronization not configured
 1 - out of sync - running master mode
 2 - in sync - running  mastermode
 3 - in sync - running slave mode
 4 - in sync - running master mode (wait to reach state 2)
"
    ::= {noMSGIDsigRe 5}

syncStatStrnoMSGIDsigRe  OBJECT-TYPE
    SYNTAX      OCTET STRING
    MAX-ACCESS  read-only
    STATUS      current
    DESCRIPTION
"
synchronization status line from file assp_sync.cfg for noMSGIDsigRe
 0 - synchronization not configured
 1 - out of sync - running master mode
 2 - in sync - running  mastermode
 3 - in sync - running slave mode
 4 - in sync - running master mode (wait to reach state 2)
"
    ::= {noMSGIDsigRe 6}

noRedMSGIDsig  OBJECT-TYPE
    SYNTAX      OCTET STRING
    MAX-ACCESS  read-write
    STATUS      current
    DESCRIPTION
"
If selected, FBMTV will not be done for redlisted emails!
"
    REFERENCE "Skip Message-ID signing for Redlisted mails"
    DEFVAL { "0" }
    ::= {BackscatterDetection 891}

syncStatnoRedMSGIDsig  OBJECT-TYPE
    SYNTAX      OCTET STRING
    MAX-ACCESS  read-only
    STATUS      current
    DESCRIPTION
"
synchronization status for noRedMSGIDsig
-1 - noRedMSGIDsig could not be synchronized
 0 - synchronization not configured
 1 - out of sync - running master mode
 2 - in sync - running  mastermode
 3 - in sync - running slave mode
 4 - in sync - running master mode (wait to reach state 2)
"
    ::= {noRedMSGIDsig 5}

syncStatStrnoRedMSGIDsig  OBJECT-TYPE
    SYNTAX      OCTET STRING
    MAX-ACCESS  read-only
    STATUS      current
    DESCRIPTION
"
synchronization status line from file assp_sync.cfg for noRedMSGIDsig
 0 - synchronization not configured
 1 - out of sync - running master mode
 2 - in sync - running  mastermode
 3 - in sync - running slave mode
 4 - in sync - running master mode (wait to reach state 2)
"
    ::= {noRedMSGIDsig 6}

noBackSctrRe  OBJECT-TYPE
    SYNTAX      OCTET STRING
    MAX-ACCESS  read-write
    STATUS      current
    DESCRIPTION
"
If the contents of a mail matches these regular expressions, all BackScatter checks will be skipped.
"
    REFERENCE "Regular Expression to Skip all BackScatter Checks*"
    DEFVAL { "" }
    ::= {BackscatterDetection 924}

TestModes  OBJECT IDENTIFIER ::= {asspConfig 25}
spamSubject  OBJECT-TYPE
    SYNTAX      OCTET STRING
    MAX-ACCESS  read-write
    STATUS      current
    DESCRIPTION
"
Setting a filter to testmode will tell ASSP not to reject the mail but rather build up the whitelist and spam and notspam collections. This can go on for some time without disturbing normal operation. After this very important phase TestMode can be used to tag the message: if TestMode and the message is spam Spam Subject gets prepended to the subject of the email. For example: [SPAM]
"
    REFERENCE "Prepend Spam Subject "
    DEFVAL { "" }
    ::= {TestModes 498}

syncStatspamSubject  OBJECT-TYPE
    SYNTAX      OCTET STRING
    MAX-ACCESS  read-only
    STATUS      current
    DESCRIPTION
"
synchronization status for spamSubject
-1 - spamSubject could not be synchronized
 0 - synchronization not configured
 1 - out of sync - running master mode
 2 - in sync - running  mastermode
 3 - in sync - running slave mode
 4 - in sync - running master mode (wait to reach state 2)
"
    ::= {spamSubject 5}

syncStatStrspamSubject  OBJECT-TYPE
    SYNTAX      OCTET STRING
    MAX-ACCESS  read-only
    STATUS      current
    DESCRIPTION
"
synchronization status line from file assp_sync.cfg for spamSubject
 0 - synchronization not configured
 1 - out of sync - running master mode
 2 - in sync - running  mastermode
 3 - in sync - running slave mode
 4 - in sync - running master mode (wait to reach state 2)
"
    ::= {spamSubject 6}

spamTag  OBJECT-TYPE
    SYNTAX      OCTET STRING
    MAX-ACCESS  read-write
    STATUS      current
    DESCRIPTION
"
ASSP uses many methods. The method which caught the spam will be prepended to the subject of the email. For example; [DNSBL]
"
    REFERENCE "Prepend Spam Tag"
    DEFVAL { "" }
    ::= {TestModes 499}

syncStatspamTag  OBJECT-TYPE
    SYNTAX      OCTET STRING
    MAX-ACCESS  read-only
    STATUS      current
    DESCRIPTION
"
synchronization status for spamTag
-1 - spamTag could not be synchronized
 0 - synchronization not configured
 1 - out of sync - running master mode
 2 - in sync - running  mastermode
 3 - in sync - running slave mode
 4 - in sync - running master mode (wait to reach state 2)
"
    ::= {spamTag 5}

syncStatStrspamTag  OBJECT-TYPE
    SYNTAX      OCTET STRING
    MAX-ACCESS  read-only
    STATUS      current
    DESCRIPTION
"
synchronization status line from file assp_sync.cfg for spamTag
 0 - synchronization not configured
 1 - out of sync - running master mode
 2 - in sync - running  mastermode
 3 - in sync - running slave mode
 4 - in sync - running master mode (wait to reach state 2)
"
    ::= {spamTag 6}

allTestMode  OBJECT-TYPE
    SYNTAX      OCTET STRING
    MAX-ACCESS  read-write
    STATUS      current
    DESCRIPTION
"
Turn all of the individual testmodes on - regardless of the individual test mode settings. 
"
    REFERENCE "All Test Mode ON"
    DEFVAL { "" }
    ::= {TestModes 500}

syncStatallTestMode  OBJECT-TYPE
    SYNTAX      OCTET STRING
    MAX-ACCESS  read-only
    STATUS      current
    DESCRIPTION
"
synchronization status for allTestMode
-1 - allTestMode could not be synchronized
 0 - synchronization not configured
 1 - out of sync - running master mode
 2 - in sync - running  mastermode
 3 - in sync - running slave mode
 4 - in sync - running master mode (wait to reach state 2)
"
    ::= {allTestMode 5}

syncStatStrallTestMode  OBJECT-TYPE
    SYNTAX      OCTET STRING
    MAX-ACCESS  read-only
    STATUS      current
    DESCRIPTION
"
synchronization status line from file assp_sync.cfg for allTestMode
 0 - synchronization not configured
 1 - out of sync - running master mode
 2 - in sync - running  mastermode
 3 - in sync - running slave mode
 4 - in sync - running master mode (wait to reach state 2)
"
    ::= {allTestMode 6}

baysTestMode  OBJECT-TYPE
    SYNTAX      OCTET STRING
    MAX-ACCESS  read-write
    STATUS      current
    DESCRIPTION
"

"
    REFERENCE "Bayesian/Hidden-Markov-Model Test Mode"
    DEFVAL { "" }
    ::= {TestModes 501}

syncStatbaysTestMode  OBJECT-TYPE
    SYNTAX      OCTET STRING
    MAX-ACCESS  read-only
    STATUS      current
    DESCRIPTION
"
synchronization status for baysTestMode
-1 - baysTestMode could not be synchronized
 0 - synchronization not configured
 1 - out of sync - running master mode
 2 - in sync - running  mastermode
 3 - in sync - running slave mode
 4 - in sync - running master mode (wait to reach state 2)
"
    ::= {baysTestMode 5}

syncStatStrbaysTestMode  OBJECT-TYPE
    SYNTAX      OCTET STRING
    MAX-ACCESS  read-only
    STATUS      current
    DESCRIPTION
"
synchronization status line from file assp_sync.cfg for baysTestMode
 0 - synchronization not configured
 1 - out of sync - running master mode
 2 - in sync - running  mastermode
 3 - in sync - running slave mode
 4 - in sync - running master mode (wait to reach state 2)
"
    ::= {baysTestMode 6}

baysTestModeUserAddresses  OBJECT-TYPE
    SYNTAX      OCTET STRING
    MAX-ACCESS  read-write
    STATUS      current
    DESCRIPTION
"
These users are in test mode / mark subject only for bayesian spam, even with test mode above off
"
    REFERENCE "Bayesian Test Mode User Addresses*"
    DEFVAL { "" }
    ::= {TestModes 502}

syncStatbaysTestModeUserAddresses  OBJECT-TYPE
    SYNTAX      OCTET STRING
    MAX-ACCESS  read-only
    STATUS      current
    DESCRIPTION
"
synchronization status for baysTestModeUserAddresses
-1 - baysTestModeUserAddresses could not be synchronized
 0 - synchronization not configured
 1 - out of sync - running master mode
 2 - in sync - running  mastermode
 3 - in sync - running slave mode
 4 - in sync - running master mode (wait to reach state 2)
"
    ::= {baysTestModeUserAddresses 5}

syncStatStrbaysTestModeUserAddresses  OBJECT-TYPE
    SYNTAX      OCTET STRING
    MAX-ACCESS  read-only
    STATUS      current
    DESCRIPTION
"
synchronization status line from file assp_sync.cfg for baysTestModeUserAddresses
 0 - synchronization not configured
 1 - out of sync - running master mode
 2 - in sync - running  mastermode
 3 - in sync - running slave mode
 4 - in sync - running master mode (wait to reach state 2)
"
    ::= {baysTestModeUserAddresses 6}

blTestMode  OBJECT-TYPE
    SYNTAX      OCTET STRING
    MAX-ACCESS  read-write
    STATUS      current
    DESCRIPTION
"

"
    REFERENCE "BlackDomain Test Mode"
    DEFVAL { "" }
    ::= {TestModes 503}

syncStatblTestMode  OBJECT-TYPE
    SYNTAX      OCTET STRING
    MAX-ACCESS  read-only
    STATUS      current
    DESCRIPTION
"
synchronization status for blTestMode
-1 - blTestMode could not be synchronized
 0 - synchronization not configured
 1 - out of sync - running master mode
 2 - in sync - running  mastermode
 3 - in sync - running slave mode
 4 - in sync - running master mode (wait to reach state 2)
"
    ::= {blTestMode 5}

syncStatStrblTestMode  OBJECT-TYPE
    SYNTAX      OCTET STRING
    MAX-ACCESS  read-only
    STATUS      current
    DESCRIPTION
"
synchronization status line from file assp_sync.cfg for blTestMode
 0 - synchronization not configured
 1 - out of sync - running master mode
 2 - in sync - running  mastermode
 3 - in sync - running slave mode
 4 - in sync - running master mode (wait to reach state 2)
"
    ::= {blTestMode 6}

hlTestMode  OBJECT-TYPE
    SYNTAX      OCTET STRING
    MAX-ACCESS  read-write
    STATUS      current
    DESCRIPTION
"

"
    REFERENCE "Helo Blacklist Test Mode"
    DEFVAL { "" }
    ::= {TestModes 504}

syncStathlTestMode  OBJECT-TYPE
    SYNTAX      OCTET STRING
    MAX-ACCESS  read-only
    STATUS      current
    DESCRIPTION
"
synchronization status for hlTestMode
-1 - hlTestMode could not be synchronized
 0 - synchronization not configured
 1 - out of sync - running master mode
 2 - in sync - running  mastermode
 3 - in sync - running slave mode
 4 - in sync - running master mode (wait to reach state 2)
"
    ::= {hlTestMode 5}

syncStatStrhlTestMode  OBJECT-TYPE
    SYNTAX      OCTET STRING
    MAX-ACCESS  read-only
    STATUS      current
    DESCRIPTION
"
synchronization status line from file assp_sync.cfg for hlTestMode
 0 - synchronization not configured
 1 - out of sync - running master mode
 2 - in sync - running  mastermode
 3 - in sync - running slave mode
 4 - in sync - running master mode (wait to reach state 2)
"
    ::= {hlTestMode 6}

flsTestMode  OBJECT-TYPE
    SYNTAX      OCTET STRING
    MAX-ACCESS  read-write
    STATUS      current
    DESCRIPTION
"
-> DoNoValidLocalSender
"
    REFERENCE "Forged Local Domain Test Mode"
    DEFVAL { "" }
    ::= {TestModes 505}

syncStatflsTestMode  OBJECT-TYPE
    SYNTAX      OCTET STRING
    MAX-ACCESS  read-only
    STATUS      current
    DESCRIPTION
"
synchronization status for flsTestMode
-1 - flsTestMode could not be synchronized
 0 - synchronization not configured
 1 - out of sync - running master mode
 2 - in sync - running  mastermode
 3 - in sync - running slave mode
 4 - in sync - running master mode (wait to reach state 2)
"
    ::= {flsTestMode 5}

syncStatStrflsTestMode  OBJECT-TYPE
    SYNTAX      OCTET STRING
    MAX-ACCESS  read-only
    STATUS      current
    DESCRIPTION
"
synchronization status line from file assp_sync.cfg for flsTestMode
 0 - synchronization not configured
 1 - out of sync - running master mode
 2 - in sync - running  mastermode
 3 - in sync - running slave mode
 4 - in sync - running master mode (wait to reach state 2)
"
    ::= {flsTestMode 6}

spfTestMode  OBJECT-TYPE
    SYNTAX      OCTET STRING
    MAX-ACCESS  read-write
    STATUS      current
    DESCRIPTION
"

"
    REFERENCE "SPF Test Mode"
    DEFVAL { "" }
    ::= {TestModes 506}

syncStatspfTestMode  OBJECT-TYPE
    SYNTAX      OCTET STRING
    MAX-ACCESS  read-only
    STATUS      current
    DESCRIPTION
"
synchronization status for spfTestMode
-1 - spfTestMode could not be synchronized
 0 - synchronization not configured
 1 - out of sync - running master mode
 2 - in sync - running  mastermode
 3 - in sync - running slave mode
 4 - in sync - running master mode (wait to reach state 2)
"
    ::= {spfTestMode 5}

syncStatStrspfTestMode  OBJECT-TYPE
    SYNTAX      OCTET STRING
    MAX-ACCESS  read-only
    STATUS      current
    DESCRIPTION
"
synchronization status line from file assp_sync.cfg for spfTestMode
 0 - synchronization not configured
 1 - out of sync - running master mode
 2 - in sync - running  mastermode
 3 - in sync - running slave mode
 4 - in sync - running master mode (wait to reach state 2)
"
    ::= {spfTestMode 6}

rblTestMode  OBJECT-TYPE
    SYNTAX      OCTET STRING
    MAX-ACCESS  read-write
    STATUS      current
    DESCRIPTION
"

"
    REFERENCE "DNSBL Test Mode"
    DEFVAL { "" }
    ::= {TestModes 507}

syncStatrblTestMode  OBJECT-TYPE
    SYNTAX      OCTET STRING
    MAX-ACCESS  read-only
    STATUS      current
    DESCRIPTION
"
synchronization status for rblTestMode
-1 - rblTestMode could not be synchronized
 0 - synchronization not configured
 1 - out of sync - running master mode
 2 - in sync - running  mastermode
 3 - in sync - running slave mode
 4 - in sync - running master mode (wait to reach state 2)
"
    ::= {rblTestMode 5}

syncStatStrrblTestMode  OBJECT-TYPE
    SYNTAX      OCTET STRING
    MAX-ACCESS  read-only
    STATUS      current
    DESCRIPTION
"
synchronization status line from file assp_sync.cfg for rblTestMode
 0 - synchronization not configured
 1 - out of sync - running master mode
 2 - in sync - running  mastermode
 3 - in sync - running slave mode
 4 - in sync - running master mode (wait to reach state 2)
"
    ::= {rblTestMode 6}

attachTestMode  OBJECT-TYPE
    SYNTAX      OCTET STRING
    MAX-ACCESS  read-write
    STATUS      current
    DESCRIPTION
"

"
    REFERENCE "Bad Attachment Test Mode"
    DEFVAL { "" }
    ::= {TestModes 508}

syncStatattachTestMode  OBJECT-TYPE
    SYNTAX      OCTET STRING
    MAX-ACCESS  read-only
    STATUS      current
    DESCRIPTION
"
synchronization status for attachTestMode
-1 - attachTestMode could not be synchronized
 0 - synchronization not configured
 1 - out of sync - running master mode
 2 - in sync - running  mastermode
 3 - in sync - running slave mode
 4 - in sync - running master mode (wait to reach state 2)
"
    ::= {attachTestMode 5}

syncStatStrattachTestMode  OBJECT-TYPE
    SYNTAX      OCTET STRING
    MAX-ACCESS  read-only
    STATUS      current
    DESCRIPTION
"
synchronization status line from file assp_sync.cfg for attachTestMode
 0 - synchronization not configured
 1 - out of sync - running master mode
 2 - in sync - running  mastermode
 3 - in sync - running slave mode
 4 - in sync - running master mode (wait to reach state 2)
"
    ::= {attachTestMode 6}

uriblTestMode  OBJECT-TYPE
    SYNTAX      OCTET STRING
    MAX-ACCESS  read-write
    STATUS      current
    DESCRIPTION
"

"
    REFERENCE "URIBL Test Mode"
    DEFVAL { "" }
    ::= {TestModes 509}

syncStaturiblTestMode  OBJECT-TYPE
    SYNTAX      OCTET STRING
    MAX-ACCESS  read-only
    STATUS      current
    DESCRIPTION
"
synchronization status for uriblTestMode
-1 - uriblTestMode could not be synchronized
 0 - synchronization not configured
 1 - out of sync - running master mode
 2 - in sync - running  mastermode
 3 - in sync - running slave mode
 4 - in sync - running master mode (wait to reach state 2)
"
    ::= {uriblTestMode 5}

syncStatStruriblTestMode  OBJECT-TYPE
    SYNTAX      OCTET STRING
    MAX-ACCESS  read-only
    STATUS      current
    DESCRIPTION
"
synchronization status line from file assp_sync.cfg for uriblTestMode
 0 - synchronization not configured
 1 - out of sync - running master mode
 2 - in sync - running  mastermode
 3 - in sync - running slave mode
 4 - in sync - running master mode (wait to reach state 2)
"
    ::= {uriblTestMode 6}

srsTestMode  OBJECT-TYPE
    SYNTAX      OCTET STRING
    MAX-ACCESS  read-write
    STATUS      current
    DESCRIPTION
"

"
    REFERENCE "SRS Test Mode"
    DEFVAL { "" }
    ::= {TestModes 510}

syncStatsrsTestMode  OBJECT-TYPE
    SYNTAX      OCTET STRING
    MAX-ACCESS  read-only
    STATUS      current
    DESCRIPTION
"
synchronization status for srsTestMode
-1 - srsTestMode could not be synchronized
 0 - synchronization not configured
 1 - out of sync - running master mode
 2 - in sync - running  mastermode
 3 - in sync - running slave mode
 4 - in sync - running master mode (wait to reach state 2)
"
    ::= {srsTestMode 5}

syncStatStrsrsTestMode  OBJECT-TYPE
    SYNTAX      OCTET STRING
    MAX-ACCESS  read-only
    STATUS      current
    DESCRIPTION
"
synchronization status line from file assp_sync.cfg for srsTestMode
 0 - synchronization not configured
 1 - out of sync - running master mode
 2 - in sync - running  mastermode
 3 - in sync - running slave mode
 4 - in sync - running master mode (wait to reach state 2)
"
    ::= {srsTestMode 6}

bombTestMode  OBJECT-TYPE
    SYNTAX      OCTET STRING
    MAX-ACCESS  read-write
    STATUS      current
    DESCRIPTION
"

"
    REFERENCE "Bomb Regex Test Mode"
    DEFVAL { "" }
    ::= {TestModes 511}

syncStatbombTestMode  OBJECT-TYPE
    SYNTAX      OCTET STRING
    MAX-ACCESS  read-only
    STATUS      current
    DESCRIPTION
"
synchronization status for bombTestMode
-1 - bombTestMode could not be synchronized
 0 - synchronization not configured
 1 - out of sync - running master mode
 2 - in sync - running  mastermode
 3 - in sync - running slave mode
 4 - in sync - running master mode (wait to reach state 2)
"
    ::= {bombTestMode 5}

syncStatStrbombTestMode  OBJECT-TYPE
    SYNTAX      OCTET STRING
    MAX-ACCESS  read-only
    STATUS      current
    DESCRIPTION
"
synchronization status line from file assp_sync.cfg for bombTestMode
 0 - synchronization not configured
 1 - out of sync - running master mode
 2 - in sync - running  mastermode
 3 - in sync - running slave mode
 4 - in sync - running master mode (wait to reach state 2)
"
    ::= {bombTestMode 6}

scriptTestMode  OBJECT-TYPE
    SYNTAX      OCTET STRING
    MAX-ACCESS  read-write
    STATUS      current
    DESCRIPTION
"

"
    REFERENCE "Script Regex Test Mode"
    DEFVAL { "" }
    ::= {TestModes 512}

syncStatscriptTestMode  OBJECT-TYPE
    SYNTAX      OCTET STRING
    MAX-ACCESS  read-only
    STATUS      current
    DESCRIPTION
"
synchronization status for scriptTestMode
-1 - scriptTestMode could not be synchronized
 0 - synchronization not configured
 1 - out of sync - running master mode
 2 - in sync - running  mastermode
 3 - in sync - running slave mode
 4 - in sync - running master mode (wait to reach state 2)
"
    ::= {scriptTestMode 5}

syncStatStrscriptTestMode  OBJECT-TYPE
    SYNTAX      OCTET STRING
    MAX-ACCESS  read-only
    STATUS      current
    DESCRIPTION
"
synchronization status line from file assp_sync.cfg for scriptTestMode
 0 - synchronization not configured
 1 - out of sync - running master mode
 2 - in sync - running  mastermode
 3 - in sync - running slave mode
 4 - in sync - running master mode (wait to reach state 2)
"
    ::= {scriptTestMode 6}

mxaTestMode  OBJECT-TYPE
    SYNTAX      OCTET STRING
    MAX-ACCESS  read-write
    STATUS      current
    DESCRIPTION
"

"
    REFERENCE "Missing MX Record Test Mode"
    DEFVAL { "" }
    ::= {TestModes 513}

syncStatmxaTestMode  OBJECT-TYPE
    SYNTAX      OCTET STRING
    MAX-ACCESS  read-only
    STATUS      current
    DESCRIPTION
"
synchronization status for mxaTestMode
-1 - mxaTestMode could not be synchronized
 0 - synchronization not configured
 1 - out of sync - running master mode
 2 - in sync - running  mastermode
 3 - in sync - running slave mode
 4 - in sync - running master mode (wait to reach state 2)
"
    ::= {mxaTestMode 5}

syncStatStrmxaTestMode  OBJECT-TYPE
    SYNTAX      OCTET STRING
    MAX-ACCESS  read-only
    STATUS      current
    DESCRIPTION
"
synchronization status line from file assp_sync.cfg for mxaTestMode
 0 - synchronization not configured
 1 - out of sync - running master mode
 2 - in sync - running  mastermode
 3 - in sync - running slave mode
 4 - in sync - running master mode (wait to reach state 2)
"
    ::= {mxaTestMode 6}

ptrTestMode  OBJECT-TYPE
    SYNTAX      OCTET STRING
    MAX-ACCESS  read-write
    STATUS      current
    DESCRIPTION
"

"
    REFERENCE "Reversed Lookup Test Mode"
    DEFVAL { "" }
    ::= {TestModes 514}

syncStatptrTestMode  OBJECT-TYPE
    SYNTAX      OCTET STRING
    MAX-ACCESS  read-only
    STATUS      current
    DESCRIPTION
"
synchronization status for ptrTestMode
-1 - ptrTestMode could not be synchronized
 0 - synchronization not configured
 1 - out of sync - running master mode
 2 - in sync - running  mastermode
 3 - in sync - running slave mode
 4 - in sync - running master mode (wait to reach state 2)
"
    ::= {ptrTestMode 5}

syncStatStrptrTestMode  OBJECT-TYPE
    SYNTAX      OCTET STRING
    MAX-ACCESS  read-only
    STATUS      current
    DESCRIPTION
"
synchronization status line from file assp_sync.cfg for ptrTestMode
 0 - synchronization not configured
 1 - out of sync - running master mode
 2 - in sync - running  mastermode
 3 - in sync - running slave mode
 4 - in sync - running master mode (wait to reach state 2)
"
    ::= {ptrTestMode 6}

ihTestMode  OBJECT-TYPE
    SYNTAX      OCTET STRING
    MAX-ACCESS  read-write
    STATUS      current
    DESCRIPTION
"

"
    REFERENCE "Invalid Helo Test Mode"
    DEFVAL { "" }
    ::= {TestModes 515}

syncStatihTestMode  OBJECT-TYPE
    SYNTAX      OCTET STRING
    MAX-ACCESS  read-only
    STATUS      current
    DESCRIPTION
"
synchronization status for ihTestMode
-1 - ihTestMode could not be synchronized
 0 - synchronization not configured
 1 - out of sync - running master mode
 2 - in sync - running  mastermode
 3 - in sync - running slave mode
 4 - in sync - running master mode (wait to reach state 2)
"
    ::= {ihTestMode 5}

syncStatStrihTestMode  OBJECT-TYPE
    SYNTAX      OCTET STRING
    MAX-ACCESS  read-only
    STATUS      current
    DESCRIPTION
"
synchronization status line from file assp_sync.cfg for ihTestMode
 0 - synchronization not configured
 1 - out of sync - running master mode
 2 - in sync - running  mastermode
 3 - in sync - running slave mode
 4 - in sync - running master mode (wait to reach state 2)
"
    ::= {ihTestMode 6}

fhTestMode  OBJECT-TYPE
    SYNTAX      OCTET STRING
    MAX-ACCESS  read-write
    STATUS      current
    DESCRIPTION
"

"
    REFERENCE "Forged Helo Test Mode"
    DEFVAL { "" }
    ::= {TestModes 516}

syncStatfhTestMode  OBJECT-TYPE
    SYNTAX      OCTET STRING
    MAX-ACCESS  read-only
    STATUS      current
    DESCRIPTION
"
synchronization status for fhTestMode
-1 - fhTestMode could not be synchronized
 0 - synchronization not configured
 1 - out of sync - running master mode
 2 - in sync - running  mastermode
 3 - in sync - running slave mode
 4 - in sync - running master mode (wait to reach state 2)
"
    ::= {fhTestMode 5}

syncStatStrfhTestMode  OBJECT-TYPE
    SYNTAX      OCTET STRING
    MAX-ACCESS  read-only
    STATUS      current
    DESCRIPTION
"
synchronization status line from file assp_sync.cfg for fhTestMode
 0 - synchronization not configured
 1 - out of sync - running master mode
 2 - in sync - running  mastermode
 3 - in sync - running slave mode
 4 - in sync - running master mode (wait to reach state 2)
"
    ::= {fhTestMode 6}

msTestMode  OBJECT-TYPE
    SYNTAX      OCTET STRING
    MAX-ACCESS  read-write
    STATUS      current
    DESCRIPTION
"

"
    REFERENCE "Message Scoring Test Mode"
    DEFVAL { "" }
    ::= {TestModes 517}

syncStatmsTestMode  OBJECT-TYPE
    SYNTAX      OCTET STRING
    MAX-ACCESS  read-only
    STATUS      current
    DESCRIPTION
"
synchronization status for msTestMode
-1 - msTestMode could not be synchronized
 0 - synchronization not configured
 1 - out of sync - running master mode
 2 - in sync - running  mastermode
 3 - in sync - running slave mode
 4 - in sync - running master mode (wait to reach state 2)
"
    ::= {msTestMode 5}

syncStatStrmsTestMode  OBJECT-TYPE
    SYNTAX      OCTET STRING
    MAX-ACCESS  read-only
    STATUS      current
    DESCRIPTION
"
synchronization status line from file assp_sync.cfg for msTestMode
 0 - synchronization not configured
 1 - out of sync - running master mode
 2 - in sync - running  mastermode
 3 - in sync - running slave mode
 4 - in sync - running master mode (wait to reach state 2)
"
    ::= {msTestMode 6}

dkimTestMode  OBJECT-TYPE
    SYNTAX      OCTET STRING
    MAX-ACCESS  read-write
    STATUS      current
    DESCRIPTION
"

"
    REFERENCE "DKIM Test Mode"
    DEFVAL { "" }
    ::= {TestModes 518}

syncStatdkimTestMode  OBJECT-TYPE
    SYNTAX      OCTET STRING
    MAX-ACCESS  read-only
    STATUS      current
    DESCRIPTION
"
synchronization status for dkimTestMode
-1 - dkimTestMode could not be synchronized
 0 - synchronization not configured
 1 - out of sync - running master mode
 2 - in sync - running  mastermode
 3 - in sync - running slave mode
 4 - in sync - running master mode (wait to reach state 2)
"
    ::= {dkimTestMode 5}

syncStatStrdkimTestMode  OBJECT-TYPE
    SYNTAX      OCTET STRING
    MAX-ACCESS  read-only
    STATUS      current
    DESCRIPTION
"
synchronization status line from file assp_sync.cfg for dkimTestMode
 0 - synchronization not configured
 1 - out of sync - running master mode
 2 - in sync - running  mastermode
 3 - in sync - running slave mode
 4 - in sync - running master mode (wait to reach state 2)
"
    ::= {dkimTestMode 6}

pbTestMode  OBJECT-TYPE
    SYNTAX      OCTET STRING
    MAX-ACCESS  read-write
    STATUS      current
    DESCRIPTION
"

"
    REFERENCE "Penalty Box Test Mode"
    DEFVAL { "" }
    ::= {TestModes 519}

syncStatpbTestMode  OBJECT-TYPE
    SYNTAX      OCTET STRING
    MAX-ACCESS  read-only
    STATUS      current
    DESCRIPTION
"
synchronization status for pbTestMode
-1 - pbTestMode could not be synchronized
 0 - synchronization not configured
 1 - out of sync - running master mode
 2 - in sync - running  mastermode
 3 - in sync - running slave mode
 4 - in sync - running master mode (wait to reach state 2)
"
    ::= {pbTestMode 5}

syncStatStrpbTestMode  OBJECT-TYPE
    SYNTAX      OCTET STRING
    MAX-ACCESS  read-only
    STATUS      current
    DESCRIPTION
"
synchronization status line from file assp_sync.cfg for pbTestMode
 0 - synchronization not configured
 1 - out of sync - running master mode
 2 - in sync - running  mastermode
 3 - in sync - running slave mode
 4 - in sync - running master mode (wait to reach state 2)
"
    ::= {pbTestMode 6}

switchTestToScoring  OBJECT-TYPE
    SYNTAX      OCTET STRING
    MAX-ACCESS  read-write
    STATUS      current
    DESCRIPTION
"
Put the filter automatically in 'Message Scoring' when DoPenaltyMessage is set  (instead of stopping spam processing altogether).
"
    REFERENCE "Switch Testmode to Message Scoring"
    DEFVAL { "" }
    ::= {TestModes 520}

syncStatswitchTestToScoring  OBJECT-TYPE
    SYNTAX      OCTET STRING
    MAX-ACCESS  read-only
    STATUS      current
    DESCRIPTION
"
synchronization status for switchTestToScoring
-1 - switchTestToScoring could not be synchronized
 0 - synchronization not configured
 1 - out of sync - running master mode
 2 - in sync - running  mastermode
 3 - in sync - running slave mode
 4 - in sync - running master mode (wait to reach state 2)
"
    ::= {switchTestToScoring 5}

syncStatStrswitchTestToScoring  OBJECT-TYPE
    SYNTAX      OCTET STRING
    MAX-ACCESS  read-only
    STATUS      current
    DESCRIPTION
"
synchronization status line from file assp_sync.cfg for switchTestToScoring
 0 - synchronization not configured
 1 - out of sync - running master mode
 2 - in sync - running  mastermode
 3 - in sync - running slave mode
 4 - in sync - running master mode (wait to reach state 2)
"
    ::= {switchTestToScoring 6}

EmailInterface  OBJECT IDENTIFIER ::= {asspConfig 26}
EmailInterfaceOk  OBJECT-TYPE
    SYNTAX      OCTET STRING
    MAX-ACCESS  read-write
    STATUS      current
    DESCRIPTION
"
Checked means that you want ASSP to intercept and parse mail to the following usernames at any localdomains. The domain '@assp.local' is automatically a local domain and can be used for the email-interface.
  
  NOTICE: It is possible to define any MIME-header lines in any report file after the first (subject) line. This makes it possible to define MIME encoding and/or charset settings.
  If a definition of MIME encoding and/or charset is found in a report file, assp converts the report from UTF-8 in to the defined encodings.  Don't forget to terminate your MIME-header with an empty line!
  It is also possible to include files at any line of such a file, using the following directive
  # include filename
  where filename is the relative path (from C:/assp) to the included file like reports/mime-header.txt (one file per line). The line will be internaly replaced by the contents of the included file!
"
    REFERENCE "Enable Email Interface"
    DEFVAL { "1" }
    ::= {EmailInterface 521}

syncStatEmailInterfaceOk  OBJECT-TYPE
    SYNTAX      OCTET STRING
    MAX-ACCESS  read-only
    STATUS      current
    DESCRIPTION
"
synchronization status for EmailInterfaceOk
-1 - EmailInterfaceOk could not be synchronized
 0 - synchronization not configured
 1 - out of sync - running master mode
 2 - in sync - running  mastermode
 3 - in sync - running slave mode
 4 - in sync - running master mode (wait to reach state 2)
"
    ::= {EmailInterfaceOk 5}

syncStatStrEmailInterfaceOk  OBJECT-TYPE
    SYNTAX      OCTET STRING
    MAX-ACCESS  read-only
    STATUS      current
    DESCRIPTION
"
synchronization status line from file assp_sync.cfg for EmailInterfaceOk
 0 - synchronization not configured
 1 - out of sync - running master mode
 2 - in sync - running  mastermode
 3 - in sync - running slave mode
 4 - in sync - running master mode (wait to reach state 2)
"
    ::= {EmailInterfaceOk 6}

EmailAdminReportsTo  OBJECT-TYPE
    SYNTAX      OCTET STRING
    MAX-ACCESS  read-write
    STATUS      current
    DESCRIPTION
"
If set internal warnings/infos  will be sent to this address. For example: admin@domain.com
"
    REFERENCE "Admin Mail Address"
    DEFVAL { "" }
    ::= {EmailInterface 522}

syncStatEmailAdminReportsTo  OBJECT-TYPE
    SYNTAX      OCTET STRING
    MAX-ACCESS  read-only
    STATUS      current
    DESCRIPTION
"
synchronization status for EmailAdminReportsTo
-1 - EmailAdminReportsTo could not be synchronized
 0 - synchronization not configured
 1 - out of sync - running master mode
 2 - in sync - running  mastermode
 3 - in sync - running slave mode
 4 - in sync - running master mode (wait to reach state 2)
"
    ::= {EmailAdminReportsTo 5}

syncStatStrEmailAdminReportsTo  OBJECT-TYPE
    SYNTAX      OCTET STRING
    MAX-ACCESS  read-only
    STATUS      current
    DESCRIPTION
"
synchronization status line from file assp_sync.cfg for EmailAdminReportsTo
 0 - synchronization not configured
 1 - out of sync - running master mode
 2 - in sync - running  mastermode
 3 - in sync - running slave mode
 4 - in sync - running master mode (wait to reach state 2)
"
    ::= {EmailAdminReportsTo 6}

EmailReportDestination  OBJECT-TYPE
    SYNTAX      OCTET STRING
    MAX-ACCESS  read-write
    STATUS      current
    DESCRIPTION
"
Port to connect to when Email Interface or Block reports are send. If blank they go to the main smtpDestination.
  If you need to connect to the EmailReportDestination host using native SSL, write 'SSL:' in front of the IP/host definition. In this case the Perl module  must be installed and enabled ( useIOSocketSSL ).
  eg 10.0.1.3:1025 SSL:10.0.1.3:465, etc.
"
    REFERENCE "Email Interface Reports Destination"
    DEFVAL { "" }
    ::= {EmailInterface 523}

syncStatEmailReportDestination  OBJECT-TYPE
    SYNTAX      OCTET STRING
    MAX-ACCESS  read-only
    STATUS      current
    DESCRIPTION
"
synchronization status for EmailReportDestination
-1 - EmailReportDestination could not be synchronized
 0 - synchronization not configured
 1 - out of sync - running master mode
 2 - in sync - running  mastermode
 3 - in sync - running slave mode
 4 - in sync - running master mode (wait to reach state 2)
"
    ::= {EmailReportDestination 5}

syncStatStrEmailReportDestination  OBJECT-TYPE
    SYNTAX      OCTET STRING
    MAX-ACCESS  read-only
    STATUS      current
    DESCRIPTION
"
synchronization status line from file assp_sync.cfg for EmailReportDestination
 0 - synchronization not configured
 1 - out of sync - running master mode
 2 - in sync - running  mastermode
 3 - in sync - running slave mode
 4 - in sync - running master mode (wait to reach state 2)
"
    ::= {EmailReportDestination 6}

EmailHelp  OBJECT-TYPE
    SYNTAX      OCTET STRING
    MAX-ACCESS  read-write
    STATUS      current
    DESCRIPTION
"
Any mail sent by local/authenticated users to this username will be interpreted as a request for help. Do not put the full address here, just the user part. For example: assphelp
"
    REFERENCE "Help Address"
    DEFVAL { "assphelp" }
    ::= {EmailInterface 524}

syncStatEmailHelp  OBJECT-TYPE
    SYNTAX      OCTET STRING
    MAX-ACCESS  read-only
    STATUS      current
    DESCRIPTION
"
synchronization status for EmailHelp
-1 - EmailHelp could not be synchronized
 0 - synchronization not configured
 1 - out of sync - running master mode
 2 - in sync - running  mastermode
 3 - in sync - running slave mode
 4 - in sync - running master mode (wait to reach state 2)
"
    ::= {EmailHelp 5}

syncStatStrEmailHelp  OBJECT-TYPE
    SYNTAX      OCTET STRING
    MAX-ACCESS  read-only
    STATUS      current
    DESCRIPTION
"
synchronization status line from file assp_sync.cfg for EmailHelp
 0 - synchronization not configured
 1 - out of sync - running master mode
 2 - in sync - running  mastermode
 3 - in sync - running slave mode
 4 - in sync - running master mode (wait to reach state 2)
"
    ::= {EmailHelp 6}

EmailAdmins  OBJECT-TYPE
    SYNTAX      OCTET STRING
    MAX-ACCESS  read-write
    STATUS      current
    DESCRIPTION
"
Mail from any of these addresses can add/remove to/from redlist, spamlovers, noprocessing, blacklist. May request an EmailBlockReport for a list of users. Accepts specific addresses (user@example.com), user parts (user) or entire domains (@example.com)
"
    REFERENCE "Authorized Addresses*"
    DEFVAL { "" }
    ::= {EmailInterface 525}

syncStatEmailAdmins  OBJECT-TYPE
    SYNTAX      OCTET STRING
    MAX-ACCESS  read-only
    STATUS      current
    DESCRIPTION
"
synchronization status for EmailAdmins
-1 - EmailAdmins could not be synchronized
 0 - synchronization not configured
 1 - out of sync - running master mode
 2 - in sync - running  mastermode
 3 - in sync - running slave mode
 4 - in sync - running master mode (wait to reach state 2)
"
    ::= {EmailAdmins 5}

syncStatStrEmailAdmins  OBJECT-TYPE
    SYNTAX      OCTET STRING
    MAX-ACCESS  read-only
    STATUS      current
    DESCRIPTION
"
synchronization status line from file assp_sync.cfg for EmailAdmins
 0 - synchronization not configured
 1 - out of sync - running master mode
 2 - in sync - running  mastermode
 3 - in sync - running slave mode
 4 - in sync - running master mode (wait to reach state 2)
"
    ::= {EmailAdmins 6}

EmailSenderOK  OBJECT-TYPE
    SYNTAX      OCTET STRING
    MAX-ACCESS  read-write
    STATUS      current
    DESCRIPTION
"
Allow these external domains/addresses to report to the email interface (NOT RECOMMENDED). The reply address for the reports must be set to a local one.  By default, ASSP only accepts reports from local or authenticated users. Accepts specific addresses (user@domain.com), user parts (user) or entire domains (@domain.com)
"
    REFERENCE "Accept Mails (Reports) from these external addresses*"
    DEFVAL { "" }
    ::= {EmailInterface 526}

syncStatEmailSenderOK  OBJECT-TYPE
    SYNTAX      OCTET STRING
    MAX-ACCESS  read-only
    STATUS      current
    DESCRIPTION
"
synchronization status for EmailSenderOK
-1 - EmailSenderOK could not be synchronized
 0 - synchronization not configured
 1 - out of sync - running master mode
 2 - in sync - running  mastermode
 3 - in sync - running slave mode
 4 - in sync - running master mode (wait to reach state 2)
"
    ::= {EmailSenderOK 5}

syncStatStrEmailSenderOK  OBJECT-TYPE
    SYNTAX      OCTET STRING
    MAX-ACCESS  read-only
    STATUS      current
    DESCRIPTION
"
synchronization status line from file assp_sync.cfg for EmailSenderOK
 0 - synchronization not configured
 1 - out of sync - running master mode
 2 - in sync - running  mastermode
 3 - in sync - running slave mode
 4 - in sync - running master mode (wait to reach state 2)
"
    ::= {EmailSenderOK 6}

EmailSenderNotOK  OBJECT-TYPE
    SYNTAX      OCTET STRING
    MAX-ACCESS  read-write
    STATUS      current
    DESCRIPTION
"
Mail from any of these addresses are not accepted from Email Interface, except 'Help Report', 'Analyze Report' and 'Block Report/Resend'. Accepts specific addresses (user@example.com), user parts (user) or entire domains (@example.com). The user will get informed about the denied request.
"
    REFERENCE "Not Authorized Addresses*"
    DEFVAL { "" }
    ::= {EmailInterface 527}

syncStatEmailSenderNotOK  OBJECT-TYPE
    SYNTAX      OCTET STRING
    MAX-ACCESS  read-only
    STATUS      current
    DESCRIPTION
"
synchronization status for EmailSenderNotOK
-1 - EmailSenderNotOK could not be synchronized
 0 - synchronization not configured
 1 - out of sync - running master mode
 2 - in sync - running  mastermode
 3 - in sync - running slave mode
 4 - in sync - running master mode (wait to reach state 2)
"
    ::= {EmailSenderNotOK 5}

syncStatStrEmailSenderNotOK  OBJECT-TYPE
    SYNTAX      OCTET STRING
    MAX-ACCESS  read-only
    STATUS      current
    DESCRIPTION
"
synchronization status line from file assp_sync.cfg for EmailSenderNotOK
 0 - synchronization not configured
 1 - out of sync - running master mode
 2 - in sync - running  mastermode
 3 - in sync - running slave mode
 4 - in sync - running master mode (wait to reach state 2)
"
    ::= {EmailSenderNotOK 6}

EmailSpam  OBJECT-TYPE
    SYNTAX      OCTET STRING
    MAX-ACCESS  read-write
    STATUS      current
    DESCRIPTION
"
Any mail sent or forwarded by local/authenticated users to this username will be interpreted as a spam report. Multiple attachments get truncated to MaxBytesReports. Do not put the full address here, just the user part.
   For example: asspspam . Use a fake domain like @assp.local when you send the email- so the full address would be then asspspam@assp.local. 
   You can sent multiple mails as attachments and/or zipped file(s). Each attached email-file must have the extension defined in 'maillogExt'. In this case only the attachments will be processed. To use this multi-attachment-feature an installed  module in PERL is needed. It is also possible to send MS-outlook '.msg' files (possibly zipped). To use this MS-outlook-feature in addition an installed  module in PERL is needed.
"
    REFERENCE "Report Spam Address"
    DEFVAL { "asspspam" }
    ::= {EmailInterface 528}

syncStatEmailSpam  OBJECT-TYPE
    SYNTAX      OCTET STRING
    MAX-ACCESS  read-only
    STATUS      current
    DESCRIPTION
"
synchronization status for EmailSpam
-1 - EmailSpam could not be synchronized
 0 - synchronization not configured
 1 - out of sync - running master mode
 2 - in sync - running  mastermode
 3 - in sync - running slave mode
 4 - in sync - running master mode (wait to reach state 2)
"
    ::= {EmailSpam 5}

syncStatStrEmailSpam  OBJECT-TYPE
    SYNTAX      OCTET STRING
    MAX-ACCESS  read-only
    STATUS      current
    DESCRIPTION
"
synchronization status line from file assp_sync.cfg for EmailSpam
 0 - synchronization not configured
 1 - out of sync - running master mode
 2 - in sync - running  mastermode
 3 - in sync - running slave mode
 4 - in sync - running master mode (wait to reach state 2)
"
    ::= {EmailSpam 6}

EmailHam  OBJECT-TYPE
    SYNTAX      OCTET STRING
    MAX-ACCESS  read-write
    STATUS      current
    DESCRIPTION
"
Any mail sent or forwarded by local/authenticated users to this username will be interpreted as a false-positive report. Multiple attachments get truncated to MaxBytesReports. Do not put the full address here, just the user part.
   For example: asspnotspam . Use a fake domain like @assp.local when you send the email- so the full address would be then asspspam@assp.local. 
   You can sent multiple mails as attachments and/or zipped file(s). Each attached email-file must have the extension defined in 'maillogExt'. In this case only the attachments will be processed. To use this multi-attachment-feature an installed  module in PERL is needed. It is also possible to send MS-outlook '.msg' files (possibly zipped). To use this MS-outlook-feature in addition an installed  module in PERL is needed.
"
    REFERENCE "Report Ham (Not-Spam) Address"
    DEFVAL { "asspnotspam" }
    ::= {EmailInterface 529}

syncStatEmailHam  OBJECT-TYPE
    SYNTAX      OCTET STRING
    MAX-ACCESS  read-only
    STATUS      current
    DESCRIPTION
"
synchronization status for EmailHam
-1 - EmailHam could not be synchronized
 0 - synchronization not configured
 1 - out of sync - running master mode
 2 - in sync - running  mastermode
 3 - in sync - running slave mode
 4 - in sync - running master mode (wait to reach state 2)
"
    ::= {EmailHam 5}

syncStatStrEmailHam  OBJECT-TYPE
    SYNTAX      OCTET STRING
    MAX-ACCESS  read-only
    STATUS      current
    DESCRIPTION
"
synchronization status line from file assp_sync.cfg for EmailHam
 0 - synchronization not configured
 1 - out of sync - running master mode
 2 - in sync - running  mastermode
 3 - in sync - running slave mode
 4 - in sync - running master mode (wait to reach state 2)
"
    ::= {EmailHam 6}

EmailErrorsReply  OBJECT-TYPE
    SYNTAX      OCTET STRING
    MAX-ACCESS  read-write
    STATUS      current
    DESCRIPTION
"

"
    REFERENCE "Reply to Spam/Not-Spam Reports"
    DEFVAL { "1" }
    ::= {EmailInterface 530}

syncStatEmailErrorsReply  OBJECT-TYPE
    SYNTAX      OCTET STRING
    MAX-ACCESS  read-only
    STATUS      current
    DESCRIPTION
"
synchronization status for EmailErrorsReply
-1 - EmailErrorsReply could not be synchronized
 0 - synchronization not configured
 1 - out of sync - running master mode
 2 - in sync - running  mastermode
 3 - in sync - running slave mode
 4 - in sync - running master mode (wait to reach state 2)
"
    ::= {EmailErrorsReply 5}

syncStatStrEmailErrorsReply  OBJECT-TYPE
    SYNTAX      OCTET STRING
    MAX-ACCESS  read-only
    STATUS      current
    DESCRIPTION
"
synchronization status line from file assp_sync.cfg for EmailErrorsReply
 0 - synchronization not configured
 1 - out of sync - running master mode
 2 - in sync - running  mastermode
 3 - in sync - running slave mode
 4 - in sync - running master mode (wait to reach state 2)
"
    ::= {EmailErrorsReply 6}

EmailErrorsTo  OBJECT-TYPE
    SYNTAX      OCTET STRING
    MAX-ACCESS  read-write
    STATUS      current
    DESCRIPTION
"
Email sent from ASSP acknowledging your submissions will be sent to this address. For example: admin@domain.com
"
    REFERENCE "Send Copy of Spam/Ham-Reports TO"
    DEFVAL { "" }
    ::= {EmailInterface 531}

syncStatEmailErrorsTo  OBJECT-TYPE
    SYNTAX      OCTET STRING
    MAX-ACCESS  read-only
    STATUS      current
    DESCRIPTION
"
synchronization status for EmailErrorsTo
-1 - EmailErrorsTo could not be synchronized
 0 - synchronization not configured
 1 - out of sync - running master mode
 2 - in sync - running  mastermode
 3 - in sync - running slave mode
 4 - in sync - running master mode (wait to reach state 2)
"
    ::= {EmailErrorsTo 5}

syncStatStrEmailErrorsTo  OBJECT-TYPE
    SYNTAX      OCTET STRING
    MAX-ACCESS  read-only
    STATUS      current
    DESCRIPTION
"
synchronization status line from file assp_sync.cfg for EmailErrorsTo
 0 - synchronization not configured
 1 - out of sync - running master mode
 2 - in sync - running  mastermode
 3 - in sync - running slave mode
 4 - in sync - running master mode (wait to reach state 2)
"
    ::= {EmailErrorsTo 6}

EmailErrorsModifyWhite  OBJECT-TYPE
    SYNTAX      OCTET STRING
    MAX-ACCESS  read-write
    STATUS      current
    DESCRIPTION
"
If set to 'modify whitelist' Ham Reports will add email addresses to the Whitelist, Spam Reports will remove addresses from the Whitelist, also a copy of a file in the GUI to correctedspam (remove) and correctednotspam (add) will modify the Whitelist for the found addresses. If set to 'show whitelist' Spam Reports will show if addresses are whitelisted.
"
    REFERENCE "Combined Spam/Ham Report &amp; Whitelist Check"
    DEFVAL { "1" }
    ::= {EmailInterface 532}

syncStatEmailErrorsModifyWhite  OBJECT-TYPE
    SYNTAX      OCTET STRING
    MAX-ACCESS  read-only
    STATUS      current
    DESCRIPTION
"
synchronization status for EmailErrorsModifyWhite
-1 - EmailErrorsModifyWhite could not be synchronized
 0 - synchronization not configured
 1 - out of sync - running master mode
 2 - in sync - running  mastermode
 3 - in sync - running slave mode
 4 - in sync - running master mode (wait to reach state 2)
"
    ::= {EmailErrorsModifyWhite 5}

syncStatStrEmailErrorsModifyWhite  OBJECT-TYPE
    SYNTAX      OCTET STRING
    MAX-ACCESS  read-only
    STATUS      current
    DESCRIPTION
"
synchronization status line from file assp_sync.cfg for EmailErrorsModifyWhite
 0 - synchronization not configured
 1 - out of sync - running master mode
 2 - in sync - running  mastermode
 3 - in sync - running slave mode
 4 - in sync - running master mode (wait to reach state 2)
"
    ::= {EmailErrorsModifyWhite 6}

EmailWhitelistAdd  OBJECT-TYPE
    SYNTAX      OCTET STRING
    MAX-ACCESS  read-write
    STATUS      current
    DESCRIPTION
"
Any mail sent by local/authenticated users to this username will be interpreted as a request to add addresses to the whitelist. Do not put the full address here, just the user part. 
  For example: asspwhite
  If an address is added to whitelist, it will be removed from the Personal Blacklist of the sending user.
"
    REFERENCE "Add to Whitelist Address"
    DEFVAL { "asspwhite" }
    ::= {EmailInterface 533}

syncStatEmailWhitelistAdd  OBJECT-TYPE
    SYNTAX      OCTET STRING
    MAX-ACCESS  read-only
    STATUS      current
    DESCRIPTION
"
synchronization status for EmailWhitelistAdd
-1 - EmailWhitelistAdd could not be synchronized
 0 - synchronization not configured
 1 - out of sync - running master mode
 2 - in sync - running  mastermode
 3 - in sync - running slave mode
 4 - in sync - running master mode (wait to reach state 2)
"
    ::= {EmailWhitelistAdd 5}

syncStatStrEmailWhitelistAdd  OBJECT-TYPE
    SYNTAX      OCTET STRING
    MAX-ACCESS  read-only
    STATUS      current
    DESCRIPTION
"
synchronization status line from file assp_sync.cfg for EmailWhitelistAdd
 0 - synchronization not configured
 1 - out of sync - running master mode
 2 - in sync - running  mastermode
 3 - in sync - running slave mode
 4 - in sync - running master mode (wait to reach state 2)
"
    ::= {EmailWhitelistAdd 6}

EmailWhitelistRemove  OBJECT-TYPE
    SYNTAX      OCTET STRING
    MAX-ACCESS  read-write
    STATUS      current
    DESCRIPTION
"
Any mail sent by local/authenticated users to this username will be interpreted as a request to remove addresses from the whitelist. Do not put the full address here, just the user part. For example: asspnotwhite
"
    REFERENCE "Remove from Whitelist Address"
    DEFVAL { "asspnotwhite" }
    ::= {EmailInterface 534}

syncStatEmailWhitelistRemove  OBJECT-TYPE
    SYNTAX      OCTET STRING
    MAX-ACCESS  read-only
    STATUS      current
    DESCRIPTION
"
synchronization status for EmailWhitelistRemove
-1 - EmailWhitelistRemove could not be synchronized
 0 - synchronization not configured
 1 - out of sync - running master mode
 2 - in sync - running  mastermode
 3 - in sync - running slave mode
 4 - in sync - running master mode (wait to reach state 2)
"
    ::= {EmailWhitelistRemove 5}

syncStatStrEmailWhitelistRemove  OBJECT-TYPE
    SYNTAX      OCTET STRING
    MAX-ACCESS  read-only
    STATUS      current
    DESCRIPTION
"
synchronization status line from file assp_sync.cfg for EmailWhitelistRemove
 0 - synchronization not configured
 1 - out of sync - running master mode
 2 - in sync - running  mastermode
 3 - in sync - running slave mode
 4 - in sync - running master mode (wait to reach state 2)
"
    ::= {EmailWhitelistRemove 6}

EmailWhitelistReply  OBJECT-TYPE
    SYNTAX      OCTET STRING
    MAX-ACCESS  read-write
    STATUS      current
    DESCRIPTION
"

"
    REFERENCE "Reply to Add to/Remove from Whitelist"
    DEFVAL { "1" }
    ::= {EmailInterface 535}

syncStatEmailWhitelistReply  OBJECT-TYPE
    SYNTAX      OCTET STRING
    MAX-ACCESS  read-only
    STATUS      current
    DESCRIPTION
"
synchronization status for EmailWhitelistReply
-1 - EmailWhitelistReply could not be synchronized
 0 - synchronization not configured
 1 - out of sync - running master mode
 2 - in sync - running  mastermode
 3 - in sync - running slave mode
 4 - in sync - running master mode (wait to reach state 2)
"
    ::= {EmailWhitelistReply 5}

syncStatStrEmailWhitelistReply  OBJECT-TYPE
    SYNTAX      OCTET STRING
    MAX-ACCESS  read-only
    STATUS      current
    DESCRIPTION
"
synchronization status line from file assp_sync.cfg for EmailWhitelistReply
 0 - synchronization not configured
 1 - out of sync - running master mode
 2 - in sync - running  mastermode
 3 - in sync - running slave mode
 4 - in sync - running master mode (wait to reach state 2)
"
    ::= {EmailWhitelistReply 6}

EmailWhitelistTo  OBJECT-TYPE
    SYNTAX      OCTET STRING
    MAX-ACCESS  read-write
    STATUS      current
    DESCRIPTION
"
Email sent from ASSP acknowledging your submissions will be sent to this address. For example: admin@domain.com
"
    REFERENCE "Send Copy of Whitelist-Reports TO"
    DEFVAL { "" }
    ::= {EmailInterface 536}

syncStatEmailWhitelistTo  OBJECT-TYPE
    SYNTAX      OCTET STRING
    MAX-ACCESS  read-only
    STATUS      current
    DESCRIPTION
"
synchronization status for EmailWhitelistTo
-1 - EmailWhitelistTo could not be synchronized
 0 - synchronization not configured
 1 - out of sync - running master mode
 2 - in sync - running  mastermode
 3 - in sync - running slave mode
 4 - in sync - running master mode (wait to reach state 2)
"
    ::= {EmailWhitelistTo 5}

syncStatStrEmailWhitelistTo  OBJECT-TYPE
    SYNTAX      OCTET STRING
    MAX-ACCESS  read-only
    STATUS      current
    DESCRIPTION
"
synchronization status line from file assp_sync.cfg for EmailWhitelistTo
 0 - synchronization not configured
 1 - out of sync - running master mode
 2 - in sync - running  mastermode
 3 - in sync - running slave mode
 4 - in sync - running master mode (wait to reach state 2)
"
    ::= {EmailWhitelistTo 6}

EmailRedlistAdd  OBJECT-TYPE
    SYNTAX      OCTET STRING
    MAX-ACCESS  read-write
    STATUS      current
    DESCRIPTION
"
Any mail sent by local/authenticated users to this username will be interpreted as a request to add the sender address to the redlist. Only the users defined in EmailRedlistTo, EmailAdmins and EmailAdminReportsTo are able to define a list of email addresses in the mail body.  Do not put the full address here, just the user part. For example: asspred.
"
    REFERENCE "Add to Redlist Address"
    DEFVAL { "asspred" }
    ::= {EmailInterface 537}

syncStatEmailRedlistAdd  OBJECT-TYPE
    SYNTAX      OCTET STRING
    MAX-ACCESS  read-only
    STATUS      current
    DESCRIPTION
"
synchronization status for EmailRedlistAdd
-1 - EmailRedlistAdd could not be synchronized
 0 - synchronization not configured
 1 - out of sync - running master mode
 2 - in sync - running  mastermode
 3 - in sync - running slave mode
 4 - in sync - running master mode (wait to reach state 2)
"
    ::= {EmailRedlistAdd 5}

syncStatStrEmailRedlistAdd  OBJECT-TYPE
    SYNTAX      OCTET STRING
    MAX-ACCESS  read-only
    STATUS      current
    DESCRIPTION
"
synchronization status line from file assp_sync.cfg for EmailRedlistAdd
 0 - synchronization not configured
 1 - out of sync - running master mode
 2 - in sync - running  mastermode
 3 - in sync - running slave mode
 4 - in sync - running master mode (wait to reach state 2)
"
    ::= {EmailRedlistAdd 6}

EmailRedlistRemove  OBJECT-TYPE
    SYNTAX      OCTET STRING
    MAX-ACCESS  read-write
    STATUS      current
    DESCRIPTION
"
Any mail sent by local/authenticated users to this username will be interpreted as a request to remove the sender address from the redlist. Only the users defined in EmailRedlistTo, EmailAdmins and EmailAdminReportsTo are able to define a list of email addresses in the mail body. 
  Do not put the full address here, just the user part. For example: asspnotred
"
    REFERENCE "Remove from Redlist Addresses"
    DEFVAL { "asspnotred" }
    ::= {EmailInterface 538}

syncStatEmailRedlistRemove  OBJECT-TYPE
    SYNTAX      OCTET STRING
    MAX-ACCESS  read-only
    STATUS      current
    DESCRIPTION
"
synchronization status for EmailRedlistRemove
-1 - EmailRedlistRemove could not be synchronized
 0 - synchronization not configured
 1 - out of sync - running master mode
 2 - in sync - running  mastermode
 3 - in sync - running slave mode
 4 - in sync - running master mode (wait to reach state 2)
"
    ::= {EmailRedlistRemove 5}

syncStatStrEmailRedlistRemove  OBJECT-TYPE
    SYNTAX      OCTET STRING
    MAX-ACCESS  read-only
    STATUS      current
    DESCRIPTION
"
synchronization status line from file assp_sync.cfg for EmailRedlistRemove
 0 - synchronization not configured
 1 - out of sync - running master mode
 2 - in sync - running  mastermode
 3 - in sync - running slave mode
 4 - in sync - running master mode (wait to reach state 2)
"
    ::= {EmailRedlistRemove 6}

EmailRedlistReply  OBJECT-TYPE
    SYNTAX      OCTET STRING
    MAX-ACCESS  read-write
    STATUS      current
    DESCRIPTION
"

"
    REFERENCE "Reply to Add to/Remove from Redlist"
    DEFVAL { "1" }
    ::= {EmailInterface 539}

syncStatEmailRedlistReply  OBJECT-TYPE
    SYNTAX      OCTET STRING
    MAX-ACCESS  read-only
    STATUS      current
    DESCRIPTION
"
synchronization status for EmailRedlistReply
-1 - EmailRedlistReply could not be synchronized
 0 - synchronization not configured
 1 - out of sync - running master mode
 2 - in sync - running  mastermode
 3 - in sync - running slave mode
 4 - in sync - running master mode (wait to reach state 2)
"
    ::= {EmailRedlistReply 5}

syncStatStrEmailRedlistReply  OBJECT-TYPE
    SYNTAX      OCTET STRING
    MAX-ACCESS  read-only
    STATUS      current
    DESCRIPTION
"
synchronization status line from file assp_sync.cfg for EmailRedlistReply
 0 - synchronization not configured
 1 - out of sync - running master mode
 2 - in sync - running  mastermode
 3 - in sync - running slave mode
 4 - in sync - running master mode (wait to reach state 2)
"
    ::= {EmailRedlistReply 6}

EmailRedlistTo  OBJECT-TYPE
    SYNTAX      OCTET STRING
    MAX-ACCESS  read-write
    STATUS      current
    DESCRIPTION
"
Email sent from ASSP acknowledging your submissions will be sent to this address. For example: admin@domain.com
"
    REFERENCE "Send Copy of Redlist-Reports TO"
    DEFVAL { "" }
    ::= {EmailInterface 540}

syncStatEmailRedlistTo  OBJECT-TYPE
    SYNTAX      OCTET STRING
    MAX-ACCESS  read-only
    STATUS      current
    DESCRIPTION
"
synchronization status for EmailRedlistTo
-1 - EmailRedlistTo could not be synchronized
 0 - synchronization not configured
 1 - out of sync - running master mode
 2 - in sync - running  mastermode
 3 - in sync - running slave mode
 4 - in sync - running master mode (wait to reach state 2)
"
    ::= {EmailRedlistTo 5}

syncStatStrEmailRedlistTo  OBJECT-TYPE
    SYNTAX      OCTET STRING
    MAX-ACCESS  read-only
    STATUS      current
    DESCRIPTION
"
synchronization status line from file assp_sync.cfg for EmailRedlistTo
 0 - synchronization not configured
 1 - out of sync - running master mode
 2 - in sync - running  mastermode
 3 - in sync - running slave mode
 4 - in sync - running master mode (wait to reach state 2)
"
    ::= {EmailRedlistTo 6}

EmailSpamLoverAdd  OBJECT-TYPE
    SYNTAX      OCTET STRING
    MAX-ACCESS  read-write
    STATUS      current
    DESCRIPTION
"
Any mail sent by local/authenticated users to this username will be interpreted as a request to add the sender address to spamLovers. Only the users defined in EmailSpamLoverTo, EmailAdmins and EmailAdminReportsTo are able to define a list of email addresses in the mail body. Do not put the full address here, just the user part. For example: asspspamlover. To use this option, you have to configure spamLovers with 'file:...' for example 'file:files/spamlovers.txt' !
"
    REFERENCE "Add to SpamLover Addresses"
    DEFVAL { "asspspamlover" }
    ::= {EmailInterface 541}

syncStatEmailSpamLoverAdd  OBJECT-TYPE
    SYNTAX      OCTET STRING
    MAX-ACCESS  read-only
    STATUS      current
    DESCRIPTION
"
synchronization status for EmailSpamLoverAdd
-1 - EmailSpamLoverAdd could not be synchronized
 0 - synchronization not configured
 1 - out of sync - running master mode
 2 - in sync - running  mastermode
 3 - in sync - running slave mode
 4 - in sync - running master mode (wait to reach state 2)
"
    ::= {EmailSpamLoverAdd 5}

syncStatStrEmailSpamLoverAdd  OBJECT-TYPE
    SYNTAX      OCTET STRING
    MAX-ACCESS  read-only
    STATUS      current
    DESCRIPTION
"
synchronization status line from file assp_sync.cfg for EmailSpamLoverAdd
 0 - synchronization not configured
 1 - out of sync - running master mode
 2 - in sync - running  mastermode
 3 - in sync - running slave mode
 4 - in sync - running master mode (wait to reach state 2)
"
    ::= {EmailSpamLoverAdd 6}

EmailSpamLoverRemove  OBJECT-TYPE
    SYNTAX      OCTET STRING
    MAX-ACCESS  read-write
    STATUS      current
    DESCRIPTION
"
Any mail sent by local/authenticated users to this username will be interpreted as a request to remove the sender address from spamLovers. Only the users defined in EmailSpamLoverTo, EmailAdmins and EmailAdminReportsTo are able to define a list of email addresses in the mail body. 
  Do not put the full address here, just the user part. For example: asspnotspamlover
"
    REFERENCE "Remove from SpamLover Addresses"
    DEFVAL { "asspnotspamlover" }
    ::= {EmailInterface 542}

syncStatEmailSpamLoverRemove  OBJECT-TYPE
    SYNTAX      OCTET STRING
    MAX-ACCESS  read-only
    STATUS      current
    DESCRIPTION
"
synchronization status for EmailSpamLoverRemove
-1 - EmailSpamLoverRemove could not be synchronized
 0 - synchronization not configured
 1 - out of sync - running master mode
 2 - in sync - running  mastermode
 3 - in sync - running slave mode
 4 - in sync - running master mode (wait to reach state 2)
"
    ::= {EmailSpamLoverRemove 5}

syncStatStrEmailSpamLoverRemove  OBJECT-TYPE
    SYNTAX      OCTET STRING
    MAX-ACCESS  read-only
    STATUS      current
    DESCRIPTION
"
synchronization status line from file assp_sync.cfg for EmailSpamLoverRemove
 0 - synchronization not configured
 1 - out of sync - running master mode
 2 - in sync - running  mastermode
 3 - in sync - running slave mode
 4 - in sync - running master mode (wait to reach state 2)
"
    ::= {EmailSpamLoverRemove 6}

EmailSpamLoverReply  OBJECT-TYPE
    SYNTAX      OCTET STRING
    MAX-ACCESS  read-write
    STATUS      current
    DESCRIPTION
"

"
    REFERENCE "Reply to Add to/Remove from SpamLovers"
    DEFVAL { "1" }
    ::= {EmailInterface 543}

syncStatEmailSpamLoverReply  OBJECT-TYPE
    SYNTAX      OCTET STRING
    MAX-ACCESS  read-only
    STATUS      current
    DESCRIPTION
"
synchronization status for EmailSpamLoverReply
-1 - EmailSpamLoverReply could not be synchronized
 0 - synchronization not configured
 1 - out of sync - running master mode
 2 - in sync - running  mastermode
 3 - in sync - running slave mode
 4 - in sync - running master mode (wait to reach state 2)
"
    ::= {EmailSpamLoverReply 5}

syncStatStrEmailSpamLoverReply  OBJECT-TYPE
    SYNTAX      OCTET STRING
    MAX-ACCESS  read-only
    STATUS      current
    DESCRIPTION
"
synchronization status line from file assp_sync.cfg for EmailSpamLoverReply
 0 - synchronization not configured
 1 - out of sync - running master mode
 2 - in sync - running  mastermode
 3 - in sync - running slave mode
 4 - in sync - running master mode (wait to reach state 2)
"
    ::= {EmailSpamLoverReply 6}

EmailSpamLoverTo  OBJECT-TYPE
    SYNTAX      OCTET STRING
    MAX-ACCESS  read-write
    STATUS      current
    DESCRIPTION
"
Email sent from ASSP acknowledging your submissions will be sent to this address. For example: admin@domain.com
"
    REFERENCE "Send Copy of Spamlover-Reports TO"
    DEFVAL { "" }
    ::= {EmailInterface 544}

syncStatEmailSpamLoverTo  OBJECT-TYPE
    SYNTAX      OCTET STRING
    MAX-ACCESS  read-only
    STATUS      current
    DESCRIPTION
"
synchronization status for EmailSpamLoverTo
-1 - EmailSpamLoverTo could not be synchronized
 0 - synchronization not configured
 1 - out of sync - running master mode
 2 - in sync - running  mastermode
 3 - in sync - running slave mode
 4 - in sync - running master mode (wait to reach state 2)
"
    ::= {EmailSpamLoverTo 5}

syncStatStrEmailSpamLoverTo  OBJECT-TYPE
    SYNTAX      OCTET STRING
    MAX-ACCESS  read-only
    STATUS      current
    DESCRIPTION
"
synchronization status line from file assp_sync.cfg for EmailSpamLoverTo
 0 - synchronization not configured
 1 - out of sync - running master mode
 2 - in sync - running  mastermode
 3 - in sync - running slave mode
 4 - in sync - running master mode (wait to reach state 2)
"
    ::= {EmailSpamLoverTo 6}

EmailNoProcessingAdd  OBJECT-TYPE
    SYNTAX      OCTET STRING
    MAX-ACCESS  read-write
    STATUS      current
    DESCRIPTION
"
Any mail sent by local/authenticated users to this username will be interpreted as a request to add the sender address to the noProcessing addresses. Only the users defined in EmailNoProcessingTo, EmailAdmins and EmailAdminReportsTo are able to define a list of email addresses in the mail body. Do not put the full address here, just the user part. For example: asspnpadd. To use this option, you have to configure noProcessing with 'file:...' for example 'file:files/noprocessing.txt' !
"
    REFERENCE "Add to NoProcessing Addresses"
    DEFVAL { "asspnpadd" }
    ::= {EmailInterface 545}

syncStatEmailNoProcessingAdd  OBJECT-TYPE
    SYNTAX      OCTET STRING
    MAX-ACCESS  read-only
    STATUS      current
    DESCRIPTION
"
synchronization status for EmailNoProcessingAdd
-1 - EmailNoProcessingAdd could not be synchronized
 0 - synchronization not configured
 1 - out of sync - running master mode
 2 - in sync - running  mastermode
 3 - in sync - running slave mode
 4 - in sync - running master mode (wait to reach state 2)
"
    ::= {EmailNoProcessingAdd 5}

syncStatStrEmailNoProcessingAdd  OBJECT-TYPE
    SYNTAX      OCTET STRING
    MAX-ACCESS  read-only
    STATUS      current
    DESCRIPTION
"
synchronization status line from file assp_sync.cfg for EmailNoProcessingAdd
 0 - synchronization not configured
 1 - out of sync - running master mode
 2 - in sync - running  mastermode
 3 - in sync - running slave mode
 4 - in sync - running master mode (wait to reach state 2)
"
    ::= {EmailNoProcessingAdd 6}

EmailNoProcessingRemove  OBJECT-TYPE
    SYNTAX      OCTET STRING
    MAX-ACCESS  read-write
    STATUS      current
    DESCRIPTION
"
Any mail sent by local/authenticated users to this username will be interpreted as a request to remove the sender address from noProcessing .
  Do not put the full address here, just the user part. Only the users defined in EmailNoProcessingTo, EmailAdmins and EmailAdminReportsTo are able to define a list of email addresses in the mail body. For example: asspnprem. To use this option, you have to configure noProcessing with 'file:...' for example 'file:files/noprocessing.txt' !
"
    REFERENCE "Remove from noProcessing Addresses"
    DEFVAL { "asspnprem" }
    ::= {EmailInterface 546}

syncStatEmailNoProcessingRemove  OBJECT-TYPE
    SYNTAX      OCTET STRING
    MAX-ACCESS  read-only
    STATUS      current
    DESCRIPTION
"
synchronization status for EmailNoProcessingRemove
-1 - EmailNoProcessingRemove could not be synchronized
 0 - synchronization not configured
 1 - out of sync - running master mode
 2 - in sync - running  mastermode
 3 - in sync - running slave mode
 4 - in sync - running master mode (wait to reach state 2)
"
    ::= {EmailNoProcessingRemove 5}

syncStatStrEmailNoProcessingRemove  OBJECT-TYPE
    SYNTAX      OCTET STRING
    MAX-ACCESS  read-only
    STATUS      current
    DESCRIPTION
"
synchronization status line from file assp_sync.cfg for EmailNoProcessingRemove
 0 - synchronization not configured
 1 - out of sync - running master mode
 2 - in sync - running  mastermode
 3 - in sync - running slave mode
 4 - in sync - running master mode (wait to reach state 2)
"
    ::= {EmailNoProcessingRemove 6}

EmailNoProcessingReply  OBJECT-TYPE
    SYNTAX      OCTET STRING
    MAX-ACCESS  read-write
    STATUS      current
    DESCRIPTION
"

"
    REFERENCE "Reply to Add to/Remove from noProcessing"
    DEFVAL { "1" }
    ::= {EmailInterface 547}

syncStatEmailNoProcessingReply  OBJECT-TYPE
    SYNTAX      OCTET STRING
    MAX-ACCESS  read-only
    STATUS      current
    DESCRIPTION
"
synchronization status for EmailNoProcessingReply
-1 - EmailNoProcessingReply could not be synchronized
 0 - synchronization not configured
 1 - out of sync - running master mode
 2 - in sync - running  mastermode
 3 - in sync - running slave mode
 4 - in sync - running master mode (wait to reach state 2)
"
    ::= {EmailNoProcessingReply 5}

syncStatStrEmailNoProcessingReply  OBJECT-TYPE
    SYNTAX      OCTET STRING
    MAX-ACCESS  read-only
    STATUS      current
    DESCRIPTION
"
synchronization status line from file assp_sync.cfg for EmailNoProcessingReply
 0 - synchronization not configured
 1 - out of sync - running master mode
 2 - in sync - running  mastermode
 3 - in sync - running slave mode
 4 - in sync - running master mode (wait to reach state 2)
"
    ::= {EmailNoProcessingReply 6}

EmailNoProcessingTo  OBJECT-TYPE
    SYNTAX      OCTET STRING
    MAX-ACCESS  read-write
    STATUS      current
    DESCRIPTION
"
Email sent from ASSP acknowledging your submissions will be sent to this address. For example: admin@domain.com
"
    REFERENCE "Send Copy of NoProcessing-Reports TO"
    DEFVAL { "" }
    ::= {EmailInterface 548}

syncStatEmailNoProcessingTo  OBJECT-TYPE
    SYNTAX      OCTET STRING
    MAX-ACCESS  read-only
    STATUS      current
    DESCRIPTION
"
synchronization status for EmailNoProcessingTo
-1 - EmailNoProcessingTo could not be synchronized
 0 - synchronization not configured
 1 - out of sync - running master mode
 2 - in sync - running  mastermode
 3 - in sync - running slave mode
 4 - in sync - running master mode (wait to reach state 2)
"
    ::= {EmailNoProcessingTo 5}

syncStatStrEmailNoProcessingTo  OBJECT-TYPE
    SYNTAX      OCTET STRING
    MAX-ACCESS  read-only
    STATUS      current
    DESCRIPTION
"
synchronization status line from file assp_sync.cfg for EmailNoProcessingTo
 0 - synchronization not configured
 1 - out of sync - running master mode
 2 - in sync - running  mastermode
 3 - in sync - running slave mode
 4 - in sync - running master mode (wait to reach state 2)
"
    ::= {EmailNoProcessingTo 6}

EmailBlackAdd  OBJECT-TYPE
    SYNTAX      OCTET STRING
    MAX-ACCESS  read-write
    STATUS      current
    DESCRIPTION
"
Any mail sent by local/authenticated users to this username will be interpreted as a request to add the sender address to the blackListedDomains addresses. Only the users defined in EmailAdmins and EmailAdminReportsTo are able to request an addition. Do not put the full address here, just the user part. For example: assp-black. To use this option, you have to configure blackListedDomains with 'file:...' for example 'file:files/blacklisted.txt' !
"
    REFERENCE "Add to BlackListed  Addresses"
    DEFVAL { "assp-black" }
    ::= {EmailInterface 549}

syncStatEmailBlackAdd  OBJECT-TYPE
    SYNTAX      OCTET STRING
    MAX-ACCESS  read-only
    STATUS      current
    DESCRIPTION
"
synchronization status for EmailBlackAdd
-1 - EmailBlackAdd could not be synchronized
 0 - synchronization not configured
 1 - out of sync - running master mode
 2 - in sync - running  mastermode
 3 - in sync - running slave mode
 4 - in sync - running master mode (wait to reach state 2)
"
    ::= {EmailBlackAdd 5}

syncStatStrEmailBlackAdd  OBJECT-TYPE
    SYNTAX      OCTET STRING
    MAX-ACCESS  read-only
    STATUS      current
    DESCRIPTION
"
synchronization status line from file assp_sync.cfg for EmailBlackAdd
 0 - synchronization not configured
 1 - out of sync - running master mode
 2 - in sync - running  mastermode
 3 - in sync - running slave mode
 4 - in sync - running master mode (wait to reach state 2)
"
    ::= {EmailBlackAdd 6}

EmailBlackRemove  OBJECT-TYPE
    SYNTAX      OCTET STRING
    MAX-ACCESS  read-write
    STATUS      current
    DESCRIPTION
"
Any mail sent by local/authenticated users to this username will be interpreted as a request to remove the sender address from blackListedDomains .
  Do not put the full address here, just the user part. Only the users defined in EmailAdmins and EmailAdminReportsTo are able to request an addition. For example: assp-notblack. To use this option, you have to configure blackListedDomains with 'file:...' for example 'file:files/blacklisted.txt' !
"
    REFERENCE "Remove from BlackListed Addresses"
    DEFVAL { "assp-notblack" }
    ::= {EmailInterface 550}

syncStatEmailBlackRemove  OBJECT-TYPE
    SYNTAX      OCTET STRING
    MAX-ACCESS  read-only
    STATUS      current
    DESCRIPTION
"
synchronization status for EmailBlackRemove
-1 - EmailBlackRemove could not be synchronized
 0 - synchronization not configured
 1 - out of sync - running master mode
 2 - in sync - running  mastermode
 3 - in sync - running slave mode
 4 - in sync - running master mode (wait to reach state 2)
"
    ::= {EmailBlackRemove 5}

syncStatStrEmailBlackRemove  OBJECT-TYPE
    SYNTAX      OCTET STRING
    MAX-ACCESS  read-only
    STATUS      current
    DESCRIPTION
"
synchronization status line from file assp_sync.cfg for EmailBlackRemove
 0 - synchronization not configured
 1 - out of sync - running master mode
 2 - in sync - running  mastermode
 3 - in sync - running slave mode
 4 - in sync - running master mode (wait to reach state 2)
"
    ::= {EmailBlackRemove 6}

EmailBlackReply  OBJECT-TYPE
    SYNTAX      OCTET STRING
    MAX-ACCESS  read-write
    STATUS      current
    DESCRIPTION
"

"
    REFERENCE "Reply to Add to/Remove from BlackListed"
    DEFVAL { "1" }
    ::= {EmailInterface 551}

syncStatEmailBlackReply  OBJECT-TYPE
    SYNTAX      OCTET STRING
    MAX-ACCESS  read-only
    STATUS      current
    DESCRIPTION
"
synchronization status for EmailBlackReply
-1 - EmailBlackReply could not be synchronized
 0 - synchronization not configured
 1 - out of sync - running master mode
 2 - in sync - running  mastermode
 3 - in sync - running slave mode
 4 - in sync - running master mode (wait to reach state 2)
"
    ::= {EmailBlackReply 5}

syncStatStrEmailBlackReply  OBJECT-TYPE
    SYNTAX      OCTET STRING
    MAX-ACCESS  read-only
    STATUS      current
    DESCRIPTION
"
synchronization status line from file assp_sync.cfg for EmailBlackReply
 0 - synchronization not configured
 1 - out of sync - running master mode
 2 - in sync - running  mastermode
 3 - in sync - running slave mode
 4 - in sync - running master mode (wait to reach state 2)
"
    ::= {EmailBlackReply 6}

EmailBlackTo  OBJECT-TYPE
    SYNTAX      OCTET STRING
    MAX-ACCESS  read-write
    STATUS      current
    DESCRIPTION
"
Email sent from ASSP acknowledging your submissions will be sent to this address. For example: admin@domain.com
"
    REFERENCE "Send Copy of Black-Change-Reports TO"
    DEFVAL { "" }
    ::= {EmailInterface 552}

syncStatEmailBlackTo  OBJECT-TYPE
    SYNTAX      OCTET STRING
    MAX-ACCESS  read-only
    STATUS      current
    DESCRIPTION
"
synchronization status for EmailBlackTo
-1 - EmailBlackTo could not be synchronized
 0 - synchronization not configured
 1 - out of sync - running master mode
 2 - in sync - running  mastermode
 3 - in sync - running slave mode
 4 - in sync - running master mode (wait to reach state 2)
"
    ::= {EmailBlackTo 5}

syncStatStrEmailBlackTo  OBJECT-TYPE
    SYNTAX      OCTET STRING
    MAX-ACCESS  read-only
    STATUS      current
    DESCRIPTION
"
synchronization status line from file assp_sync.cfg for EmailBlackTo
 0 - synchronization not configured
 1 - out of sync - running master mode
 2 - in sync - running  mastermode
 3 - in sync - running slave mode
 4 - in sync - running master mode (wait to reach state 2)
"
    ::= {EmailBlackTo 6}

EmailAnalyze  OBJECT-TYPE
    SYNTAX      OCTET STRING
    MAX-ACCESS  read-write
    STATUS      current
    DESCRIPTION
"
Any mail sent or forwarded by local/authenticated users to this username will be interpreted as a request for analyzing the mail. Do not put the full address here, just the user part. For example: asspanalyze 
  Use a fake domain like @assp.local when you send the email- so the full address would be then asspanalyze@assp.local. You can sent multiple mails as attachments and/or zipped file(s). Each attached email-file must have the extension defined in 'maillogExt'. In this case only the attachments will be processed. To use this multi-attachment-feature an installed  module in PERL is needed. It is also possible to send MS-outlook '.msg' files (possibly zipped). To use this MS-outlook-feature in addition an installed  module in PERL is needed.
"
    REFERENCE "Request Analyze Report"
    DEFVAL { "asspanalyze" }
    ::= {EmailInterface 553}

syncStatEmailAnalyze  OBJECT-TYPE
    SYNTAX      OCTET STRING
    MAX-ACCESS  read-only
    STATUS      current
    DESCRIPTION
"
synchronization status for EmailAnalyze
-1 - EmailAnalyze could not be synchronized
 0 - synchronization not configured
 1 - out of sync - running master mode
 2 - in sync - running  mastermode
 3 - in sync - running slave mode
 4 - in sync - running master mode (wait to reach state 2)
"
    ::= {EmailAnalyze 5}

syncStatStrEmailAnalyze  OBJECT-TYPE
    SYNTAX      OCTET STRING
    MAX-ACCESS  read-only
    STATUS      current
    DESCRIPTION
"
synchronization status line from file assp_sync.cfg for EmailAnalyze
 0 - synchronization not configured
 1 - out of sync - running master mode
 2 - in sync - running  mastermode
 3 - in sync - running slave mode
 4 - in sync - running master mode (wait to reach state 2)
"
    ::= {EmailAnalyze 6}

EmailAnalyzeReply  OBJECT-TYPE
    SYNTAX      OCTET STRING
    MAX-ACCESS  read-write
    STATUS      current
    DESCRIPTION
"

"
    REFERENCE "Reply to Analyze Request"
    DEFVAL { "1" }
    ::= {EmailInterface 554}

syncStatEmailAnalyzeReply  OBJECT-TYPE
    SYNTAX      OCTET STRING
    MAX-ACCESS  read-only
    STATUS      current
    DESCRIPTION
"
synchronization status for EmailAnalyzeReply
-1 - EmailAnalyzeReply could not be synchronized
 0 - synchronization not configured
 1 - out of sync - running master mode
 2 - in sync - running  mastermode
 3 - in sync - running slave mode
 4 - in sync - running master mode (wait to reach state 2)
"
    ::= {EmailAnalyzeReply 5}

syncStatStrEmailAnalyzeReply  OBJECT-TYPE
    SYNTAX      OCTET STRING
    MAX-ACCESS  read-only
    STATUS      current
    DESCRIPTION
"
synchronization status line from file assp_sync.cfg for EmailAnalyzeReply
 0 - synchronization not configured
 1 - out of sync - running master mode
 2 - in sync - running  mastermode
 3 - in sync - running slave mode
 4 - in sync - running master mode (wait to reach state 2)
"
    ::= {EmailAnalyzeReply 6}

EmailAnalyzeTo  OBJECT-TYPE
    SYNTAX      OCTET STRING
    MAX-ACCESS  read-write
    STATUS      current
    DESCRIPTION
"
A copy of the Analyze-Report will be sent to this address. For example: admin@domain.com
"
    REFERENCE "Send Copy of Analyze-Reports"
    DEFVAL { "" }
    ::= {EmailInterface 555}

syncStatEmailAnalyzeTo  OBJECT-TYPE
    SYNTAX      OCTET STRING
    MAX-ACCESS  read-only
    STATUS      current
    DESCRIPTION
"
synchronization status for EmailAnalyzeTo
-1 - EmailAnalyzeTo could not be synchronized
 0 - synchronization not configured
 1 - out of sync - running master mode
 2 - in sync - running  mastermode
 3 - in sync - running slave mode
 4 - in sync - running master mode (wait to reach state 2)
"
    ::= {EmailAnalyzeTo 5}

syncStatStrEmailAnalyzeTo  OBJECT-TYPE
    SYNTAX      OCTET STRING
    MAX-ACCESS  read-only
    STATUS      current
    DESCRIPTION
"
synchronization status line from file assp_sync.cfg for EmailAnalyzeTo
 0 - synchronization not configured
 1 - out of sync - running master mode
 2 - in sync - running  mastermode
 3 - in sync - running slave mode
 4 - in sync - running master mode (wait to reach state 2)
"
    ::= {EmailAnalyzeTo 6}

DoAdditionalAnalyze  OBJECT-TYPE
    SYNTAX      OCTET STRING
    MAX-ACCESS  read-write
    STATUS      current
    DESCRIPTION
"
Additional Analyze Report will be generated for Spam and Ham Reports. Setting the TO Address accordingly and choosing EmailAnalyzeTo will send the Analyze Report to the admin only.
"
    REFERENCE "Spam and Ham Reports will trigger an additional Analyze Report "
    DEFVAL { "0" }
    ::= {EmailInterface 556}

syncStatDoAdditionalAnalyze  OBJECT-TYPE
    SYNTAX      OCTET STRING
    MAX-ACCESS  read-only
    STATUS      current
    DESCRIPTION
"
synchronization status for DoAdditionalAnalyze
-1 - DoAdditionalAnalyze could not be synchronized
 0 - synchronization not configured
 1 - out of sync - running master mode
 2 - in sync - running  mastermode
 3 - in sync - running slave mode
 4 - in sync - running master mode (wait to reach state 2)
"
    ::= {DoAdditionalAnalyze 5}

syncStatStrDoAdditionalAnalyze  OBJECT-TYPE
    SYNTAX      OCTET STRING
    MAX-ACCESS  read-only
    STATUS      current
    DESCRIPTION
"
synchronization status line from file assp_sync.cfg for DoAdditionalAnalyze
 0 - synchronization not configured
 1 - out of sync - running master mode
 2 - in sync - running  mastermode
 3 - in sync - running slave mode
 4 - in sync - running master mode (wait to reach state 2)
"
    ::= {DoAdditionalAnalyze 6}

EmailFrom  OBJECT-TYPE
    SYNTAX      OCTET STRING
    MAX-ACCESS  read-write
    STATUS      current
    DESCRIPTION
"
Email sent from ASSP acknowledging your submissions will be sent from this address.
"
    REFERENCE "From Address for Reports"
    DEFVAL { "<spammaster@yourdomain.com>" }
    ::= {EmailInterface 557}

syncStatEmailFrom  OBJECT-TYPE
    SYNTAX      OCTET STRING
    MAX-ACCESS  read-only
    STATUS      current
    DESCRIPTION
"
synchronization status for EmailFrom
-1 - EmailFrom could not be synchronized
 0 - synchronization not configured
 1 - out of sync - running master mode
 2 - in sync - running  mastermode
 3 - in sync - running slave mode
 4 - in sync - running master mode (wait to reach state 2)
"
    ::= {EmailFrom 5}

syncStatStrEmailFrom  OBJECT-TYPE
    SYNTAX      OCTET STRING
    MAX-ACCESS  read-only
    STATUS      current
    DESCRIPTION
"
synchronization status line from file assp_sync.cfg for EmailFrom
 0 - synchronization not configured
 1 - out of sync - running master mode
 2 - in sync - running  mastermode
 3 - in sync - running slave mode
 4 - in sync - running master mode (wait to reach state 2)
"
    ::= {EmailFrom 6}

EmailAllowEqual  OBJECT-TYPE
    SYNTAX      OCTET STRING
    MAX-ACCESS  read-write
    STATUS      current
    DESCRIPTION
"
Allow '=' in addresses to be whitelisted or redlisted.
"
    REFERENCE "Allow '=' in Addresses"
    DEFVAL { "1" }
    ::= {EmailInterface 558}

syncStatEmailAllowEqual  OBJECT-TYPE
    SYNTAX      OCTET STRING
    MAX-ACCESS  read-only
    STATUS      current
    DESCRIPTION
"
synchronization status for EmailAllowEqual
-1 - EmailAllowEqual could not be synchronized
 0 - synchronization not configured
 1 - out of sync - running master mode
 2 - in sync - running  mastermode
 3 - in sync - running slave mode
 4 - in sync - running master mode (wait to reach state 2)
"
    ::= {EmailAllowEqual 5}

syncStatStrEmailAllowEqual  OBJECT-TYPE
    SYNTAX      OCTET STRING
    MAX-ACCESS  read-only
    STATUS      current
    DESCRIPTION
"
synchronization status line from file assp_sync.cfg for EmailAllowEqual
 0 - synchronization not configured
 1 - out of sync - running master mode
 2 - in sync - running  mastermode
 3 - in sync - running slave mode
 4 - in sync - running master mode (wait to reach state 2)
"
    ::= {EmailAllowEqual 6}

EmailSenderNoReply  OBJECT-TYPE
    SYNTAX      OCTET STRING
    MAX-ACCESS  read-write
    STATUS      current
    DESCRIPTION
"
Email sent from ASSP acknowledging your submissions will not be sent to these addresses. Accepts specific addresses (user@example.com), user parts (user) or entire domains (@example.com).
  Analyze-, PersonalBlackList- and all virus related reports are ignored by this feature (are sent even a user is listed here).
  An Report copy to EmailAnalyzeTo, EmailBlackTo, EmailNoProcessingTo, EmailSpamLoverTo, EmailRedlistTo, EmailWhitelistTo and EmailErrorsTo is also ignored by this feature.
  
  
"
    REFERENCE "Do Not Reply To These Addresses*"
    DEFVAL { "" }
    ::= {EmailInterface 559}

syncStatEmailSenderNoReply  OBJECT-TYPE
    SYNTAX      OCTET STRING
    MAX-ACCESS  read-only
    STATUS      current
    DESCRIPTION
"
synchronization status for EmailSenderNoReply
-1 - EmailSenderNoReply could not be synchronized
 0 - synchronization not configured
 1 - out of sync - running master mode
 2 - in sync - running  mastermode
 3 - in sync - running slave mode
 4 - in sync - running master mode (wait to reach state 2)
"
    ::= {EmailSenderNoReply 5}

syncStatStrEmailSenderNoReply  OBJECT-TYPE
    SYNTAX      OCTET STRING
    MAX-ACCESS  read-only
    STATUS      current
    DESCRIPTION
"
synchronization status line from file assp_sync.cfg for EmailSenderNoReply
 0 - synchronization not configured
 1 - out of sync - running master mode
 2 - in sync - running  mastermode
 3 - in sync - running slave mode
 4 - in sync - running master mode (wait to reach state 2)
"
    ::= {EmailSenderNoReply 6}

EmailErrorsModifyNoP  OBJECT-TYPE
    SYNTAX      OCTET STRING
    MAX-ACCESS  read-write
    STATUS      current
    DESCRIPTION
"
If set to 'modify noProcessing' Spam Reports will remove email addresses from noProcessing list. If set to 'show noProcessing' Spam Reports will show if addresses are on noProcessing list, also a copy of a file in the GUI to correctedspam (remove) and correctednotspam (show) will modify the noProcessing list for the found addresses.
"
    REFERENCE "Combined Spam Report and NoProcessing Deletion"
    DEFVAL { "1" }
    ::= {EmailInterface 879}

syncStatEmailErrorsModifyNoP  OBJECT-TYPE
    SYNTAX      OCTET STRING
    MAX-ACCESS  read-only
    STATUS      current
    DESCRIPTION
"
synchronization status for EmailErrorsModifyNoP
-1 - EmailErrorsModifyNoP could not be synchronized
 0 - synchronization not configured
 1 - out of sync - running master mode
 2 - in sync - running  mastermode
 3 - in sync - running slave mode
 4 - in sync - running master mode (wait to reach state 2)
"
    ::= {EmailErrorsModifyNoP 5}

syncStatStrEmailErrorsModifyNoP  OBJECT-TYPE
    SYNTAX      OCTET STRING
    MAX-ACCESS  read-only
    STATUS      current
    DESCRIPTION
"
synchronization status line from file assp_sync.cfg for EmailErrorsModifyNoP
 0 - synchronization not configured
 1 - out of sync - running master mode
 2 - in sync - running  mastermode
 3 - in sync - running slave mode
 4 - in sync - running master mode (wait to reach state 2)
"
    ::= {EmailErrorsModifyNoP 6}

EmailPersBlackAdd  OBJECT-TYPE
    SYNTAX      OCTET STRING
    MAX-ACCESS  read-write
    STATUS      current
    DESCRIPTION
"
Any mail sent by local/authenticated users to this username will be interpreted as a request to add the listed address(es) to the personal blackListed addresses. Do not put the full address here, just the user part. 
  For example: assp-persblack.
  The add and remove is done via email-interface, by sending specific email addresses to 'EmailPersBlackAdd'  and 'EmailPersBlackRemove'.
  A local user can force a complete report about all his personal black list entries by defining an email address that begins with 'reportpersblack' in a remove or add request : eg: reportpersblack@anydomain.com or by sending an empty body.
  Any mail address sent to this username will be removed from the whitelist if possible.
  Globalized adding an address to all local users is not supported - use EmailBlackAdd instead.
  The following wildcard combinations are allowed for an email address to support personal blacklisting of domains:
  full_sender_address
  *@sender_domain or @sender_domain
  @*sender_domain or *@*sender_domain
  @*.sender_domain or *@*.sender_domain
"
    REFERENCE "Add to Personal BlackListed Addresses"
    DEFVAL { "assp-persblack" }
    ::= {EmailInterface 911}

syncStatEmailPersBlackAdd  OBJECT-TYPE
    SYNTAX      OCTET STRING
    MAX-ACCESS  read-only
    STATUS      current
    DESCRIPTION
"
synchronization status for EmailPersBlackAdd
-1 - EmailPersBlackAdd could not be synchronized
 0 - synchronization not configured
 1 - out of sync - running master mode
 2 - in sync - running  mastermode
 3 - in sync - running slave mode
 4 - in sync - running master mode (wait to reach state 2)
"
    ::= {EmailPersBlackAdd 5}

syncStatStrEmailPersBlackAdd  OBJECT-TYPE
    SYNTAX      OCTET STRING
    MAX-ACCESS  read-only
    STATUS      current
    DESCRIPTION
"
synchronization status line from file assp_sync.cfg for EmailPersBlackAdd
 0 - synchronization not configured
 1 - out of sync - running master mode
 2 - in sync - running  mastermode
 3 - in sync - running slave mode
 4 - in sync - running master mode (wait to reach state 2)
"
    ::= {EmailPersBlackAdd 6}

EmailPersBlackRemove  OBJECT-TYPE
    SYNTAX      OCTET STRING
    MAX-ACCESS  read-write
    STATUS      current
    DESCRIPTION
"
Any mail sent by local/authenticated users to this username will be interpreted as a request to remove the listed address(es) from the personal blackListed addresses .
  Do not put the full address here, just the user part.
  For example: assp-persnotblack.
  The add and remove is done via email-interface, by sending specific email addresses to 'EmailPersBlackAdd'  and 'EmailPersBlackRemove'.
  A local user can force a complete report about all his personal black list entries by defining an email address that begins with 'reportpersblack' in a remove or add request : eg: reportpersblack@anydomain.com or by sending an empty body.
  Only an admin can force a complete cleanup of all personal black entries for a specific email address for all local users - sending an email to 'EmailPersBlackRemove' with the address followed by ',*' in the body
  eg: address_to_remove@the_domain.foo,* - be carefull modifying personal entries of other users!
  The same wildcard combinations like in EmailPersBlackAdd are supported.
  Notice: a removement request for a specific email address will remove ALL entries from the users personal blacklist, that would block this email address (also all matching wildcard entries)!
"
    REFERENCE "Remove from Personal BlackListed Addresses"
    DEFVAL { "assp-persnotblack" }
    ::= {EmailInterface 912}

syncStatEmailPersBlackRemove  OBJECT-TYPE
    SYNTAX      OCTET STRING
    MAX-ACCESS  read-only
    STATUS      current
    DESCRIPTION
"
synchronization status for EmailPersBlackRemove
-1 - EmailPersBlackRemove could not be synchronized
 0 - synchronization not configured
 1 - out of sync - running master mode
 2 - in sync - running  mastermode
 3 - in sync - running slave mode
 4 - in sync - running master mode (wait to reach state 2)
"
    ::= {EmailPersBlackRemove 5}

syncStatStrEmailPersBlackRemove  OBJECT-TYPE
    SYNTAX      OCTET STRING
    MAX-ACCESS  read-only
    STATUS      current
    DESCRIPTION
"
synchronization status line from file assp_sync.cfg for EmailPersBlackRemove
 0 - synchronization not configured
 1 - out of sync - running master mode
 2 - in sync - running  mastermode
 3 - in sync - running slave mode
 4 - in sync - running master mode (wait to reach state 2)
"
    ::= {EmailPersBlackRemove 6}

EmailSenderIgnore  OBJECT-TYPE
    SYNTAX      OCTET STRING
    MAX-ACCESS  read-write
    STATUS      current
    DESCRIPTION
"
Mail from any of these addresses are not accepted from Email Interface. Accepts specific addresses (user@example.com), user parts (user) or entire domains (@example.com). The user will get not informed about the denied request.
"
    REFERENCE "Ignore Not Authorized Addresses*"
    DEFVAL { "" }
    ::= {EmailInterface 939}

syncStatEmailSenderIgnore  OBJECT-TYPE
    SYNTAX      OCTET STRING
    MAX-ACCESS  read-only
    STATUS      current
    DESCRIPTION
"
synchronization status for EmailSenderIgnore
-1 - EmailSenderIgnore could not be synchronized
 0 - synchronization not configured
 1 - out of sync - running master mode
 2 - in sync - running  mastermode
 3 - in sync - running slave mode
 4 - in sync - running master mode (wait to reach state 2)
"
    ::= {EmailSenderIgnore 5}

syncStatStrEmailSenderIgnore  OBJECT-TYPE
    SYNTAX      OCTET STRING
    MAX-ACCESS  read-only
    STATUS      current
    DESCRIPTION
"
synchronization status line from file assp_sync.cfg for EmailSenderIgnore
 0 - synchronization not configured
 1 - out of sync - running master mode
 2 - in sync - running  mastermode
 3 - in sync - running slave mode
 4 - in sync - running master mode (wait to reach state 2)
"
    ::= {EmailSenderIgnore 6}

EmailErrorsModifyPersBlack  OBJECT-TYPE
    SYNTAX      OCTET STRING
    MAX-ACCESS  read-write
    STATUS      current
    DESCRIPTION
"
Spam Reports will add email addresses to the Personal Blacklist, NotSpam Reports will remove addresses from the Personal Blacklist, if the report senders address matches.
  Accepts specific addresses (user@domain.com), user parts (user) or entire domains (@domain.com). Wildcards are supported (fribo*@domain.com).
  Default is *@* , which matches all addresses.
"
    REFERENCE "Spam/NotSpam Report will modify Personal Blacklist *"
    DEFVAL { "*@*" }
    ::= {EmailInterface 961}

syncStatEmailErrorsModifyPersBlack  OBJECT-TYPE
    SYNTAX      OCTET STRING
    MAX-ACCESS  read-only
    STATUS      current
    DESCRIPTION
"
synchronization status for EmailErrorsModifyPersBlack
-1 - EmailErrorsModifyPersBlack could not be synchronized
 0 - synchronization not configured
 1 - out of sync - running master mode
 2 - in sync - running  mastermode
 3 - in sync - running slave mode
 4 - in sync - running master mode (wait to reach state 2)
"
    ::= {EmailErrorsModifyPersBlack 5}

syncStatStrEmailErrorsModifyPersBlack  OBJECT-TYPE
    SYNTAX      OCTET STRING
    MAX-ACCESS  read-only
    STATUS      current
    DESCRIPTION
"
synchronization status line from file assp_sync.cfg for EmailErrorsModifyPersBlack
 0 - synchronization not configured
 1 - out of sync - running master mode
 2 - in sync - running  mastermode
 3 - in sync - running slave mode
 4 - in sync - running master mode (wait to reach state 2)
"
    ::= {EmailErrorsModifyPersBlack 6}

EmailForwardReportedTo  OBJECT-TYPE
    SYNTAX      OCTET STRING
    MAX-ACCESS  read-write
    STATUS      current
    DESCRIPTION
"
Host and Port to forward EmailSpam and EmailHam reports to - eg '10.0.1.3:1025'.
  If you use more than one assp instance and your users are reporting spam and ham mails to multiple or all of them, but only one (but not this instance) is doing the rebuildspamdb and the corpus folders are not shared between the instances,
  define the 'host:port' of the central assp (rebuild-) instance here. Every report to EmailSpam and EmailHam (but only these!) will be forwarded to the defined host(s) and NO other local action will be taken. If the forwarding to all defined hosts fails, the request will be processed localy. To define multiple hosts for failover, separte them by pipe (|).
"
    REFERENCE "Email Interface Forward Reports Destination"
    DEFVAL { "" }
    ::= {EmailInterface 993}

syncStatEmailForwardReportedTo  OBJECT-TYPE
    SYNTAX      OCTET STRING
    MAX-ACCESS  read-only
    STATUS      current
    DESCRIPTION
"
synchronization status for EmailForwardReportedTo
-1 - EmailForwardReportedTo could not be synchronized
 0 - synchronization not configured
 1 - out of sync - running master mode
 2 - in sync - running  mastermode
 3 - in sync - running slave mode
 4 - in sync - running master mode (wait to reach state 2)
"
    ::= {EmailForwardReportedTo 5}

syncStatStrEmailForwardReportedTo  OBJECT-TYPE
    SYNTAX      OCTET STRING
    MAX-ACCESS  read-only
    STATUS      current
    DESCRIPTION
"
synchronization status line from file assp_sync.cfg for EmailForwardReportedTo
 0 - synchronization not configured
 1 - out of sync - running master mode
 2 - in sync - running  mastermode
 3 - in sync - running slave mode
 4 - in sync - running master mode (wait to reach state 2)
"
    ::= {EmailForwardReportedTo 6}

EmailInterfaceDomains  OBJECT-TYPE
    SYNTAX      OCTET STRING
    MAX-ACCESS  read-write
    STATUS      current
    DESCRIPTION
"
Enable the EmailInterface and BlockReports for these local domains ONLY (NOT RECOMMENDED). If used, you have also to define '@assp.local' (if required). If not used, all localdomains and '@assp.local' take place ( see EmailInterfaceOk ). Accepts entire domains (@domain.com|domain.com)
"
    REFERENCE "Accept Mails (Reports) for these local domains only*"
    DEFVAL { "" }
    ::= {EmailInterface 1037}

syncStatEmailInterfaceDomains  OBJECT-TYPE
    SYNTAX      OCTET STRING
    MAX-ACCESS  read-only
    STATUS      current
    DESCRIPTION
"
synchronization status for EmailInterfaceDomains
-1 - EmailInterfaceDomains could not be synchronized
 0 - synchronization not configured
 1 - out of sync - running master mode
 2 - in sync - running  mastermode
 3 - in sync - running slave mode
 4 - in sync - running master mode (wait to reach state 2)
"
    ::= {EmailInterfaceDomains 5}

syncStatStrEmailInterfaceDomains  OBJECT-TYPE
    SYNTAX      OCTET STRING
    MAX-ACCESS  read-only
    STATUS      current
    DESCRIPTION
"
synchronization status line from file assp_sync.cfg for EmailInterfaceDomains
 0 - synchronization not configured
 1 - out of sync - running master mode
 2 - in sync - running  mastermode
 3 - in sync - running slave mode
 4 - in sync - running master mode (wait to reach state 2)
"
    ::= {EmailInterfaceDomains 6}

FilePathsandDatabase  OBJECT IDENTIFIER ::= {asspConfig 27}
base  OBJECT-TYPE
    SYNTAX      OCTET STRING
    MAX-ACCESS  read-write
    STATUS      current
    DESCRIPTION
"
All paths are relative to this folder.
  Note: Display only.
"
    REFERENCE "Directory Base"
    DEFVAL { "." }
    ::= {FilePathsandDatabase 560}

spamlog  OBJECT-TYPE
    SYNTAX      OCTET STRING
    MAX-ACCESS  read-write
    STATUS      current
    DESCRIPTION
"
The folder to save the collection of spam mails. This directory will be used in building the spamdb . For example: spam
"
    REFERENCE "Spam Collection"
    DEFVAL { "spam" }
    ::= {FilePathsandDatabase 561}

syncStatspamlog  OBJECT-TYPE
    SYNTAX      OCTET STRING
    MAX-ACCESS  read-only
    STATUS      current
    DESCRIPTION
"
synchronization status for spamlog
-1 - spamlog could not be synchronized
 0 - synchronization not configured
 1 - out of sync - running master mode
 2 - in sync - running  mastermode
 3 - in sync - running slave mode
 4 - in sync - running master mode (wait to reach state 2)
"
    ::= {spamlog 5}

syncStatStrspamlog  OBJECT-TYPE
    SYNTAX      OCTET STRING
    MAX-ACCESS  read-only
    STATUS      current
    DESCRIPTION
"
synchronization status line from file assp_sync.cfg for spamlog
 0 - synchronization not configured
 1 - out of sync - running master mode
 2 - in sync - running  mastermode
 3 - in sync - running slave mode
 4 - in sync - running master mode (wait to reach state 2)
"
    ::= {spamlog 6}

notspamlog  OBJECT-TYPE
    SYNTAX      OCTET STRING
    MAX-ACCESS  read-write
    STATUS      current
    DESCRIPTION
"
The folder to save the collection of not-spam mails. This directory will be used in building the spamdb . For example: notspam
"
    REFERENCE "Not-spam Collection"
    DEFVAL { "notspam" }
    ::= {FilePathsandDatabase 562}

syncStatnotspamlog  OBJECT-TYPE
    SYNTAX      OCTET STRING
    MAX-ACCESS  read-only
    STATUS      current
    DESCRIPTION
"
synchronization status for notspamlog
-1 - notspamlog could not be synchronized
 0 - synchronization not configured
 1 - out of sync - running master mode
 2 - in sync - running  mastermode
 3 - in sync - running slave mode
 4 - in sync - running master mode (wait to reach state 2)
"
    ::= {notspamlog 5}

syncStatStrnotspamlog  OBJECT-TYPE
    SYNTAX      OCTET STRING
    MAX-ACCESS  read-only
    STATUS      current
    DESCRIPTION
"
synchronization status line from file assp_sync.cfg for notspamlog
 0 - synchronization not configured
 1 - out of sync - running master mode
 2 - in sync - running  mastermode
 3 - in sync - running slave mode
 4 - in sync - running master mode (wait to reach state 2)
"
    ::= {notspamlog 6}

incomingOkMail  OBJECT-TYPE
    SYNTAX      OCTET STRING
    MAX-ACCESS  read-write
    STATUS      current
    DESCRIPTION
"
The folder to save non-spam (message ok). These are messages which are considered as HAM, but are not stored in the standard HAM folder because of our policy to use only confirmed HAM messages (whitelisted or local) for spamdb . If you want to keep copies of ok mail then put in a directory name. This directory will not be used in building the spamdb . Default: okmail
"
    REFERENCE "OK Mail"
    DEFVAL { "okmail" }
    ::= {FilePathsandDatabase 563}

syncStatincomingOkMail  OBJECT-TYPE
    SYNTAX      OCTET STRING
    MAX-ACCESS  read-only
    STATUS      current
    DESCRIPTION
"
synchronization status for incomingOkMail
-1 - incomingOkMail could not be synchronized
 0 - synchronization not configured
 1 - out of sync - running master mode
 2 - in sync - running  mastermode
 3 - in sync - running slave mode
 4 - in sync - running master mode (wait to reach state 2)
"
    ::= {incomingOkMail 5}

syncStatStrincomingOkMail  OBJECT-TYPE
    SYNTAX      OCTET STRING
    MAX-ACCESS  read-only
    STATUS      current
    DESCRIPTION
"
synchronization status line from file assp_sync.cfg for incomingOkMail
 0 - synchronization not configured
 1 - out of sync - running master mode
 2 - in sync - running  mastermode
 3 - in sync - running slave mode
 4 - in sync - running master mode (wait to reach state 2)
"
    ::= {incomingOkMail 6}

discarded  OBJECT-TYPE
    SYNTAX      OCTET STRING
    MAX-ACCESS  read-write
    STATUS      current
    DESCRIPTION
"
The folder to save discarded spam-messages. These are Spam messages which are not stored for building the spamdb but for resending with an EmailBlockReport. If you want to keep copies of discarded Spam then put in a directory name. Default: discarded
"
    REFERENCE "Discarded Spam"
    DEFVAL { "discarded" }
    ::= {FilePathsandDatabase 564}

syncStatdiscarded  OBJECT-TYPE
    SYNTAX      OCTET STRING
    MAX-ACCESS  read-only
    STATUS      current
    DESCRIPTION
"
synchronization status for discarded
-1 - discarded could not be synchronized
 0 - synchronization not configured
 1 - out of sync - running master mode
 2 - in sync - running  mastermode
 3 - in sync - running slave mode
 4 - in sync - running master mode (wait to reach state 2)
"
    ::= {discarded 5}

syncStatStrdiscarded  OBJECT-TYPE
    SYNTAX      OCTET STRING
    MAX-ACCESS  read-only
    STATUS      current
    DESCRIPTION
"
synchronization status line from file assp_sync.cfg for discarded
 0 - synchronization not configured
 1 - out of sync - running master mode
 2 - in sync - running  mastermode
 3 - in sync - running slave mode
 4 - in sync - running master mode (wait to reach state 2)
"
    ::= {discarded 6}

viruslog  OBJECT-TYPE
    SYNTAX      OCTET STRING
    MAX-ACCESS  read-write
    STATUS      current
    DESCRIPTION
"
The folder to save rejected attachments and viruses. Leave this blank to not save these files (default). If you want to keep copies of rejected content then put in a directory name. Note: you must create the directory. This directory will not be used in building the spamdb . For example: quarantine
"
    REFERENCE "Attachment/Virus Collection"
    DEFVAL { "quarantine" }
    ::= {FilePathsandDatabase 565}

syncStatviruslog  OBJECT-TYPE
    SYNTAX      OCTET STRING
    MAX-ACCESS  read-only
    STATUS      current
    DESCRIPTION
"
synchronization status for viruslog
-1 - viruslog could not be synchronized
 0 - synchronization not configured
 1 - out of sync - running master mode
 2 - in sync - running  mastermode
 3 - in sync - running slave mode
 4 - in sync - running master mode (wait to reach state 2)
"
    ::= {viruslog 5}

syncStatStrviruslog  OBJECT-TYPE
    SYNTAX      OCTET STRING
    MAX-ACCESS  read-only
    STATUS      current
    DESCRIPTION
"
synchronization status line from file assp_sync.cfg for viruslog
 0 - synchronization not configured
 1 - out of sync - running master mode
 2 - in sync - running  mastermode
 3 - in sync - running slave mode
 4 - in sync - running master mode (wait to reach state 2)
"
    ::= {viruslog 6}

correctedspam  OBJECT-TYPE
    SYNTAX      OCTET STRING
    MAX-ACCESS  read-write
    STATUS      current
    DESCRIPTION
"
Spam that got through -- counts double. This directory will be used in building the spamdb . For example: errors/spam
"
    REFERENCE "False-negative Collection"
    DEFVAL { "errors/spam" }
    ::= {FilePathsandDatabase 566}

syncStatcorrectedspam  OBJECT-TYPE
    SYNTAX      OCTET STRING
    MAX-ACCESS  read-only
    STATUS      current
    DESCRIPTION
"
synchronization status for correctedspam
-1 - correctedspam could not be synchronized
 0 - synchronization not configured
 1 - out of sync - running master mode
 2 - in sync - running  mastermode
 3 - in sync - running slave mode
 4 - in sync - running master mode (wait to reach state 2)
"
    ::= {correctedspam 5}

syncStatStrcorrectedspam  OBJECT-TYPE
    SYNTAX      OCTET STRING
    MAX-ACCESS  read-only
    STATUS      current
    DESCRIPTION
"
synchronization status line from file assp_sync.cfg for correctedspam
 0 - synchronization not configured
 1 - out of sync - running master mode
 2 - in sync - running  mastermode
 3 - in sync - running slave mode
 4 - in sync - running master mode (wait to reach state 2)
"
    ::= {correctedspam 6}

correctednotspam  OBJECT-TYPE
    SYNTAX      OCTET STRING
    MAX-ACCESS  read-write
    STATUS      current
    DESCRIPTION
"
Good mail that was listed as spam, count 4x. This directory will be used in building the spamdb . For example: errors/notspam
"
    REFERENCE "False-positive Collection"
    DEFVAL { "errors/notspam" }
    ::= {FilePathsandDatabase 567}

syncStatcorrectednotspam  OBJECT-TYPE
    SYNTAX      OCTET STRING
    MAX-ACCESS  read-only
    STATUS      current
    DESCRIPTION
"
synchronization status for correctednotspam
-1 - correctednotspam could not be synchronized
 0 - synchronization not configured
 1 - out of sync - running master mode
 2 - in sync - running  mastermode
 3 - in sync - running slave mode
 4 - in sync - running master mode (wait to reach state 2)
"
    ::= {correctednotspam 5}

syncStatStrcorrectednotspam  OBJECT-TYPE
    SYNTAX      OCTET STRING
    MAX-ACCESS  read-only
    STATUS      current
    DESCRIPTION
"
synchronization status line from file assp_sync.cfg for correctednotspam
 0 - synchronization not configured
 1 - out of sync - running master mode
 2 - in sync - running  mastermode
 3 - in sync - running slave mode
 4 - in sync - running master mode (wait to reach state 2)
"
    ::= {correctednotspam 6}

resendmail  OBJECT-TYPE
    SYNTAX      OCTET STRING
    MAX-ACCESS  read-write
    STATUS      current
    DESCRIPTION
"
ASSP will try to resend the files in this directory to the original recipient. The files must have the 'maillogExt' extension and must have the SMTP-format. For example: resendmail. This requires an installed  module in PERL.
"
    REFERENCE "try to resend this files"
    DEFVAL { "resendmail" }
    ::= {FilePathsandDatabase 568}

syncStatresendmail  OBJECT-TYPE
    SYNTAX      OCTET STRING
    MAX-ACCESS  read-only
    STATUS      current
    DESCRIPTION
"
synchronization status for resendmail
-1 - resendmail could not be synchronized
 0 - synchronization not configured
 1 - out of sync - running master mode
 2 - in sync - running  mastermode
 3 - in sync - running slave mode
 4 - in sync - running master mode (wait to reach state 2)
"
    ::= {resendmail 5}

syncStatStrresendmail  OBJECT-TYPE
    SYNTAX      OCTET STRING
    MAX-ACCESS  read-only
    STATUS      current
    DESCRIPTION
"
synchronization status line from file assp_sync.cfg for resendmail
 0 - synchronization not configured
 1 - out of sync - running master mode
 2 - in sync - running  mastermode
 3 - in sync - running slave mode
 4 - in sync - running master mode (wait to reach state 2)
"
    ::= {resendmail 6}

maillogExt  OBJECT-TYPE
    SYNTAX      OCTET STRING
    MAX-ACCESS  read-write
    STATUS      current
    DESCRIPTION
"
Enter the file extension (include the period) you want appended to the mail files in the mail collections.
  Leave it blank for no extension - this setting will prevent several features from working. Never use '.msg' - this is an extension used by MS-outlook! For Example: .eml
"
    REFERENCE "Extension for Mail Files"
    DEFVAL { ".eml" }
    ::= {FilePathsandDatabase 569}

syncStatmaillogExt  OBJECT-TYPE
    SYNTAX      OCTET STRING
    MAX-ACCESS  read-only
    STATUS      current
    DESCRIPTION
"
synchronization status for maillogExt
-1 - maillogExt could not be synchronized
 0 - synchronization not configured
 1 - out of sync - running master mode
 2 - in sync - running  mastermode
 3 - in sync - running slave mode
 4 - in sync - running master mode (wait to reach state 2)
"
    ::= {maillogExt 5}

syncStatStrmaillogExt  OBJECT-TYPE
    SYNTAX      OCTET STRING
    MAX-ACCESS  read-only
    STATUS      current
    DESCRIPTION
"
synchronization status line from file assp_sync.cfg for maillogExt
 0 - synchronization not configured
 1 - out of sync - running master mode
 2 - in sync - running  mastermode
 3 - in sync - running slave mode
 4 - in sync - running master mode (wait to reach state 2)
"
    ::= {maillogExt 6}

spamdb  OBJECT-TYPE
    SYNTAX      OCTET STRING
    MAX-ACCESS  read-write
    STATUS      current
    DESCRIPTION
"
The output file from rebuildspamdb. Write only 'DB:' to use a database table instead of a local file, in this case you need to edit the database parameters below. The Hidden Makov Model is only available if this parameter is set to DB: .
 It is recommended to use a database for all possible lists and caches for best performance, less memoryusage and stability! If you do not want to install a database engine like MySql or Oracle, use BerkeleyDB! Please read the section DBdriver !
 
"
    REFERENCE "Spam/HMM Bayesian Database Files"
    DEFVAL { "spamdb" }
    ::= {FilePathsandDatabase 570}

whitelistdb  OBJECT-TYPE
    SYNTAX      OCTET STRING
    MAX-ACCESS  read-write
    STATUS      current
    DESCRIPTION
"
The file with the whitelist.
  Write only 'DB:' to use a database table instead of a local file, in this case you need to edit the database parameters below.
"
    REFERENCE "E<!--get rid of google autofill-->mail Whitelist Database File"
    DEFVAL { "whitelist" }
    ::= {FilePathsandDatabase 571}

redlistdb  OBJECT-TYPE
    SYNTAX      OCTET STRING
    MAX-ACCESS  read-write
    STATUS      current
    DESCRIPTION
"
The file with the redlist.
  Write only 'DB:' to use a database table instead of a local file, in this case you need to edit the database parameters below.
"
    REFERENCE "E<!--get rid of google autofill-->mail Redlist Database File"
    DEFVAL { "redlist" }
    ::= {FilePathsandDatabase 572}

griplist  OBJECT-TYPE
    SYNTAX      OCTET STRING
    MAX-ACCESS  read-write
    STATUS      current
    DESCRIPTION
"
The file with the current Grey-IP-List database -- make this blank if you don't use it.
"
    REFERENCE "GreyIPlist Database"
    DEFVAL { "griplist" }
    ::= {FilePathsandDatabase 573}

useDB4griplist  OBJECT-TYPE
    SYNTAX      OCTET STRING
    MAX-ACCESS  read-write
    STATUS      current
    DESCRIPTION
"
If selected ASSP uses 'BerkeleyDB' instead of 'orderedtie' for griplist. Depending on your settings for OrderedTieHashTableSize this could spend some memory and/or result in better performance.  The perl module  version 0.34 or higher and BerkeleyDB version 4.5 or higher is required to use this feature.
"
    REFERENCE "Use BerkeleyDB for Griplist"
    DEFVAL { "" }
    ::= {FilePathsandDatabase 574}

syncStatuseDB4griplist  OBJECT-TYPE
    SYNTAX      OCTET STRING
    MAX-ACCESS  read-only
    STATUS      current
    DESCRIPTION
"
synchronization status for useDB4griplist
-1 - useDB4griplist could not be synchronized
 0 - synchronization not configured
 1 - out of sync - running master mode
 2 - in sync - running  mastermode
 3 - in sync - running slave mode
 4 - in sync - running master mode (wait to reach state 2)
"
    ::= {useDB4griplist 5}

syncStatStruseDB4griplist  OBJECT-TYPE
    SYNTAX      OCTET STRING
    MAX-ACCESS  read-only
    STATUS      current
    DESCRIPTION
"
synchronization status line from file assp_sync.cfg for useDB4griplist
 0 - synchronization not configured
 1 - out of sync - running master mode
 2 - in sync - running  mastermode
 3 - in sync - running slave mode
 4 - in sync - running master mode (wait to reach state 2)
"
    ::= {useDB4griplist 6}

droplist  OBJECT-TYPE
    SYNTAX      OCTET STRING
    MAX-ACCESS  read-write
    STATUS      current
    DESCRIPTION
"
Automatically downloaded (http://www.spamhaus.org/drop/drop.lasso) list of IP's which should be blocked right away. This list could be used in addition to denySMTPConnectionsFrom and/or denySMTPConnectionsFromAlways!
"
    REFERENCE "Drop also Connections from these IP's*"
    DEFVAL { "file:files/droplist.txt" }
    ::= {FilePathsandDatabase 575}

delaydb  OBJECT-TYPE
    SYNTAX      OCTET STRING
    MAX-ACCESS  read-write
    STATUS      current
    DESCRIPTION
"
The file with the delay database.Write only 'DB:' to use a database table instead of a local file, in this case you need to edit the database parameters below.
"
    REFERENCE "Delaying Database"
    DEFVAL { "delaydb" }
    ::= {FilePathsandDatabase 576}

ldaplistdb  OBJECT-TYPE
    SYNTAX      OCTET STRING
    MAX-ACCESS  read-write
    STATUS      current
    DESCRIPTION
"
The file with the LDAP-cache database.Write only 'DB:' to use a database table instead of a local file, in this case you need to edit the database parameters below.
"
    REFERENCE "LDAP Database"
    DEFVAL { "ldaplist" }
    ::= {FilePathsandDatabase 577}

adminusersdb  OBJECT-TYPE
    SYNTAX      OCTET STRING
    MAX-ACCESS  read-write
    STATUS      current
    DESCRIPTION
"
The file with the GUI-Admin-Users database - default to set is 'adminusers'.Write only 'DB:' to use a database table instead of a local file, in this case you need to edit the database parameters below. Before setting this parameter, please set adminusersdbpass to a value of your choice!
 To use this database shared between multiple ASSP's, set all ASSP to mysqlSlaveMode (except the master) and the adminusersdbpass must be the same on all installations! If you want to change the adminusersdbpass, first change it on the master.
"
    REFERENCE "Admin Users Database"
    DEFVAL { "" }
    ::= {FilePathsandDatabase 578}

adminusersdbNoBIN  OBJECT-TYPE
    SYNTAX      OCTET STRING
    MAX-ACCESS  read-write
    STATUS      current
    DESCRIPTION
"
Select this, if adminusersdb is set to 'DB:' and your database engine does not accept or has problems with binary data (eg. Postgres). If you change this value, you have to stop all assp and to cleanup both tables (adminusers and adminusersright) before restarting assp!. To keep your data do the following: do an ExportMysqlDB - change this value - stop assp - drop or clean both tables - start assp - do an ImportMysqlDB .
"
    REFERENCE "Admin Users Database uses no Binary Data (ASCII only)"
    DEFVAL { "" }
    ::= {FilePathsandDatabase 579}

syncStatadminusersdbNoBIN  OBJECT-TYPE
    SYNTAX      OCTET STRING
    MAX-ACCESS  read-only
    STATUS      current
    DESCRIPTION
"
synchronization status for adminusersdbNoBIN
-1 - adminusersdbNoBIN could not be synchronized
 0 - synchronization not configured
 1 - out of sync - running master mode
 2 - in sync - running  mastermode
 3 - in sync - running slave mode
 4 - in sync - running master mode (wait to reach state 2)
"
    ::= {adminusersdbNoBIN 5}

syncStatStradminusersdbNoBIN  OBJECT-TYPE
    SYNTAX      OCTET STRING
    MAX-ACCESS  read-only
    STATUS      current
    DESCRIPTION
"
synchronization status line from file assp_sync.cfg for adminusersdbNoBIN
 0 - synchronization not configured
 1 - out of sync - running master mode
 2 - in sync - running  mastermode
 3 - in sync - running slave mode
 4 - in sync - running master mode (wait to reach state 2)
"
    ::= {adminusersdbNoBIN 6}

adminusersdbpass  OBJECT-TYPE
    SYNTAX      OCTET STRING
    MAX-ACCESS  read-write
    STATUS      current
    DESCRIPTION
"
The passphrase that is used to encrypt the adminusersdb. This has to be the same on all ASSP installations that are sharing the adminusersdb. If you want to change it, first change it on the master installation and than on the slaves. Do not forget to configure 'mysqlSlaveMode' first. An empty value is not valid!
"
    REFERENCE "Admin Users Database PassPhrase"
    DEFVAL { "" }
    ::= {FilePathsandDatabase 580}

syncStatadminusersdbpass  OBJECT-TYPE
    SYNTAX      OCTET STRING
    MAX-ACCESS  read-only
    STATUS      current
    DESCRIPTION
"
synchronization status for adminusersdbpass
-1 - adminusersdbpass could not be synchronized
 0 - synchronization not configured
 1 - out of sync - running master mode
 2 - in sync - running  mastermode
 3 - in sync - running slave mode
 4 - in sync - running master mode (wait to reach state 2)
"
    ::= {adminusersdbpass 5}

syncStatStradminusersdbpass  OBJECT-TYPE
    SYNTAX      OCTET STRING
    MAX-ACCESS  read-only
    STATUS      current
    DESCRIPTION
"
synchronization status line from file assp_sync.cfg for adminusersdbpass
 0 - synchronization not configured
 1 - out of sync - running master mode
 2 - in sync - running  mastermode
 3 - in sync - running slave mode
 4 - in sync - running master mode (wait to reach state 2)
"
    ::= {adminusersdbpass 6}

myhost  OBJECT-TYPE
    SYNTAX      OCTET STRING
    MAX-ACCESS  read-write
    STATUS      current
    DESCRIPTION
"
You need  to use a database instead of local files.
  This way you can share whitelist, delaydb, redlist and penaltybox between servers
"
    REFERENCE "database hostname or IP"
    DEFVAL { "" }
    ::= {FilePathsandDatabase 581}

syncStatmyhost  OBJECT-TYPE
    SYNTAX      OCTET STRING
    MAX-ACCESS  read-only
    STATUS      current
    DESCRIPTION
"
synchronization status for myhost
-1 - myhost could not be synchronized
 0 - synchronization not configured
 1 - out of sync - running master mode
 2 - in sync - running  mastermode
 3 - in sync - running slave mode
 4 - in sync - running master mode (wait to reach state 2)
"
    ::= {myhost 5}

syncStatStrmyhost  OBJECT-TYPE
    SYNTAX      OCTET STRING
    MAX-ACCESS  read-only
    STATUS      current
    DESCRIPTION
"
synchronization status line from file assp_sync.cfg for myhost
 0 - synchronization not configured
 1 - out of sync - running master mode
 2 - in sync - running  mastermode
 3 - in sync - running slave mode
 4 - in sync - running master mode (wait to reach state 2)
"
    ::= {myhost 6}

DBdriver  OBJECT-TYPE
    SYNTAX      OCTET STRING
    MAX-ACCESS  read-write
    STATUS      current
    DESCRIPTION
"
The database driver used to access your database - DBD-driver. The following drivers are available on your system:
  $DBdriversJ
  If you can not find the driver for your database in this list, you should install it via cpan or ppm!
  -  or if you have installed an ODBC-driver for your database and DBD-ODBC, just create a DSN and use ODBC.
  If assp is running on windows and you want to use a MSSQL server as backend, don't use the ODBC driver - use the ADO driver with the DSN definition!
  Useful are ADO|DB2|Informix|ODBC|Oracle|Pg|Sybase|mysql - but any other SQL compatible database should also work.
  syntax examples: driver,option1,option2,...,...
  ADO[,DSN=mydsn[;Provider=sqloledb]]
  DB2
  Informix
  ODBC,DSN=mydsn|driver=\{SQL Server\},Server=server_name
  Oracle,SID=1|INSTANCE_NAME=myinstance|SERVER=myserver|SERVICE_NAME=myservice_name,[PORT=myport]
  Pg[,PORT=myport]
  Sybase,SERVER=myserver,[PORT=myport]
  mysql[,PORT=myport][,mysql_socket=/path/to/mysql.sock][,AutoCommit=1][,mysql_auto_reconnect=1]
  Instead using local files for hashes and lists via shared memory, it is recommended to use  (Perl-module) version 0.34 or higher for highest performance and less memory usage.  The BerkeleyDB (engine) version 4.5 or higher is required to use BerkeleyDB.
  If you specify BerkeleyDB here, the values for myhost, mydb, myuser and mypassword will be ignored. All possible BerkeleyDB option must be defined here - the option for '-Filename' is already set by ASSP! Options could be defined for example:
  BerkeleyDB,-Pagesize=>number,-Env=>[-Cachesize=>number,-Mode=>mode,...,...],...,...
  If '-Env=>[-Cachesize=>number]' (number in bytes) is specified, this cache size will be used at minimum for every single list. This is not recommended, because ASSP does automaticly calculate the right cache for every list. You may setup configuration values for any BerkeleyDB, creating a file  (case sensitive) in the corresponding directory ./tmpDB/[list]. Please use the BerkeleyDB documentation if you don't know the syntax of this file. Any value defined in that file will overwrite the corresponding internal ASSP configuration for this DB.
  The options for all drivers and their possible or required order depends on the DBD driver used, please read the driver's documentation, if you do not know the needed option.
  The username, password, host and databasename are always used from this configuration page.
"
    REFERENCE "database driver name"
    DEFVAL { "" }
    ::= {FilePathsandDatabase 582}

syncStatDBdriver  OBJECT-TYPE
    SYNTAX      OCTET STRING
    MAX-ACCESS  read-only
    STATUS      current
    DESCRIPTION
"
synchronization status for DBdriver
-1 - DBdriver could not be synchronized
 0 - synchronization not configured
 1 - out of sync - running master mode
 2 - in sync - running  mastermode
 3 - in sync - running slave mode
 4 - in sync - running master mode (wait to reach state 2)
"
    ::= {DBdriver 5}

syncStatStrDBdriver  OBJECT-TYPE
    SYNTAX      OCTET STRING
    MAX-ACCESS  read-only
    STATUS      current
    DESCRIPTION
"
synchronization status line from file assp_sync.cfg for DBdriver
 0 - synchronization not configured
 1 - out of sync - running master mode
 2 - in sync - running  mastermode
 3 - in sync - running slave mode
 4 - in sync - running master mode (wait to reach state 2)
"
    ::= {DBdriver 6}

mydb  OBJECT-TYPE
    SYNTAX      OCTET STRING
    MAX-ACCESS  read-write
    STATUS      current
    DESCRIPTION
"
This database must exist before starting ASSP, necessary tables will be created automatically into this database.
"
    REFERENCE "database name"
    DEFVAL { "" }
    ::= {FilePathsandDatabase 583}

syncStatmydb  OBJECT-TYPE
    SYNTAX      OCTET STRING
    MAX-ACCESS  read-only
    STATUS      current
    DESCRIPTION
"
synchronization status for mydb
-1 - mydb could not be synchronized
 0 - synchronization not configured
 1 - out of sync - running master mode
 2 - in sync - running  mastermode
 3 - in sync - running slave mode
 4 - in sync - running master mode (wait to reach state 2)
"
    ::= {mydb 5}

syncStatStrmydb  OBJECT-TYPE
    SYNTAX      OCTET STRING
    MAX-ACCESS  read-only
    STATUS      current
    DESCRIPTION
"
synchronization status line from file assp_sync.cfg for mydb
 0 - synchronization not configured
 1 - out of sync - running master mode
 2 - in sync - running  mastermode
 3 - in sync - running slave mode
 4 - in sync - running master mode (wait to reach state 2)
"
    ::= {mydb 6}

mysqlSlaveMode  OBJECT-TYPE
    SYNTAX      OCTET STRING
    MAX-ACCESS  read-write
    STATUS      current
    DESCRIPTION
"
If you are running more then one assp-computers accessing the same or  a bidirectional replicated database
  this is a slave-assp and no database maintenance will be done by this one!
  Maintenance should only be done by the first assp - the master!
  Maintenance for file based caches and lists will always be done!
"
    REFERENCE "This is a slave of more then one assp-computers accessing the same database"
    DEFVAL { "" }
    ::= {FilePathsandDatabase 584}

myuser  OBJECT-TYPE
    SYNTAX      OCTET STRING
    MAX-ACCESS  read-write
    STATUS      current
    DESCRIPTION
"
This user must have CREATE privilege on database to create tables automatically
"
    REFERENCE "database username"
    DEFVAL { "" }
    ::= {FilePathsandDatabase 585}

syncStatmyuser  OBJECT-TYPE
    SYNTAX      OCTET STRING
    MAX-ACCESS  read-only
    STATUS      current
    DESCRIPTION
"
synchronization status for myuser
-1 - myuser could not be synchronized
 0 - synchronization not configured
 1 - out of sync - running master mode
 2 - in sync - running  mastermode
 3 - in sync - running slave mode
 4 - in sync - running master mode (wait to reach state 2)
"
    ::= {myuser 5}

syncStatStrmyuser  OBJECT-TYPE
    SYNTAX      OCTET STRING
    MAX-ACCESS  read-only
    STATUS      current
    DESCRIPTION
"
synchronization status line from file assp_sync.cfg for myuser
 0 - synchronization not configured
 1 - out of sync - running master mode
 2 - in sync - running  mastermode
 3 - in sync - running slave mode
 4 - in sync - running master mode (wait to reach state 2)
"
    ::= {myuser 6}

mypassword  OBJECT-TYPE
    SYNTAX      OCTET STRING
    MAX-ACCESS  read-write
    STATUS      current
    DESCRIPTION
"

"
    REFERENCE "database password"
    DEFVAL { "" }
    ::= {FilePathsandDatabase 586}

syncStatmypassword  OBJECT-TYPE
    SYNTAX      OCTET STRING
    MAX-ACCESS  read-only
    STATUS      current
    DESCRIPTION
"
synchronization status for mypassword
-1 - mypassword could not be synchronized
 0 - synchronization not configured
 1 - out of sync - running master mode
 2 - in sync - running  mastermode
 3 - in sync - running slave mode
 4 - in sync - running master mode (wait to reach state 2)
"
    ::= {mypassword 5}

syncStatStrmypassword  OBJECT-TYPE
    SYNTAX      OCTET STRING
    MAX-ACCESS  read-only
    STATUS      current
    DESCRIPTION
"
synchronization status line from file assp_sync.cfg for mypassword
 0 - synchronization not configured
 1 - out of sync - running master mode
 2 - in sync - running  mastermode
 3 - in sync - running slave mode
 4 - in sync - running master mode (wait to reach state 2)
"
    ::= {mypassword 6}

importDBDir  OBJECT-TYPE
    SYNTAX      OCTET STRING
    MAX-ACCESS  read-write
    STATUS      current
    DESCRIPTION
"
The folder to import the used tables of the database from.The schema of the files must be the assp-schema.
Files can be:
- pbdb.back.db.(add|rpl)
- pbdb.batv.db.(add|rpl)
- pbdb.black.db.(add|rpl)
- pbdb.dkim.db.(add|rpl)
- pbdb.mxa.db.(add|rpl)
- pbdb.ptr.db(add|rpl)
- pbdb.rbl.db.(add|rpl)
- pbdb.rwl.db.(add|rpl)
- pbdb.sb.db.(add|rpl)
- pbdb.spf.db.(add|rpl)
- pbdb.trap.db.(add|rpl)
- pbdb.uribl.db.(add|rpl)
- pbdb.white.db.(add|rpl)
- ldaplist.(add|rpl)
- redlist.(add|rpl)
- whitelist.(add|rpl)
- persblackdb.(add|rpl)
- spamdb.(add|rpl)
- spamdb.helo.(add|rpl)
- delaydb.(add|rpl)
- delaydb.white.(add|rpl)
- adminusers.(add|rpl)
- adminusersright.(add|rpl)
Use the extension 'add' or 'rpl' to add or replace the records to the tables.
Only files for database-enabled tables will be imported ! The import will be done at ASSP start or if the option below is used.
Imported files will be renamed to *.OK !For example: mysql/dbimport
If you plan to import in to BerkeleyDB - do the following:
- set DisableSMTPNetworking to on
- set all needed DB parameters
- collect your import files
- restart assp and wait until all imports are finished
- restart assp
- set DisableSMTPNetworking to off 
"
    REFERENCE "import directory"
    DEFVAL { "mysql/dbimport" }
    ::= {FilePathsandDatabase 587}

syncStatimportDBDir  OBJECT-TYPE
    SYNTAX      OCTET STRING
    MAX-ACCESS  read-only
    STATUS      current
    DESCRIPTION
"
synchronization status for importDBDir
-1 - importDBDir could not be synchronized
 0 - synchronization not configured
 1 - out of sync - running master mode
 2 - in sync - running  mastermode
 3 - in sync - running slave mode
 4 - in sync - running master mode (wait to reach state 2)
"
    ::= {importDBDir 5}

syncStatStrimportDBDir  OBJECT-TYPE
    SYNTAX      OCTET STRING
    MAX-ACCESS  read-only
    STATUS      current
    DESCRIPTION
"
synchronization status line from file assp_sync.cfg for importDBDir
 0 - synchronization not configured
 1 - out of sync - running master mode
 2 - in sync - running  mastermode
 3 - in sync - running slave mode
 4 - in sync - running master mode (wait to reach state 2)
"
    ::= {importDBDir 6}

preventBulkImport  OBJECT-TYPE
    SYNTAX      OCTET STRING
    MAX-ACCESS  read-write
    STATUS      current
    DESCRIPTION
"
Do not select, if you are using MySQL! Doing a Bulk-Import of data, ASSP modifies the properties of table columnes. This could result in breaking some configured DB features like DB-replication in MSSQL. If selected, ASSP will do a line per line insert/update (which takes much more time) without modifying the tables properties.
"
    REFERENCE "Prevent Bulk Import"
    DEFVAL { "" }
    ::= {FilePathsandDatabase 588}

syncStatpreventBulkImport  OBJECT-TYPE
    SYNTAX      OCTET STRING
    MAX-ACCESS  read-only
    STATUS      current
    DESCRIPTION
"
synchronization status for preventBulkImport
-1 - preventBulkImport could not be synchronized
 0 - synchronization not configured
 1 - out of sync - running master mode
 2 - in sync - running  mastermode
 3 - in sync - running slave mode
 4 - in sync - running master mode (wait to reach state 2)
"
    ::= {preventBulkImport 5}

syncStatStrpreventBulkImport  OBJECT-TYPE
    SYNTAX      OCTET STRING
    MAX-ACCESS  read-only
    STATUS      current
    DESCRIPTION
"
synchronization status line from file assp_sync.cfg for preventBulkImport
 0 - synchronization not configured
 1 - out of sync - running master mode
 2 - in sync - running  mastermode
 3 - in sync - running slave mode
 4 - in sync - running master mode (wait to reach state 2)
"
    ::= {preventBulkImport 6}

ImportMysqlDB  OBJECT-TYPE
    SYNTAX      OCTET STRING
    MAX-ACCESS  read-write
    STATUS      current
    DESCRIPTION
"
All files from the 'importDBDir' will be imported in to database . Please define the directory above, before using the import!
&nbsp;
"
    REFERENCE "import all files from the importDBDir Directory in to the database - now."
    DEFVAL { "" }
    ::= {FilePathsandDatabase 589}

exportDBDir  OBJECT-TYPE
    SYNTAX      OCTET STRING
    MAX-ACCESS  read-write
    STATUS      current
    DESCRIPTION
"
The folder to export the used tables of the database.The schema of the files is the assp-schema.Ten versions of exports are available!For example: mysql/dbexport
"
    REFERENCE "export directory"
    DEFVAL { "mysql/dbexport" }
    ::= {FilePathsandDatabase 590}

syncStatexportDBDir  OBJECT-TYPE
    SYNTAX      OCTET STRING
    MAX-ACCESS  read-only
    STATUS      current
    DESCRIPTION
"
synchronization status for exportDBDir
-1 - exportDBDir could not be synchronized
 0 - synchronization not configured
 1 - out of sync - running master mode
 2 - in sync - running  mastermode
 3 - in sync - running slave mode
 4 - in sync - running master mode (wait to reach state 2)
"
    ::= {exportDBDir 5}

syncStatStrexportDBDir  OBJECT-TYPE
    SYNTAX      OCTET STRING
    MAX-ACCESS  read-only
    STATUS      current
    DESCRIPTION
"
synchronization status line from file assp_sync.cfg for exportDBDir
 0 - synchronization not configured
 1 - out of sync - running master mode
 2 - in sync - running  mastermode
 3 - in sync - running slave mode
 4 - in sync - running master mode (wait to reach state 2)
"
    ::= {exportDBDir 6}

ExportMysqlDB  OBJECT-TYPE
    SYNTAX      OCTET STRING
    MAX-ACCESS  read-write
    STATUS      current
    DESCRIPTION
"
All table of the database will be exported to the 'exportDBDir' Directory. Please define the Directory above, before using the export!
&nbsp;
"
    REFERENCE "export all tables from the database"
    DEFVAL { "" }
    ::= {FilePathsandDatabase 591}

backupDBDir  OBJECT-TYPE
    SYNTAX      OCTET STRING
    MAX-ACCESS  read-write
    STATUS      current
    DESCRIPTION
"
The folder to backup the used tables of the database.The schema of the files is the assp-schema.Ten versions of backups are available!For example: mysql/dbbackup
"
    REFERENCE "backup directory"
    DEFVAL { "mysql/dbbackup" }
    ::= {FilePathsandDatabase 592}

syncStatbackupDBDir  OBJECT-TYPE
    SYNTAX      OCTET STRING
    MAX-ACCESS  read-only
    STATUS      current
    DESCRIPTION
"
synchronization status for backupDBDir
-1 - backupDBDir could not be synchronized
 0 - synchronization not configured
 1 - out of sync - running master mode
 2 - in sync - running  mastermode
 3 - in sync - running slave mode
 4 - in sync - running master mode (wait to reach state 2)
"
    ::= {backupDBDir 5}

syncStatStrbackupDBDir  OBJECT-TYPE
    SYNTAX      OCTET STRING
    MAX-ACCESS  read-only
    STATUS      current
    DESCRIPTION
"
synchronization status line from file assp_sync.cfg for backupDBDir
 0 - synchronization not configured
 1 - out of sync - running master mode
 2 - in sync - running  mastermode
 3 - in sync - running slave mode
 4 - in sync - running master mode (wait to reach state 2)
"
    ::= {backupDBDir 6}

backupDBInterval  OBJECT-TYPE
    SYNTAX      OCTET STRING
    MAX-ACCESS  read-write
    STATUS      current
    DESCRIPTION
"
backup the database (all tables used by assp at the time)  every this hours.
  Defaults to 2 hours.
"
    REFERENCE "backup database Interval <sup>s</sup>"
    DEFVAL { "2" }
    ::= {FilePathsandDatabase 593}

syncStatbackupDBInterval  OBJECT-TYPE
    SYNTAX      OCTET STRING
    MAX-ACCESS  read-only
    STATUS      current
    DESCRIPTION
"
synchronization status for backupDBInterval
-1 - backupDBInterval could not be synchronized
 0 - synchronization not configured
 1 - out of sync - running master mode
 2 - in sync - running  mastermode
 3 - in sync - running slave mode
 4 - in sync - running master mode (wait to reach state 2)
"
    ::= {backupDBInterval 5}

syncStatStrbackupDBInterval  OBJECT-TYPE
    SYNTAX      OCTET STRING
    MAX-ACCESS  read-only
    STATUS      current
    DESCRIPTION
"
synchronization status line from file assp_sync.cfg for backupDBInterval
 0 - synchronization not configured
 1 - out of sync - running master mode
 2 - in sync - running  mastermode
 3 - in sync - running slave mode
 4 - in sync - running master mode (wait to reach state 2)
"
    ::= {backupDBInterval 6}

copyDBToOrgLoc  OBJECT-TYPE
    SYNTAX      OCTET STRING
    MAX-ACCESS  read-write
    STATUS      current
    DESCRIPTION
"
If DB-backup is enabled, the last backupversion is also copied to the original location.
  If database connections are failed, while ASSP is running, ASSP will switch over to use these files instead of DB-tables.
  DB-tables will not be imported from here, this must be done from the importDBDir!
"
    REFERENCE "copy the last DB-backup to the original location"
    DEFVAL { "1" }
    ::= {FilePathsandDatabase 594}

syncStatcopyDBToOrgLoc  OBJECT-TYPE
    SYNTAX      OCTET STRING
    MAX-ACCESS  read-only
    STATUS      current
    DESCRIPTION
"
synchronization status for copyDBToOrgLoc
-1 - copyDBToOrgLoc could not be synchronized
 0 - synchronization not configured
 1 - out of sync - running master mode
 2 - in sync - running  mastermode
 3 - in sync - running slave mode
 4 - in sync - running master mode (wait to reach state 2)
"
    ::= {copyDBToOrgLoc 5}

syncStatStrcopyDBToOrgLoc  OBJECT-TYPE
    SYNTAX      OCTET STRING
    MAX-ACCESS  read-only
    STATUS      current
    DESCRIPTION
"
synchronization status line from file assp_sync.cfg for copyDBToOrgLoc
 0 - synchronization not configured
 1 - out of sync - running master mode
 2 - in sync - running  mastermode
 3 - in sync - running slave mode
 4 - in sync - running master mode (wait to reach state 2)
"
    ::= {copyDBToOrgLoc 6}

logfile  OBJECT-TYPE
    SYNTAX      OCTET STRING
    MAX-ACCESS  read-write
    STATUS      current
    DESCRIPTION
"
Blank if you don't want a log file. Change it to maillog.log if you don't want auto rollover.
  NOTE: Changing this field requires restarting ASSP before changes take effect.
"
    REFERENCE "ASSP Logfile"
    DEFVAL { "logs/maillog.txt" }
    ::= {FilePathsandDatabase 595}

syncStatlogfile  OBJECT-TYPE
    SYNTAX      OCTET STRING
    MAX-ACCESS  read-only
    STATUS      current
    DESCRIPTION
"
synchronization status for logfile
-1 - logfile could not be synchronized
 0 - synchronization not configured
 1 - out of sync - running master mode
 2 - in sync - running  mastermode
 3 - in sync - running slave mode
 4 - in sync - running master mode (wait to reach state 2)
"
    ::= {logfile 5}

syncStatStrlogfile  OBJECT-TYPE
    SYNTAX      OCTET STRING
    MAX-ACCESS  read-only
    STATUS      current
    DESCRIPTION
"
synchronization status line from file assp_sync.cfg for logfile
 0 - synchronization not configured
 1 - out of sync - running master mode
 2 - in sync - running  mastermode
 3 - in sync - running slave mode
 4 - in sync - running master mode (wait to reach state 2)
"
    ::= {logfile 6}

MaxLogAge  OBJECT-TYPE
    SYNTAX      OCTET STRING
    MAX-ACCESS  read-write
    STATUS      current
    DESCRIPTION
"
The maximum file age in days of logfiles. If a logfile is older than this number in days, the file will be deleted. Default is 0 - recommended is 30. A value of 0 disables this feature and no logfile will be deleted because of its age.
"
    REFERENCE "Max Age of Logfiles"
    DEFVAL { "0" }
    ::= {FilePathsandDatabase 596}

syncStatMaxLogAge  OBJECT-TYPE
    SYNTAX      OCTET STRING
    MAX-ACCESS  read-only
    STATUS      current
    DESCRIPTION
"
synchronization status for MaxLogAge
-1 - MaxLogAge could not be synchronized
 0 - synchronization not configured
 1 - out of sync - running master mode
 2 - in sync - running  mastermode
 3 - in sync - running slave mode
 4 - in sync - running master mode (wait to reach state 2)
"
    ::= {MaxLogAge 5}

syncStatStrMaxLogAge  OBJECT-TYPE
    SYNTAX      OCTET STRING
    MAX-ACCESS  read-only
    STATUS      current
    DESCRIPTION
"
synchronization status line from file assp_sync.cfg for MaxLogAge
 0 - synchronization not configured
 1 - out of sync - running master mode
 2 - in sync - running  mastermode
 3 - in sync - running slave mode
 4 - in sync - running master mode (wait to reach state 2)
"
    ::= {MaxLogAge 6}

MaxLogAgeSchedule  OBJECT-TYPE
    SYNTAX      OCTET STRING
    MAX-ACCESS  read-write
    STATUS      current
    DESCRIPTION
"
Runtime hour for deleting old logfiles. Set a number between 0 and 23. 0 means midnight, 1 is default.
"
    REFERENCE "Runtime MaxLogAge"
    DEFVAL { "1" }
    ::= {FilePathsandDatabase 597}

syncStatMaxLogAgeSchedule  OBJECT-TYPE
    SYNTAX      OCTET STRING
    MAX-ACCESS  read-only
    STATUS      current
    DESCRIPTION
"
synchronization status for MaxLogAgeSchedule
-1 - MaxLogAgeSchedule could not be synchronized
 0 - synchronization not configured
 1 - out of sync - running master mode
 2 - in sync - running  mastermode
 3 - in sync - running slave mode
 4 - in sync - running master mode (wait to reach state 2)
"
    ::= {MaxLogAgeSchedule 5}

syncStatStrMaxLogAgeSchedule  OBJECT-TYPE
    SYNTAX      OCTET STRING
    MAX-ACCESS  read-only
    STATUS      current
    DESCRIPTION
"
synchronization status line from file assp_sync.cfg for MaxLogAgeSchedule
 0 - synchronization not configured
 1 - out of sync - running master mode
 2 - in sync - running  mastermode
 3 - in sync - running slave mode
 4 - in sync - running master mode (wait to reach state 2)
"
    ::= {MaxLogAgeSchedule 6}

pidfile  OBJECT-TYPE
    SYNTAX      OCTET STRING
    MAX-ACCESS  read-write
    STATUS      current
    DESCRIPTION
"
Blank is not a valid value!
  You have to restart ASSP before you get a pid file in the new location.
  This file is used to detect a clean shutdown of ASSP - in this case it does not exist at startup!
  
"
    REFERENCE "PID File"
    DEFVAL { "pid" }
    ::= {FilePathsandDatabase 598}

syncStatpidfile  OBJECT-TYPE
    SYNTAX      OCTET STRING
    MAX-ACCESS  read-only
    STATUS      current
    DESCRIPTION
"
synchronization status for pidfile
-1 - pidfile could not be synchronized
 0 - synchronization not configured
 1 - out of sync - running master mode
 2 - in sync - running  mastermode
 3 - in sync - running slave mode
 4 - in sync - running master mode (wait to reach state 2)
"
    ::= {pidfile 5}

syncStatStrpidfile  OBJECT-TYPE
    SYNTAX      OCTET STRING
    MAX-ACCESS  read-only
    STATUS      current
    DESCRIPTION
"
synchronization status line from file assp_sync.cfg for pidfile
 0 - synchronization not configured
 1 - out of sync - running master mode
 2 - in sync - running  mastermode
 3 - in sync - running slave mode
 4 - in sync - running master mode (wait to reach state 2)
"
    ::= {pidfile 6}

fillUpImportDBDir  OBJECT-TYPE
    SYNTAX      OCTET STRING
    MAX-ACCESS  read-write
    STATUS      current
    DESCRIPTION
"
If set to a value between 1 and 9, the corresponding backup file for any list/hash that configured to use a database will be copied from the backupDBDir to the importDBDir. The resulting file name will has an extension of '.rpl', so a possible import will replace the current table content. If a value of 'L' is defined, the last backup will be used. Possible values are L or 1 - 9 or blank. Any configured value will be reset to blank after the copy is finished.
"
    REFERENCE "Fill the Import Folder"
    DEFVAL { "" }
    ::= {FilePathsandDatabase 899}

persblackdb  OBJECT-TYPE
    SYNTAX      OCTET STRING
    MAX-ACCESS  read-write
    STATUS      current
    DESCRIPTION
"
The file with the personal blacklist. The check of the personal black list is done shortly after the RCPT TO: command. This command will be rejected if an entry is found - any other setting except send250OK and send250OKISP will be ignored.
  Each entry is represented by two comma separated values TO,FROM (and an expiration date).
  TO could be any of : email address, [subdomain.]domain.tld, @[subdomain.]domain.tld, *@[subdomain.]domain.tld - the last three entry options could be only added and removed by editing the list in the GUI !
  FROM could be any of : email address or any [@][subdomain.][domain.]TLD variant (wildcards are allowed). All values are supported by the email interface for all local users.
  Write only 'DB:' to use a database table instead of a local file, in this case you need to edit the database parameters below.
"
    REFERENCE "Personal Blacklist Database File"
    DEFVAL { "persblack" }
    ::= {FilePathsandDatabase 910}

DBCacheMaxAge  OBJECT-TYPE
    SYNTAX      OCTET STRING
    MAX-ACCESS  read-write
    STATUS      current
    DESCRIPTION
"
Setting this value above zero, enables an internal database cache for every defined table to reduce the concurrent database queries and to prevent possible record access collisions, which could cause stucking workers on some systems
  The value defines the maximum age in seconds a record will exists untouched in the table cache.
  Be carefull, setting this value too high in a database replication envirionment could cause unexpected query results, because this cache is NOT shared between multiple assp instances.
  If set, a value of 10 seems to be popular in any case. An too less value, will produce overhead without any advantage. An too high setting could cause the described database consistency problems.
"
    REFERENCE "Database Maximum Cache Age"
    DEFVAL { "0" }
    ::= {FilePathsandDatabase 1002}

syncStatDBCacheMaxAge  OBJECT-TYPE
    SYNTAX      OCTET STRING
    MAX-ACCESS  read-only
    STATUS      current
    DESCRIPTION
"
synchronization status for DBCacheMaxAge
-1 - DBCacheMaxAge could not be synchronized
 0 - synchronization not configured
 1 - out of sync - running master mode
 2 - in sync - running  mastermode
 3 - in sync - running slave mode
 4 - in sync - running master mode (wait to reach state 2)
"
    ::= {DBCacheMaxAge 5}

syncStatStrDBCacheMaxAge  OBJECT-TYPE
    SYNTAX      OCTET STRING
    MAX-ACCESS  read-only
    STATUS      current
    DESCRIPTION
"
synchronization status line from file assp_sync.cfg for DBCacheMaxAge
 0 - synchronization not configured
 1 - out of sync - running master mode
 2 - in sync - running  mastermode
 3 - in sync - running slave mode
 4 - in sync - running master mode (wait to reach state 2)
"
    ::= {DBCacheMaxAge 6}

Collecting  OBJECT IDENTIFIER ::= {asspConfig 28}
spamaddresses  OBJECT-TYPE
    SYNTAX      OCTET STRING
    MAX-ACCESS  read-write
    STATUS      current
    DESCRIPTION
"
Mail to any of these addresses are always spam and will contribute to the spam-collection unless from someone on the whitelist. Accepts specific addresses (user@domain.com), user parts (user) or entire domains (@domain.com). The addresses are not validated, they  are readdressed to ccallspam, however you can supersede this by putting a valid address into sendAllCollect below.
"
    REFERENCE "Spam Collect Addresses*"
    DEFVAL { "" }
    ::= {Collecting 599}

syncStatspamaddresses  OBJECT-TYPE
    SYNTAX      OCTET STRING
    MAX-ACCESS  read-only
    STATUS      current
    DESCRIPTION
"
synchronization status for spamaddresses
-1 - spamaddresses could not be synchronized
 0 - synchronization not configured
 1 - out of sync - running master mode
 2 - in sync - running  mastermode
 3 - in sync - running slave mode
 4 - in sync - running master mode (wait to reach state 2)
"
    ::= {spamaddresses 5}

syncStatStrspamaddresses  OBJECT-TYPE
    SYNTAX      OCTET STRING
    MAX-ACCESS  read-only
    STATUS      current
    DESCRIPTION
"
synchronization status line from file assp_sync.cfg for spamaddresses
 0 - synchronization not configured
 1 - out of sync - running master mode
 2 - in sync - running  mastermode
 3 - in sync - running slave mode
 4 - in sync - running master mode (wait to reach state 2)
"
    ::= {spamaddresses 6}

sendAllCollect  OBJECT-TYPE
    SYNTAX      OCTET STRING
    MAX-ACCESS  read-write
    STATUS      current
    DESCRIPTION
"
ASSP will readdress messages addressed to Collect Addresses to this address.
  For example: collect@mydomain.com
"
    REFERENCE "Catchall Address for Collect Addresses"
    DEFVAL { "" }
    ::= {Collecting 600}

syncStatsendAllCollect  OBJECT-TYPE
    SYNTAX      OCTET STRING
    MAX-ACCESS  read-only
    STATUS      current
    DESCRIPTION
"
synchronization status for sendAllCollect
-1 - sendAllCollect could not be synchronized
 0 - synchronization not configured
 1 - out of sync - running master mode
 2 - in sync - running  mastermode
 3 - in sync - running slave mode
 4 - in sync - running master mode (wait to reach state 2)
"
    ::= {sendAllCollect 5}

syncStatStrsendAllCollect  OBJECT-TYPE
    SYNTAX      OCTET STRING
    MAX-ACCESS  read-only
    STATUS      current
    DESCRIPTION
"
synchronization status line from file assp_sync.cfg for sendAllCollect
 0 - synchronization not configured
 1 - out of sync - running master mode
 2 - in sync - running  mastermode
 3 - in sync - running slave mode
 4 - in sync - running master mode (wait to reach state 2)
"
    ::= {sendAllCollect 6}

DoNotBlockCollect  OBJECT-TYPE
    SYNTAX      OCTET STRING
    MAX-ACCESS  read-write
    STATUS      current
    DESCRIPTION
"
If set ASSP will block messages from Collect Addresses after other checks are performed. That may help to test and control activated filters.
"
    REFERENCE "Use Collect Addresses for Testing Your Environment"
    DEFVAL { "" }
    ::= {Collecting 601}

syncStatDoNotBlockCollect  OBJECT-TYPE
    SYNTAX      OCTET STRING
    MAX-ACCESS  read-only
    STATUS      current
    DESCRIPTION
"
synchronization status for DoNotBlockCollect
-1 - DoNotBlockCollect could not be synchronized
 0 - synchronization not configured
 1 - out of sync - running master mode
 2 - in sync - running  mastermode
 3 - in sync - running slave mode
 4 - in sync - running master mode (wait to reach state 2)
"
    ::= {DoNotBlockCollect 5}

syncStatStrDoNotBlockCollect  OBJECT-TYPE
    SYNTAX      OCTET STRING
    MAX-ACCESS  read-only
    STATUS      current
    DESCRIPTION
"
synchronization status line from file assp_sync.cfg for DoNotBlockCollect
 0 - synchronization not configured
 1 - out of sync - running master mode
 2 - in sync - running  mastermode
 3 - in sync - running slave mode
 4 - in sync - running master mode (wait to reach state 2)
"
    ::= {DoNotBlockCollect 6}

UseTrapToCollect  OBJECT-TYPE
    SYNTAX      OCTET STRING
    MAX-ACCESS  read-write
    STATUS      current
    DESCRIPTION
"
If set ASSP will use addresses from DoPenaltyMakeTraps and spamtrapaddresses to collect spams.
"
    REFERENCE "Use Penalty Trap Addresses To Collect"
    DEFVAL { "" }
    ::= {Collecting 602}

syncStatUseTrapToCollect  OBJECT-TYPE
    SYNTAX      OCTET STRING
    MAX-ACCESS  read-only
    STATUS      current
    DESCRIPTION
"
synchronization status for UseTrapToCollect
-1 - UseTrapToCollect could not be synchronized
 0 - synchronization not configured
 1 - out of sync - running master mode
 2 - in sync - running  mastermode
 3 - in sync - running slave mode
 4 - in sync - running master mode (wait to reach state 2)
"
    ::= {UseTrapToCollect 5}

syncStatStrUseTrapToCollect  OBJECT-TYPE
    SYNTAX      OCTET STRING
    MAX-ACCESS  read-only
    STATUS      current
    DESCRIPTION
"
synchronization status line from file assp_sync.cfg for UseTrapToCollect
 0 - synchronization not configured
 1 - out of sync - running master mode
 2 - in sync - running  mastermode
 3 - in sync - running slave mode
 4 - in sync - running master mode (wait to reach state 2)
"
    ::= {UseTrapToCollect 6}

noCollecting  OBJECT-TYPE
    SYNTAX      OCTET STRING
    MAX-ACCESS  read-write
    STATUS      current
    DESCRIPTION
"
Accepts specific addresses (user@domain.com), user parts (user) or entire domains (@domain.com).
"
    REFERENCE "Do Not Collect Messages from/to these Addresses*"
    DEFVAL { "" }
    ::= {Collecting 603}

syncStatnoCollecting  OBJECT-TYPE
    SYNTAX      OCTET STRING
    MAX-ACCESS  read-only
    STATUS      current
    DESCRIPTION
"
synchronization status for noCollecting
-1 - noCollecting could not be synchronized
 0 - synchronization not configured
 1 - out of sync - running master mode
 2 - in sync - running  mastermode
 3 - in sync - running slave mode
 4 - in sync - running master mode (wait to reach state 2)
"
    ::= {noCollecting 5}

syncStatStrnoCollecting  OBJECT-TYPE
    SYNTAX      OCTET STRING
    MAX-ACCESS  read-only
    STATUS      current
    DESCRIPTION
"
synchronization status line from file assp_sync.cfg for noCollecting
 0 - synchronization not configured
 1 - out of sync - running master mode
 2 - in sync - running  mastermode
 3 - in sync - running slave mode
 4 - in sync - running master mode (wait to reach state 2)
"
    ::= {noCollecting 6}

DoNotCollectRedRe  OBJECT-TYPE
    SYNTAX      OCTET STRING
    MAX-ACCESS  read-write
    STATUS      current
    DESCRIPTION
"
Mails (Spam/Ham) matching Red Regex (redRe) will not be stored in the collection folders.
"
    REFERENCE "Do Not Collect RedRe Matching Mails"
    DEFVAL { "1" }
    ::= {Collecting 604}

syncStatDoNotCollectRedRe  OBJECT-TYPE
    SYNTAX      OCTET STRING
    MAX-ACCESS  read-only
    STATUS      current
    DESCRIPTION
"
synchronization status for DoNotCollectRedRe
-1 - DoNotCollectRedRe could not be synchronized
 0 - synchronization not configured
 1 - out of sync - running master mode
 2 - in sync - running  mastermode
 3 - in sync - running slave mode
 4 - in sync - running master mode (wait to reach state 2)
"
    ::= {DoNotCollectRedRe 5}

syncStatStrDoNotCollectRedRe  OBJECT-TYPE
    SYNTAX      OCTET STRING
    MAX-ACCESS  read-only
    STATUS      current
    DESCRIPTION
"
synchronization status line from file assp_sync.cfg for DoNotCollectRedRe
 0 - synchronization not configured
 1 - out of sync - running master mode
 2 - in sync - running  mastermode
 3 - in sync - running slave mode
 4 - in sync - running master mode (wait to reach state 2)
"
    ::= {DoNotCollectRedRe 6}

DoNotCollectRedList  OBJECT-TYPE
    SYNTAX      OCTET STRING
    MAX-ACCESS  read-write
    STATUS      current
    DESCRIPTION
"
Mails (Spam/Ham) matching  Redlist will not be stored in the collection folders.
"
    REFERENCE "Do Not Collect Redlisted Mails"
    DEFVAL { "1" }
    ::= {Collecting 605}

syncStatDoNotCollectRedList  OBJECT-TYPE
    SYNTAX      OCTET STRING
    MAX-ACCESS  read-only
    STATUS      current
    DESCRIPTION
"
synchronization status for DoNotCollectRedList
-1 - DoNotCollectRedList could not be synchronized
 0 - synchronization not configured
 1 - out of sync - running master mode
 2 - in sync - running  mastermode
 3 - in sync - running slave mode
 4 - in sync - running master mode (wait to reach state 2)
"
    ::= {DoNotCollectRedList 5}

syncStatStrDoNotCollectRedList  OBJECT-TYPE
    SYNTAX      OCTET STRING
    MAX-ACCESS  read-only
    STATUS      current
    DESCRIPTION
"
synchronization status line from file assp_sync.cfg for DoNotCollectRedList
 0 - synchronization not configured
 1 - out of sync - running master mode
 2 - in sync - running  mastermode
 3 - in sync - running slave mode
 4 - in sync - running master mode (wait to reach state 2)
"
    ::= {DoNotCollectRedList 6}

DoNotCollectBounces  OBJECT-TYPE
    SYNTAX      OCTET STRING
    MAX-ACCESS  read-write
    STATUS      current
    DESCRIPTION
"
Mails matching &lt;Bounce Senders&gt; will not be collected.
"
    REFERENCE "Do Not Collect Bounced Mails"
    DEFVAL { "1" }
    ::= {Collecting 606}

syncStatDoNotCollectBounces  OBJECT-TYPE
    SYNTAX      OCTET STRING
    MAX-ACCESS  read-only
    STATUS      current
    DESCRIPTION
"
synchronization status for DoNotCollectBounces
-1 - DoNotCollectBounces could not be synchronized
 0 - synchronization not configured
 1 - out of sync - running master mode
 2 - in sync - running  mastermode
 3 - in sync - running slave mode
 4 - in sync - running master mode (wait to reach state 2)
"
    ::= {DoNotCollectBounces 5}

syncStatStrDoNotCollectBounces  OBJECT-TYPE
    SYNTAX      OCTET STRING
    MAX-ACCESS  read-only
    STATUS      current
    DESCRIPTION
"
synchronization status line from file assp_sync.cfg for DoNotCollectBounces
 0 - synchronization not configured
 1 - out of sync - running master mode
 2 - in sync - running  mastermode
 3 - in sync - running slave mode
 4 - in sync - running master mode (wait to reach state 2)
"
    ::= {DoNotCollectBounces 6}

NoMaillog  OBJECT-TYPE
    SYNTAX      OCTET STRING
    MAX-ACCESS  read-write
    STATUS      current
    DESCRIPTION
"
Check this if you're using Whitelist-Only and don't care to save mail to build the Bayesian database.
"
    REFERENCE "Don't Collect Mail"
    DEFVAL { "" }
    ::= {Collecting 607}

syncStatNoMaillog  OBJECT-TYPE
    SYNTAX      OCTET STRING
    MAX-ACCESS  read-only
    STATUS      current
    DESCRIPTION
"
synchronization status for NoMaillog
-1 - NoMaillog could not be synchronized
 0 - synchronization not configured
 1 - out of sync - running master mode
 2 - in sync - running  mastermode
 3 - in sync - running slave mode
 4 - in sync - running master mode (wait to reach state 2)
"
    ::= {NoMaillog 5}

syncStatStrNoMaillog  OBJECT-TYPE
    SYNTAX      OCTET STRING
    MAX-ACCESS  read-only
    STATUS      current
    DESCRIPTION
"
synchronization status line from file assp_sync.cfg for NoMaillog
 0 - synchronization not configured
 1 - out of sync - running master mode
 2 - in sync - running  mastermode
 3 - in sync - running slave mode
 4 - in sync - running master mode (wait to reach state 2)
"
    ::= {NoMaillog 6}

MaxFiles  OBJECT-TYPE
    SYNTAX      OCTET STRING
    MAX-ACCESS  read-write
    STATUS      current
    DESCRIPTION
"
If you're not using subjects as file names ( UseSubjectsAsMaillogNames ), this is the maximum number of files to keep in each collection (spam &amp; nonspam)
  It's actually less than this -- files get a random number between 1 and MaxFiles.
"
    REFERENCE "Max Files"
    DEFVAL { "14000" }
    ::= {Collecting 608}

syncStatMaxFiles  OBJECT-TYPE
    SYNTAX      OCTET STRING
    MAX-ACCESS  read-only
    STATUS      current
    DESCRIPTION
"
synchronization status for MaxFiles
-1 - MaxFiles could not be synchronized
 0 - synchronization not configured
 1 - out of sync - running master mode
 2 - in sync - running  mastermode
 3 - in sync - running slave mode
 4 - in sync - running master mode (wait to reach state 2)
"
    ::= {MaxFiles 5}

syncStatStrMaxFiles  OBJECT-TYPE
    SYNTAX      OCTET STRING
    MAX-ACCESS  read-only
    STATUS      current
    DESCRIPTION
"
synchronization status line from file assp_sync.cfg for MaxFiles
 0 - synchronization not configured
 1 - out of sync - running master mode
 2 - in sync - running  mastermode
 3 - in sync - running slave mode
 4 - in sync - running master mode (wait to reach state 2)
"
    ::= {MaxFiles 6}

FilesDistribution  OBJECT-TYPE
    SYNTAX      OCTET STRING
    MAX-ACCESS  read-write
    STATUS      current
    DESCRIPTION
"
This defines how file names are chosen in each collection. If set to 1, names are uniformly distributed. If set between 0.01 and 0.99, names distribution is exponential -- files get lower numbers more frequently. This prevents from corpus being refreshed too quickly, especially when MaxFiles is set to low value (ex. 3000). This setting is ignored if UseSubjectsAsMaillogNames is set to ON.
 Recommended: 0.5, Default: 1
"
    REFERENCE "Files Distribution"
    DEFVAL { "1" }
    ::= {Collecting 609}

syncStatFilesDistribution  OBJECT-TYPE
    SYNTAX      OCTET STRING
    MAX-ACCESS  read-only
    STATUS      current
    DESCRIPTION
"
synchronization status for FilesDistribution
-1 - FilesDistribution could not be synchronized
 0 - synchronization not configured
 1 - out of sync - running master mode
 2 - in sync - running  mastermode
 3 - in sync - running slave mode
 4 - in sync - running master mode (wait to reach state 2)
"
    ::= {FilesDistribution 5}

syncStatStrFilesDistribution  OBJECT-TYPE
    SYNTAX      OCTET STRING
    MAX-ACCESS  read-only
    STATUS      current
    DESCRIPTION
"
synchronization status line from file assp_sync.cfg for FilesDistribution
 0 - synchronization not configured
 1 - out of sync - running master mode
 2 - in sync - running  mastermode
 3 - in sync - running slave mode
 4 - in sync - running master mode (wait to reach state 2)
"
    ::= {FilesDistribution 6}

UseSubjectsAsMaillogNames  OBJECT-TYPE
    SYNTAX      OCTET STRING
    MAX-ACCESS  read-write
    STATUS      current
    DESCRIPTION
"
You can turn this on to help you manualy identify mail in your spam and non-spam collections. This will prevent ASSP from controlling the number of files in your collections(-> MaxFiles ). It is recommended to switch on MaintBayesCollection and to setup MaxNoBayesFileAge to your needs, if you have switched on this option.
"
    REFERENCE "Use Subject as Maillog Names"
    DEFVAL { "1" }
    ::= {Collecting 610}

syncStatUseSubjectsAsMaillogNames  OBJECT-TYPE
    SYNTAX      OCTET STRING
    MAX-ACCESS  read-only
    STATUS      current
    DESCRIPTION
"
synchronization status for UseSubjectsAsMaillogNames
-1 - UseSubjectsAsMaillogNames could not be synchronized
 0 - synchronization not configured
 1 - out of sync - running master mode
 2 - in sync - running  mastermode
 3 - in sync - running slave mode
 4 - in sync - running master mode (wait to reach state 2)
"
    ::= {UseSubjectsAsMaillogNames 5}

syncStatStrUseSubjectsAsMaillogNames  OBJECT-TYPE
    SYNTAX      OCTET STRING
    MAX-ACCESS  read-only
    STATUS      current
    DESCRIPTION
"
synchronization status line from file assp_sync.cfg for UseSubjectsAsMaillogNames
 0 - synchronization not configured
 1 - out of sync - running master mode
 2 - in sync - running  mastermode
 3 - in sync - running slave mode
 4 - in sync - running master mode (wait to reach state 2)
"
    ::= {UseSubjectsAsMaillogNames 6}

UseUnicode4MaillogNames  OBJECT-TYPE
    SYNTAX      OCTET STRING
    MAX-ACCESS  read-write
    STATUS      current
    DESCRIPTION
"
If you have switched on UseSubjectsAsMaillogNames and your default (local language) characterset (please setup ConsoleCharset) needs 8 Bit like 'KOI8-r','CP-866','Windows-1251','Windows-1252','ISO-8859-X','X-Mac-Cyrillic','JIS_X0201' or any other (or is UTF-8) - and you want to have readable filenames in the maillog and on the console screen, you can switch on this option. The resolution of some characters written to the console could be incorrect depending on your operating system. This requires an installed  module in PERL.
  If in addition the module  is installed on windows plattforms, assp will generate unicode filenames for the collected corpus files (already on nix systems).
"
    REFERENCE "Use Unicode to build Maillog Names"
    DEFVAL { "" }
    ::= {Collecting 611}

syncStatUseUnicode4MaillogNames  OBJECT-TYPE
    SYNTAX      OCTET STRING
    MAX-ACCESS  read-only
    STATUS      current
    DESCRIPTION
"
synchronization status for UseUnicode4MaillogNames
-1 - UseUnicode4MaillogNames could not be synchronized
 0 - synchronization not configured
 1 - out of sync - running master mode
 2 - in sync - running  mastermode
 3 - in sync - running slave mode
 4 - in sync - running master mode (wait to reach state 2)
"
    ::= {UseUnicode4MaillogNames 5}

syncStatStrUseUnicode4MaillogNames  OBJECT-TYPE
    SYNTAX      OCTET STRING
    MAX-ACCESS  read-only
    STATUS      current
    DESCRIPTION
"
synchronization status line from file assp_sync.cfg for UseUnicode4MaillogNames
 0 - synchronization not configured
 1 - out of sync - running master mode
 2 - in sync - running  mastermode
 3 - in sync - running slave mode
 4 - in sync - running master mode (wait to reach state 2)
"
    ::= {UseUnicode4MaillogNames 6}

MaxFileNameLength  OBJECT-TYPE
    SYNTAX      OCTET STRING
    MAX-ACCESS  read-write
    STATUS      current
    DESCRIPTION
"
The maximum character count that is used from the mail subject to build the file name of the logged file, if UseSubjectsAsMaillogNames is selected. This could be useful, if your mail clients having trouble to build the resend file name (right button - URL) correctly in block reports. Every non printable character will be replaced by a 4 byte string in this link.
"
    REFERENCE "Max Length of File Names"
    DEFVAL { "50" }
    ::= {Collecting 613}

syncStatMaxFileNameLength  OBJECT-TYPE
    SYNTAX      OCTET STRING
    MAX-ACCESS  read-only
    STATUS      current
    DESCRIPTION
"
synchronization status for MaxFileNameLength
-1 - MaxFileNameLength could not be synchronized
 0 - synchronization not configured
 1 - out of sync - running master mode
 2 - in sync - running  mastermode
 3 - in sync - running slave mode
 4 - in sync - running master mode (wait to reach state 2)
"
    ::= {MaxFileNameLength 5}

syncStatStrMaxFileNameLength  OBJECT-TYPE
    SYNTAX      OCTET STRING
    MAX-ACCESS  read-only
    STATUS      current
    DESCRIPTION
"
synchronization status line from file assp_sync.cfg for MaxFileNameLength
 0 - synchronization not configured
 1 - out of sync - running master mode
 2 - in sync - running  mastermode
 3 - in sync - running slave mode
 4 - in sync - running master mode (wait to reach state 2)
"
    ::= {MaxFileNameLength 6}

MaintBayesCollection  OBJECT-TYPE
    SYNTAX      OCTET STRING
    MAX-ACCESS  read-write
    STATUS      current
    DESCRIPTION
"
Set this to on, if you want ASSP to run a maintenance tasks on the bayesian collection folders ( spamlog , notspamlog , correctedspam , correctednotspam ). ASSP will delete the oldest files until the number of files per folder reaches MaxFiles. If you want ASSP to delete files because of their age instead of the number of files ( MaxFiles ), setup MaxBayesFileAge and/or MaxCorrectedDays to your needs.
  MaintBayesCollection is useful, if UseSubjectsAsMaillogNames is set to on and doMove2Num is set to off, because in this case the number of files in every collection folder will grow infinite. If set to On, the rebuildspamdb task will also do the cleanup.
"
    REFERENCE "Maintenance for Bayesian Collection"
    DEFVAL { "1" }
    ::= {Collecting 614}

syncStatMaintBayesCollection  OBJECT-TYPE
    SYNTAX      OCTET STRING
    MAX-ACCESS  read-only
    STATUS      current
    DESCRIPTION
"
synchronization status for MaintBayesCollection
-1 - MaintBayesCollection could not be synchronized
 0 - synchronization not configured
 1 - out of sync - running master mode
 2 - in sync - running  mastermode
 3 - in sync - running slave mode
 4 - in sync - running master mode (wait to reach state 2)
"
    ::= {MaintBayesCollection 5}

syncStatStrMaintBayesCollection  OBJECT-TYPE
    SYNTAX      OCTET STRING
    MAX-ACCESS  read-only
    STATUS      current
    DESCRIPTION
"
synchronization status line from file assp_sync.cfg for MaintBayesCollection
 0 - synchronization not configured
 1 - out of sync - running master mode
 2 - in sync - running  mastermode
 3 - in sync - running slave mode
 4 - in sync - running master mode (wait to reach state 2)
"
    ::= {MaintBayesCollection 6}

MaxBayesFileAge  OBJECT-TYPE
    SYNTAX      OCTET STRING
    MAX-ACCESS  read-write
    STATUS      current
    DESCRIPTION
"
The maximum file age in days of every file in every bayesian collection folder ( spamlog , notspamlog ). If MaintBayesCollection is set to on and a file is older than this number in days, the file will be deleted. Default is 31. A value of 0 disables this feature and no file will be deleted because of its age. To use different values for spamlog and notspamlog, define two space separated values - the first for spamlog and the second for notspamlog, like '30 60'. The rebuildspamdb task will ignore files older than this days (if not zero).
  It is not recommended to enable this option, if you use the bayesian engine of ASSP and doMove2Num is set to ON.  A better solution in this case is, to have MaintBayesCollection take care of deletions (by date) and change this setting to 0.
"
    REFERENCE "Max Age of Bayes Files"
    DEFVAL { "31" }
    ::= {Collecting 615}

syncStatMaxBayesFileAge  OBJECT-TYPE
    SYNTAX      OCTET STRING
    MAX-ACCESS  read-only
    STATUS      current
    DESCRIPTION
"
synchronization status for MaxBayesFileAge
-1 - MaxBayesFileAge could not be synchronized
 0 - synchronization not configured
 1 - out of sync - running master mode
 2 - in sync - running  mastermode
 3 - in sync - running slave mode
 4 - in sync - running master mode (wait to reach state 2)
"
    ::= {MaxBayesFileAge 5}

syncStatStrMaxBayesFileAge  OBJECT-TYPE
    SYNTAX      OCTET STRING
    MAX-ACCESS  read-only
    STATUS      current
    DESCRIPTION
"
synchronization status line from file assp_sync.cfg for MaxBayesFileAge
 0 - synchronization not configured
 1 - out of sync - running master mode
 2 - in sync - running  mastermode
 3 - in sync - running slave mode
 4 - in sync - running master mode (wait to reach state 2)
"
    ::= {MaxBayesFileAge 6}

MaxNoBayesFileAge  OBJECT-TYPE
    SYNTAX      OCTET STRING
    MAX-ACCESS  read-write
    STATUS      current
    DESCRIPTION
"
The maximum file age in days of every file in every non bayesian collection folder ( incomingOkMail , discarded , viruslog ). If defined and a file is older than this number in days, the file will be deleted. Default is 31. A value of 0 disables this feature and no file will be deleted because of its age. To use different values for incomingOkMail and discarded and viruslog, define three space separated values - the first for incomingOkMail and the second for discarded and the third for viruslog, like '31 45 60'
"
    REFERENCE "Max Age of non Bayes Files"
    DEFVAL { "31" }
    ::= {Collecting 616}

syncStatMaxNoBayesFileAge  OBJECT-TYPE
    SYNTAX      OCTET STRING
    MAX-ACCESS  read-only
    STATUS      current
    DESCRIPTION
"
synchronization status for MaxNoBayesFileAge
-1 - MaxNoBayesFileAge could not be synchronized
 0 - synchronization not configured
 1 - out of sync - running master mode
 2 - in sync - running  mastermode
 3 - in sync - running slave mode
 4 - in sync - running master mode (wait to reach state 2)
"
    ::= {MaxNoBayesFileAge 5}

syncStatStrMaxNoBayesFileAge  OBJECT-TYPE
    SYNTAX      OCTET STRING
    MAX-ACCESS  read-only
    STATUS      current
    DESCRIPTION
"
synchronization status line from file assp_sync.cfg for MaxNoBayesFileAge
 0 - synchronization not configured
 1 - out of sync - running master mode
 2 - in sync - running  mastermode
 3 - in sync - running slave mode
 4 - in sync - running master mode (wait to reach state 2)
"
    ::= {MaxNoBayesFileAge 6}

MaxFileAgeSchedule  OBJECT-TYPE
    SYNTAX      OCTET STRING
    MAX-ACCESS  read-write
    STATUS      current
    DESCRIPTION
"
Runtime hour for deleting old collected files (bayes and non bayes). Set a number between 0 and 23. 0 means midnight, 1 is default. If empty a cleanup will not be scheduled. This could be fine, if a rebuildspamdb is scheduled, which will also do the cleanup based on the settings of MaintBayesCollection , MaxBayesFileAge and MaxCorrectedDays - but it will not maintain incomingOkMail , discarded and viruslog based on MaxNoBayesFileAge !
"
    REFERENCE "Runtime for MaintBayesCollection and MaxNoBayesFileAge <sup>s</sup>"
    DEFVAL { "1" }
    ::= {Collecting 617}

syncStatMaxFileAgeSchedule  OBJECT-TYPE
    SYNTAX      OCTET STRING
    MAX-ACCESS  read-only
    STATUS      current
    DESCRIPTION
"
synchronization status for MaxFileAgeSchedule
-1 - MaxFileAgeSchedule could not be synchronized
 0 - synchronization not configured
 1 - out of sync - running master mode
 2 - in sync - running  mastermode
 3 - in sync - running slave mode
 4 - in sync - running master mode (wait to reach state 2)
"
    ::= {MaxFileAgeSchedule 5}

syncStatStrMaxFileAgeSchedule  OBJECT-TYPE
    SYNTAX      OCTET STRING
    MAX-ACCESS  read-only
    STATUS      current
    DESCRIPTION
"
synchronization status line from file assp_sync.cfg for MaxFileAgeSchedule
 0 - synchronization not configured
 1 - out of sync - running master mode
 2 - in sync - running  mastermode
 3 - in sync - running slave mode
 4 - in sync - running master mode (wait to reach state 2)
"
    ::= {MaxFileAgeSchedule 6}

MaxBytes  OBJECT-TYPE
    SYNTAX      OCTET STRING
    MAX-ACCESS  read-write
    STATUS      current
    DESCRIPTION
"
How many bytes of the message body will ASSP look at - the message header is always included in all checks? Mails stored in the collecting folders will be truncated to this size. The average of Ham messages (message body) is 6K, the average of Spam messages is 3K. Usually the spam folder will be filled quicker than the notspam folder, therefore set this value to 4000 to get more wordpairs per Ham Message. When both folders are close to the maxfiles limit, reduce it to 3000.
"
    REFERENCE "Max Bytes"
    DEFVAL { "4000" }
    ::= {Collecting 618}

syncStatMaxBytes  OBJECT-TYPE
    SYNTAX      OCTET STRING
    MAX-ACCESS  read-only
    STATUS      current
    DESCRIPTION
"
synchronization status for MaxBytes
-1 - MaxBytes could not be synchronized
 0 - synchronization not configured
 1 - out of sync - running master mode
 2 - in sync - running  mastermode
 3 - in sync - running slave mode
 4 - in sync - running master mode (wait to reach state 2)
"
    ::= {MaxBytes 5}

syncStatStrMaxBytes  OBJECT-TYPE
    SYNTAX      OCTET STRING
    MAX-ACCESS  read-only
    STATUS      current
    DESCRIPTION
"
synchronization status line from file assp_sync.cfg for MaxBytes
 0 - synchronization not configured
 1 - out of sync - running master mode
 2 - in sync - running  mastermode
 3 - in sync - running slave mode
 4 - in sync - running master mode (wait to reach state 2)
"
    ::= {MaxBytes 6}

StoreCompleteMail  OBJECT-TYPE
    SYNTAX      OCTET STRING
    MAX-ACCESS  read-write
    STATUS      current
    DESCRIPTION
"
If set, ASSP will look at MaxBytes, but if possible it will store the complete mail up to the number of bytes configured. This could be useful for example, if you want resend blocked messages. Be carefull using this option, your disk could be filled up very fast!
"
    REFERENCE "Store the Complete Mail"
    DEFVAL { "999999999" }
    ::= {Collecting 619}

syncStatStoreCompleteMail  OBJECT-TYPE
    SYNTAX      OCTET STRING
    MAX-ACCESS  read-only
    STATUS      current
    DESCRIPTION
"
synchronization status for StoreCompleteMail
-1 - StoreCompleteMail could not be synchronized
 0 - synchronization not configured
 1 - out of sync - running master mode
 2 - in sync - running  mastermode
 3 - in sync - running slave mode
 4 - in sync - running master mode (wait to reach state 2)
"
    ::= {StoreCompleteMail 5}

syncStatStrStoreCompleteMail  OBJECT-TYPE
    SYNTAX      OCTET STRING
    MAX-ACCESS  read-only
    STATUS      current
    DESCRIPTION
"
synchronization status line from file assp_sync.cfg for StoreCompleteMail
 0 - synchronization not configured
 1 - out of sync - running master mode
 2 - in sync - running  mastermode
 3 - in sync - running slave mode
 4 - in sync - running master mode (wait to reach state 2)
"
    ::= {StoreCompleteMail 6}

MaxBytesReports  OBJECT-TYPE
    SYNTAX      OCTET STRING
    MAX-ACCESS  read-write
    STATUS      current
    DESCRIPTION
"
How many bytes of an error report message will ASSP look at. For example: 10000. Set this to zero for no limit.
"
    REFERENCE "Error Max Bytes"
    DEFVAL { "10000" }
    ::= {Collecting 620}

syncStatMaxBytesReports  OBJECT-TYPE
    SYNTAX      OCTET STRING
    MAX-ACCESS  read-only
    STATUS      current
    DESCRIPTION
"
synchronization status for MaxBytesReports
-1 - MaxBytesReports could not be synchronized
 0 - synchronization not configured
 1 - out of sync - running master mode
 2 - in sync - running  mastermode
 3 - in sync - running slave mode
 4 - in sync - running master mode (wait to reach state 2)
"
    ::= {MaxBytesReports 5}

syncStatStrMaxBytesReports  OBJECT-TYPE
    SYNTAX      OCTET STRING
    MAX-ACCESS  read-only
    STATUS      current
    DESCRIPTION
"
synchronization status line from file assp_sync.cfg for MaxBytesReports
 0 - synchronization not configured
 1 - out of sync - running master mode
 2 - in sync - running  mastermode
 3 - in sync - running slave mode
 4 - in sync - running master mode (wait to reach state 2)
"
    ::= {MaxBytesReports 6}

NonSpamLog  OBJECT-TYPE
    SYNTAX      OCTET STRING
    MAX-ACCESS  read-write
    STATUS      current
    DESCRIPTION
"
Where to store whitelisted/local non spam messages. Default: notspam folder ( notspamlog ).
"
    REFERENCE "Non Spam"
    DEFVAL { "2" }
    ::= {Collecting 621}

syncStatNonSpamLog  OBJECT-TYPE
    SYNTAX      OCTET STRING
    MAX-ACCESS  read-only
    STATUS      current
    DESCRIPTION
"
synchronization status for NonSpamLog
-1 - NonSpamLog could not be synchronized
 0 - synchronization not configured
 1 - out of sync - running master mode
 2 - in sync - running  mastermode
 3 - in sync - running slave mode
 4 - in sync - running master mode (wait to reach state 2)
"
    ::= {NonSpamLog 5}

syncStatStrNonSpamLog  OBJECT-TYPE
    SYNTAX      OCTET STRING
    MAX-ACCESS  read-only
    STATUS      current
    DESCRIPTION
"
synchronization status line from file assp_sync.cfg for NonSpamLog
 0 - synchronization not configured
 1 - out of sync - running master mode
 2 - in sync - running  mastermode
 3 - in sync - running slave mode
 4 - in sync - running master mode (wait to reach state 2)
"
    ::= {NonSpamLog 6}

baysNonSpamLog  OBJECT-TYPE
    SYNTAX      OCTET STRING
    MAX-ACCESS  read-write
    STATUS      current
    DESCRIPTION
"
Where to store non spam (message ok) messages. These are messages which are considered as HAM, but should not stored in the standard HAM folder because of our policy to use only confirmed HAM messages (whitelisted or local) for SpamDB. Set incomingOkMail accordingly if you choose 'okmail folder'. Default: no collection
"
    REFERENCE "OK Mail"
    DEFVAL { "0" }
    ::= {Collecting 622}

syncStatbaysNonSpamLog  OBJECT-TYPE
    SYNTAX      OCTET STRING
    MAX-ACCESS  read-only
    STATUS      current
    DESCRIPTION
"
synchronization status for baysNonSpamLog
-1 - baysNonSpamLog could not be synchronized
 0 - synchronization not configured
 1 - out of sync - running master mode
 2 - in sync - running  mastermode
 3 - in sync - running slave mode
 4 - in sync - running master mode (wait to reach state 2)
"
    ::= {baysNonSpamLog 5}

syncStatStrbaysNonSpamLog  OBJECT-TYPE
    SYNTAX      OCTET STRING
    MAX-ACCESS  read-only
    STATUS      current
    DESCRIPTION
"
synchronization status line from file assp_sync.cfg for baysNonSpamLog
 0 - synchronization not configured
 1 - out of sync - running master mode
 2 - in sync - running  mastermode
 3 - in sync - running slave mode
 4 - in sync - running master mode (wait to reach state 2)
"
    ::= {baysNonSpamLog 6}

SpamLog  OBJECT-TYPE
    SYNTAX      OCTET STRING
    MAX-ACCESS  read-write
    STATUS      current
    DESCRIPTION
"
Set this to 'disabled' if you do not want to store any Spam regardless of settings in. Default: enabled (store in folder spamlog ).
"
    REFERENCE "Store Spam"
    DEFVAL { "1" }
    ::= {Collecting 623}

syncStatSpamLog  OBJECT-TYPE
    SYNTAX      OCTET STRING
    MAX-ACCESS  read-only
    STATUS      current
    DESCRIPTION
"
synchronization status for SpamLog
-1 - SpamLog could not be synchronized
 0 - synchronization not configured
 1 - out of sync - running master mode
 2 - in sync - running  mastermode
 3 - in sync - running slave mode
 4 - in sync - running master mode (wait to reach state 2)
"
    ::= {SpamLog 5}

syncStatStrSpamLog  OBJECT-TYPE
    SYNTAX      OCTET STRING
    MAX-ACCESS  read-only
    STATUS      current
    DESCRIPTION
"
synchronization status line from file assp_sync.cfg for SpamLog
 0 - synchronization not configured
 1 - out of sync - running master mode
 2 - in sync - running  mastermode
 3 - in sync - running slave mode
 4 - in sync - running master mode (wait to reach state 2)
"
    ::= {SpamLog 6}

noProcessingLog  OBJECT-TYPE
    SYNTAX      OCTET STRING
    MAX-ACCESS  read-write
    STATUS      current
    DESCRIPTION
"
Where to store noprocessing OK mails.
"
    REFERENCE "NoProcessing OK Mails"
    DEFVAL { "0" }
    ::= {Collecting 624}

syncStatnoProcessingLog  OBJECT-TYPE
    SYNTAX      OCTET STRING
    MAX-ACCESS  read-only
    STATUS      current
    DESCRIPTION
"
synchronization status for noProcessingLog
-1 - noProcessingLog could not be synchronized
 0 - synchronization not configured
 1 - out of sync - running master mode
 2 - in sync - running  mastermode
 3 - in sync - running slave mode
 4 - in sync - running master mode (wait to reach state 2)
"
    ::= {noProcessingLog 5}

syncStatStrnoProcessingLog  OBJECT-TYPE
    SYNTAX      OCTET STRING
    MAX-ACCESS  read-only
    STATUS      current
    DESCRIPTION
"
synchronization status line from file assp_sync.cfg for noProcessingLog
 0 - synchronization not configured
 1 - out of sync - running master mode
 2 - in sync - running  mastermode
 3 - in sync - running slave mode
 4 - in sync - running master mode (wait to reach state 2)
"
    ::= {noProcessingLog 6}

npAttachLog  OBJECT-TYPE
    SYNTAX      OCTET STRING
    MAX-ACCESS  read-write
    STATUS      current
    DESCRIPTION
"
Where to store noprocessing rejected mail+attachments. Recommended: discard folder ( discarded ) &amp; sendAllSpam
"
    REFERENCE "NoProcessing rejected Attachments"
    DEFVAL { "7" }
    ::= {Collecting 625}

syncStatnpAttachLog  OBJECT-TYPE
    SYNTAX      OCTET STRING
    MAX-ACCESS  read-only
    STATUS      current
    DESCRIPTION
"
synchronization status for npAttachLog
-1 - npAttachLog could not be synchronized
 0 - synchronization not configured
 1 - out of sync - running master mode
 2 - in sync - running  mastermode
 3 - in sync - running slave mode
 4 - in sync - running master mode (wait to reach state 2)
"
    ::= {npAttachLog 5}

syncStatStrnpAttachLog  OBJECT-TYPE
    SYNTAX      OCTET STRING
    MAX-ACCESS  read-only
    STATUS      current
    DESCRIPTION
"
synchronization status line from file assp_sync.cfg for npAttachLog
 0 - synchronization not configured
 1 - out of sync - running master mode
 2 - in sync - running  mastermode
 3 - in sync - running slave mode
 4 - in sync - running master mode (wait to reach state 2)
"
    ::= {npAttachLog 6}

wlAttachLog  OBJECT-TYPE
    SYNTAX      OCTET STRING
    MAX-ACCESS  read-write
    STATUS      current
    DESCRIPTION
"
Where to store whitelisted rejected mail+attachments. Recommended: discard folder ( discarded ) &amp; sendAllSpam
"
    REFERENCE "Whitelisted rejected Attachments"
    DEFVAL { "7" }
    ::= {Collecting 626}

syncStatwlAttachLog  OBJECT-TYPE
    SYNTAX      OCTET STRING
    MAX-ACCESS  read-only
    STATUS      current
    DESCRIPTION
"
synchronization status for wlAttachLog
-1 - wlAttachLog could not be synchronized
 0 - synchronization not configured
 1 - out of sync - running master mode
 2 - in sync - running  mastermode
 3 - in sync - running slave mode
 4 - in sync - running master mode (wait to reach state 2)
"
    ::= {wlAttachLog 5}

syncStatStrwlAttachLog  OBJECT-TYPE
    SYNTAX      OCTET STRING
    MAX-ACCESS  read-only
    STATUS      current
    DESCRIPTION
"
synchronization status line from file assp_sync.cfg for wlAttachLog
 0 - synchronization not configured
 1 - out of sync - running master mode
 2 - in sync - running  mastermode
 3 - in sync - running slave mode
 4 - in sync - running master mode (wait to reach state 2)
"
    ::= {wlAttachLog 6}

extAttachLog  OBJECT-TYPE
    SYNTAX      OCTET STRING
    MAX-ACCESS  read-write
    STATUS      current
    DESCRIPTION
"
Where to store external rejected mail+attachments. Recommended: discard folder ( discarded ) &amp; sendAllSpam
"
    REFERENCE "External rejected Attachments"
    DEFVAL { "7" }
    ::= {Collecting 627}

syncStatextAttachLog  OBJECT-TYPE
    SYNTAX      OCTET STRING
    MAX-ACCESS  read-only
    STATUS      current
    DESCRIPTION
"
synchronization status for extAttachLog
-1 - extAttachLog could not be synchronized
 0 - synchronization not configured
 1 - out of sync - running master mode
 2 - in sync - running  mastermode
 3 - in sync - running slave mode
 4 - in sync - running master mode (wait to reach state 2)
"
    ::= {extAttachLog 5}

syncStatStrextAttachLog  OBJECT-TYPE
    SYNTAX      OCTET STRING
    MAX-ACCESS  read-only
    STATUS      current
    DESCRIPTION
"
synchronization status line from file assp_sync.cfg for extAttachLog
 0 - synchronization not configured
 1 - out of sync - running master mode
 2 - in sync - running  mastermode
 3 - in sync - running slave mode
 4 - in sync - running master mode (wait to reach state 2)
"
    ::= {extAttachLog 6}

SpamVirusLog  OBJECT-TYPE
    SYNTAX      OCTET STRING
    MAX-ACCESS  read-write
    STATUS      current
    DESCRIPTION
"
Where to store virus infected messages. Recommended: quarantine ( quarantine )
"
    REFERENCE "Virus Infected"
    DEFVAL { "5" }
    ::= {Collecting 628}

syncStatSpamVirusLog  OBJECT-TYPE
    SYNTAX      OCTET STRING
    MAX-ACCESS  read-only
    STATUS      current
    DESCRIPTION
"
synchronization status for SpamVirusLog
-1 - SpamVirusLog could not be synchronized
 0 - synchronization not configured
 1 - out of sync - running master mode
 2 - in sync - running  mastermode
 3 - in sync - running slave mode
 4 - in sync - running master mode (wait to reach state 2)
"
    ::= {SpamVirusLog 5}

syncStatStrSpamVirusLog  OBJECT-TYPE
    SYNTAX      OCTET STRING
    MAX-ACCESS  read-only
    STATUS      current
    DESCRIPTION
"
synchronization status line from file assp_sync.cfg for SpamVirusLog
 0 - synchronization not configured
 1 - out of sync - running master mode
 2 - in sync - running  mastermode
 3 - in sync - running slave mode
 4 - in sync - running master mode (wait to reach state 2)
"
    ::= {SpamVirusLog 6}

spamBombLog  OBJECT-TYPE
    SYNTAX      OCTET STRING
    MAX-ACCESS  read-write
    STATUS      current
    DESCRIPTION
"
Where to store spam bombs. Recommended: discard folder ( discarded )
"
    REFERENCE "Spam Bombs"
    DEFVAL { "6" }
    ::= {Collecting 629}

syncStatspamBombLog  OBJECT-TYPE
    SYNTAX      OCTET STRING
    MAX-ACCESS  read-only
    STATUS      current
    DESCRIPTION
"
synchronization status for spamBombLog
-1 - spamBombLog could not be synchronized
 0 - synchronization not configured
 1 - out of sync - running master mode
 2 - in sync - running  mastermode
 3 - in sync - running slave mode
 4 - in sync - running master mode (wait to reach state 2)
"
    ::= {spamBombLog 5}

syncStatStrspamBombLog  OBJECT-TYPE
    SYNTAX      OCTET STRING
    MAX-ACCESS  read-only
    STATUS      current
    DESCRIPTION
"
synchronization status line from file assp_sync.cfg for spamBombLog
 0 - synchronization not configured
 1 - out of sync - running master mode
 2 - in sync - running  mastermode
 3 - in sync - running slave mode
 4 - in sync - running master mode (wait to reach state 2)
"
    ::= {spamBombLog 6}

scriptLog  OBJECT-TYPE
    SYNTAX      OCTET STRING
    MAX-ACCESS  read-write
    STATUS      current
    DESCRIPTION
"
Where to store scripted messages. Recommended: spam folder   ( spamlog )  &amp; sendAllSpam
"
    REFERENCE "Scripts"
    DEFVAL { "3" }
    ::= {Collecting 630}

syncStatscriptLog  OBJECT-TYPE
    SYNTAX      OCTET STRING
    MAX-ACCESS  read-only
    STATUS      current
    DESCRIPTION
"
synchronization status for scriptLog
-1 - scriptLog could not be synchronized
 0 - synchronization not configured
 1 - out of sync - running master mode
 2 - in sync - running  mastermode
 3 - in sync - running slave mode
 4 - in sync - running master mode (wait to reach state 2)
"
    ::= {scriptLog 5}

syncStatStrscriptLog  OBJECT-TYPE
    SYNTAX      OCTET STRING
    MAX-ACCESS  read-only
    STATUS      current
    DESCRIPTION
"
synchronization status line from file assp_sync.cfg for scriptLog
 0 - synchronization not configured
 1 - out of sync - running master mode
 2 - in sync - running  mastermode
 3 - in sync - running slave mode
 4 - in sync - running master mode (wait to reach state 2)
"
    ::= {scriptLog 6}

blDomainLog  OBJECT-TYPE
    SYNTAX      OCTET STRING
    MAX-ACCESS  read-write
    STATUS      current
    DESCRIPTION
"
Where to store blacklisted domain messages. Recommended: spam folder ( spamlog ) &amp; sendAllSpam
"
    REFERENCE "Blacklisted Domains"
    DEFVAL { "3" }
    ::= {Collecting 631}

syncStatblDomainLog  OBJECT-TYPE
    SYNTAX      OCTET STRING
    MAX-ACCESS  read-only
    STATUS      current
    DESCRIPTION
"
synchronization status for blDomainLog
-1 - blDomainLog could not be synchronized
 0 - synchronization not configured
 1 - out of sync - running master mode
 2 - in sync - running  mastermode
 3 - in sync - running slave mode
 4 - in sync - running master mode (wait to reach state 2)
"
    ::= {blDomainLog 5}

syncStatStrblDomainLog  OBJECT-TYPE
    SYNTAX      OCTET STRING
    MAX-ACCESS  read-only
    STATUS      current
    DESCRIPTION
"
synchronization status line from file assp_sync.cfg for blDomainLog
 0 - synchronization not configured
 1 - out of sync - running master mode
 2 - in sync - running  mastermode
 3 - in sync - running slave mode
 4 - in sync - running master mode (wait to reach state 2)
"
    ::= {blDomainLog 6}

spamHeloLog  OBJECT-TYPE
    SYNTAX      OCTET STRING
    MAX-ACCESS  read-write
    STATUS      current
    DESCRIPTION
"
Where to store spam helo messages. Recommended: discard folder ( discarded ) &amp; sendAllSpam
"
    REFERENCE "Blacklisted Helos"
    DEFVAL { "7" }
    ::= {Collecting 632}

syncStatspamHeloLog  OBJECT-TYPE
    SYNTAX      OCTET STRING
    MAX-ACCESS  read-only
    STATUS      current
    DESCRIPTION
"
synchronization status for spamHeloLog
-1 - spamHeloLog could not be synchronized
 0 - synchronization not configured
 1 - out of sync - running master mode
 2 - in sync - running  mastermode
 3 - in sync - running slave mode
 4 - in sync - running master mode (wait to reach state 2)
"
    ::= {spamHeloLog 5}

syncStatStrspamHeloLog  OBJECT-TYPE
    SYNTAX      OCTET STRING
    MAX-ACCESS  read-only
    STATUS      current
    DESCRIPTION
"
synchronization status line from file assp_sync.cfg for spamHeloLog
 0 - synchronization not configured
 1 - out of sync - running master mode
 2 - in sync - running  mastermode
 3 - in sync - running slave mode
 4 - in sync - running master mode (wait to reach state 2)
"
    ::= {spamHeloLog 6}

forgedHeloLog  OBJECT-TYPE
    SYNTAX      OCTET STRING
    MAX-ACCESS  read-write
    STATUS      current
    DESCRIPTION
"
Where to store forged helo messages. Recommended: no collection
"
    REFERENCE "Forged Helos"
    DEFVAL { "0" }
    ::= {Collecting 633}

syncStatforgedHeloLog  OBJECT-TYPE
    SYNTAX      OCTET STRING
    MAX-ACCESS  read-only
    STATUS      current
    DESCRIPTION
"
synchronization status for forgedHeloLog
-1 - forgedHeloLog could not be synchronized
 0 - synchronization not configured
 1 - out of sync - running master mode
 2 - in sync - running  mastermode
 3 - in sync - running slave mode
 4 - in sync - running master mode (wait to reach state 2)
"
    ::= {forgedHeloLog 5}

syncStatStrforgedHeloLog  OBJECT-TYPE
    SYNTAX      OCTET STRING
    MAX-ACCESS  read-only
    STATUS      current
    DESCRIPTION
"
synchronization status line from file assp_sync.cfg for forgedHeloLog
 0 - synchronization not configured
 1 - out of sync - running master mode
 2 - in sync - running  mastermode
 3 - in sync - running slave mode
 4 - in sync - running master mode (wait to reach state 2)
"
    ::= {forgedHeloLog 6}

invalidHeloLog  OBJECT-TYPE
    SYNTAX      OCTET STRING
    MAX-ACCESS  read-write
    STATUS      current
    DESCRIPTION
"
Where to store invalid helo messages. Recommended: discard folder ( discarded )
"
    REFERENCE "Invalid Helos"
    DEFVAL { "6" }
    ::= {Collecting 634}

syncStatinvalidHeloLog  OBJECT-TYPE
    SYNTAX      OCTET STRING
    MAX-ACCESS  read-only
    STATUS      current
    DESCRIPTION
"
synchronization status for invalidHeloLog
-1 - invalidHeloLog could not be synchronized
 0 - synchronization not configured
 1 - out of sync - running master mode
 2 - in sync - running  mastermode
 3 - in sync - running slave mode
 4 - in sync - running master mode (wait to reach state 2)
"
    ::= {invalidHeloLog 5}

syncStatStrinvalidHeloLog  OBJECT-TYPE
    SYNTAX      OCTET STRING
    MAX-ACCESS  read-only
    STATUS      current
    DESCRIPTION
"
synchronization status line from file assp_sync.cfg for invalidHeloLog
 0 - synchronization not configured
 1 - out of sync - running master mode
 2 - in sync - running  mastermode
 3 - in sync - running slave mode
 4 - in sync - running master mode (wait to reach state 2)
"
    ::= {invalidHeloLog 6}

spamBucketLog  OBJECT-TYPE
    SYNTAX      OCTET STRING
    MAX-ACCESS  read-write
    STATUS      current
    DESCRIPTION
"
Where to store mails addressed to Spam Collect Addresses. Recommended: spam folder ( spamlog )
"
    REFERENCE "Spam Collect Addresses"
    DEFVAL { "1" }
    ::= {Collecting 635}

syncStatspamBucketLog  OBJECT-TYPE
    SYNTAX      OCTET STRING
    MAX-ACCESS  read-only
    STATUS      current
    DESCRIPTION
"
synchronization status for spamBucketLog
-1 - spamBucketLog could not be synchronized
 0 - synchronization not configured
 1 - out of sync - running master mode
 2 - in sync - running  mastermode
 3 - in sync - running slave mode
 4 - in sync - running master mode (wait to reach state 2)
"
    ::= {spamBucketLog 5}

syncStatStrspamBucketLog  OBJECT-TYPE
    SYNTAX      OCTET STRING
    MAX-ACCESS  read-only
    STATUS      current
    DESCRIPTION
"
synchronization status line from file assp_sync.cfg for spamBucketLog
 0 - synchronization not configured
 1 - out of sync - running master mode
 2 - in sync - running  mastermode
 3 - in sync - running slave mode
 4 - in sync - running master mode (wait to reach state 2)
"
    ::= {spamBucketLog 6}

baysSpamLog  OBJECT-TYPE
    SYNTAX      OCTET STRING
    MAX-ACCESS  read-write
    STATUS      current
    DESCRIPTION
"
Where to store Bayesian spam messages. Recommended: discard folder ( discarded ) &amp; sendAllSpam
"
    REFERENCE "Bayesian Spams"
    DEFVAL { "7" }
    ::= {Collecting 636}

syncStatbaysSpamLog  OBJECT-TYPE
    SYNTAX      OCTET STRING
    MAX-ACCESS  read-only
    STATUS      current
    DESCRIPTION
"
synchronization status for baysSpamLog
-1 - baysSpamLog could not be synchronized
 0 - synchronization not configured
 1 - out of sync - running master mode
 2 - in sync - running  mastermode
 3 - in sync - running slave mode
 4 - in sync - running master mode (wait to reach state 2)
"
    ::= {baysSpamLog 5}

syncStatStrbaysSpamLog  OBJECT-TYPE
    SYNTAX      OCTET STRING
    MAX-ACCESS  read-only
    STATUS      current
    DESCRIPTION
"
synchronization status line from file assp_sync.cfg for baysSpamLog
 0 - synchronization not configured
 1 - out of sync - running master mode
 2 - in sync - running  mastermode
 3 - in sync - running slave mode
 4 - in sync - running master mode (wait to reach state 2)
"
    ::= {baysSpamLog 6}

SPFFailLog  OBJECT-TYPE
    SYNTAX      OCTET STRING
    MAX-ACCESS  read-write
    STATUS      current
    DESCRIPTION
"
Where to store SPF Failure spam messages. Recommended: spam folder ( spamlog ) &amp; sendAllSpam
"
    REFERENCE "SPF Failures"
    DEFVAL { "3" }
    ::= {Collecting 637}

syncStatSPFFailLog  OBJECT-TYPE
    SYNTAX      OCTET STRING
    MAX-ACCESS  read-only
    STATUS      current
    DESCRIPTION
"
synchronization status for SPFFailLog
-1 - SPFFailLog could not be synchronized
 0 - synchronization not configured
 1 - out of sync - running master mode
 2 - in sync - running  mastermode
 3 - in sync - running slave mode
 4 - in sync - running master mode (wait to reach state 2)
"
    ::= {SPFFailLog 5}

syncStatStrSPFFailLog  OBJECT-TYPE
    SYNTAX      OCTET STRING
    MAX-ACCESS  read-only
    STATUS      current
    DESCRIPTION
"
synchronization status line from file assp_sync.cfg for SPFFailLog
 0 - synchronization not configured
 1 - out of sync - running master mode
 2 - in sync - running  mastermode
 3 - in sync - running slave mode
 4 - in sync - running master mode (wait to reach state 2)
"
    ::= {SPFFailLog 6}

RBLFailLog  OBJECT-TYPE
    SYNTAX      OCTET STRING
    MAX-ACCESS  read-write
    STATUS      current
    DESCRIPTION
"
Where to store DNSBL Failure spam messages. Recommended: spam folder ( spamlog ) &amp; sendAllSpam
"
    REFERENCE "DNSBL Failures"
    DEFVAL { "3" }
    ::= {Collecting 638}

syncStatRBLFailLog  OBJECT-TYPE
    SYNTAX      OCTET STRING
    MAX-ACCESS  read-only
    STATUS      current
    DESCRIPTION
"
synchronization status for RBLFailLog
-1 - RBLFailLog could not be synchronized
 0 - synchronization not configured
 1 - out of sync - running master mode
 2 - in sync - running  mastermode
 3 - in sync - running slave mode
 4 - in sync - running master mode (wait to reach state 2)
"
    ::= {RBLFailLog 5}

syncStatStrRBLFailLog  OBJECT-TYPE
    SYNTAX      OCTET STRING
    MAX-ACCESS  read-only
    STATUS      current
    DESCRIPTION
"
synchronization status line from file assp_sync.cfg for RBLFailLog
 0 - synchronization not configured
 1 - out of sync - running master mode
 2 - in sync - running  mastermode
 3 - in sync - running slave mode
 4 - in sync - running master mode (wait to reach state 2)
"
    ::= {RBLFailLog 6}

URIBLFailLog  OBJECT-TYPE
    SYNTAX      OCTET STRING
    MAX-ACCESS  read-write
    STATUS      current
    DESCRIPTION
"
Where to store URIBL Failure spam messages. Recommended: spam folder ( spamlog ) &amp; sendAllSpam
"
    REFERENCE "URIBL Failures"
    DEFVAL { "3" }
    ::= {Collecting 639}

syncStatURIBLFailLog  OBJECT-TYPE
    SYNTAX      OCTET STRING
    MAX-ACCESS  read-only
    STATUS      current
    DESCRIPTION
"
synchronization status for URIBLFailLog
-1 - URIBLFailLog could not be synchronized
 0 - synchronization not configured
 1 - out of sync - running master mode
 2 - in sync - running  mastermode
 3 - in sync - running slave mode
 4 - in sync - running master mode (wait to reach state 2)
"
    ::= {URIBLFailLog 5}

syncStatStrURIBLFailLog  OBJECT-TYPE
    SYNTAX      OCTET STRING
    MAX-ACCESS  read-only
    STATUS      current
    DESCRIPTION
"
synchronization status line from file assp_sync.cfg for URIBLFailLog
 0 - synchronization not configured
 1 - out of sync - running master mode
 2 - in sync - running  mastermode
 3 - in sync - running slave mode
 4 - in sync - running master mode (wait to reach state 2)
"
    ::= {URIBLFailLog 6}

SRSFailLog  OBJECT-TYPE
    SYNTAX      OCTET STRING
    MAX-ACCESS  read-write
    STATUS      current
    DESCRIPTION
"
Where to store SRS Failure (not signed bounces) spam messages. Recommended: spam folder ( spamlog ) &amp; sendAllSpam
"
    REFERENCE "SRS Failures"
    DEFVAL { "3" }
    ::= {Collecting 640}

syncStatSRSFailLog  OBJECT-TYPE
    SYNTAX      OCTET STRING
    MAX-ACCESS  read-only
    STATUS      current
    DESCRIPTION
"
synchronization status for SRSFailLog
-1 - SRSFailLog could not be synchronized
 0 - synchronization not configured
 1 - out of sync - running master mode
 2 - in sync - running  mastermode
 3 - in sync - running slave mode
 4 - in sync - running master mode (wait to reach state 2)
"
    ::= {SRSFailLog 5}

syncStatStrSRSFailLog  OBJECT-TYPE
    SYNTAX      OCTET STRING
    MAX-ACCESS  read-only
    STATUS      current
    DESCRIPTION
"
synchronization status line from file assp_sync.cfg for SRSFailLog
 0 - synchronization not configured
 1 - out of sync - running master mode
 2 - in sync - running  mastermode
 3 - in sync - running slave mode
 4 - in sync - running master mode (wait to reach state 2)
"
    ::= {SRSFailLog 6}

spamPTRLog  OBJECT-TYPE
    SYNTAX      OCTET STRING
    MAX-ACCESS  read-write
    STATUS      current
    DESCRIPTION
"
Where to store Missing/Invalid Pointer rejected messages. Recommended: spam folder ( spamlog ) &amp; sendAllSpam
"
    REFERENCE "Missing/Invalid Pointer "
    DEFVAL { "3" }
    ::= {Collecting 641}

syncStatspamPTRLog  OBJECT-TYPE
    SYNTAX      OCTET STRING
    MAX-ACCESS  read-only
    STATUS      current
    DESCRIPTION
"
synchronization status for spamPTRLog
-1 - spamPTRLog could not be synchronized
 0 - synchronization not configured
 1 - out of sync - running master mode
 2 - in sync - running  mastermode
 3 - in sync - running slave mode
 4 - in sync - running master mode (wait to reach state 2)
"
    ::= {spamPTRLog 5}

syncStatStrspamPTRLog  OBJECT-TYPE
    SYNTAX      OCTET STRING
    MAX-ACCESS  read-only
    STATUS      current
    DESCRIPTION
"
synchronization status line from file assp_sync.cfg for spamPTRLog
 0 - synchronization not configured
 1 - out of sync - running master mode
 2 - in sync - running  mastermode
 3 - in sync - running slave mode
 4 - in sync - running master mode (wait to reach state 2)
"
    ::= {spamPTRLog 6}

spamMXALog  OBJECT-TYPE
    SYNTAX      OCTET STRING
    MAX-ACCESS  read-write
    STATUS      current
    DESCRIPTION
"
Where to store Missing MX record rejected messages. Recommended: spam folder ( spamlog ) &amp; sendAllSpam
"
    REFERENCE "Missing MX Record "
    DEFVAL { "3" }
    ::= {Collecting 642}

syncStatspamMXALog  OBJECT-TYPE
    SYNTAX      OCTET STRING
    MAX-ACCESS  read-only
    STATUS      current
    DESCRIPTION
"
synchronization status for spamMXALog
-1 - spamMXALog could not be synchronized
 0 - synchronization not configured
 1 - out of sync - running master mode
 2 - in sync - running  mastermode
 3 - in sync - running slave mode
 4 - in sync - running master mode (wait to reach state 2)
"
    ::= {spamMXALog 5}

syncStatStrspamMXALog  OBJECT-TYPE
    SYNTAX      OCTET STRING
    MAX-ACCESS  read-only
    STATUS      current
    DESCRIPTION
"
synchronization status line from file assp_sync.cfg for spamMXALog
 0 - synchronization not configured
 1 - out of sync - running master mode
 2 - in sync - running  mastermode
 3 - in sync - running slave mode
 4 - in sync - running master mode (wait to reach state 2)
"
    ::= {spamMXALog 6}

spamISLog  OBJECT-TYPE
    SYNTAX      OCTET STRING
    MAX-ACCESS  read-write
    STATUS      current
    DESCRIPTION
"
Where to store messages from a local domain with an unknown userpart. Recommended: no collection
"
    REFERENCE "Invalid Local Sender"
    DEFVAL { "0" }
    ::= {Collecting 643}

syncStatspamISLog  OBJECT-TYPE
    SYNTAX      OCTET STRING
    MAX-ACCESS  read-only
    STATUS      current
    DESCRIPTION
"
synchronization status for spamISLog
-1 - spamISLog could not be synchronized
 0 - synchronization not configured
 1 - out of sync - running master mode
 2 - in sync - running  mastermode
 3 - in sync - running slave mode
 4 - in sync - running master mode (wait to reach state 2)
"
    ::= {spamISLog 5}

syncStatStrspamISLog  OBJECT-TYPE
    SYNTAX      OCTET STRING
    MAX-ACCESS  read-only
    STATUS      current
    DESCRIPTION
"
synchronization status line from file assp_sync.cfg for spamISLog
 0 - synchronization not configured
 1 - out of sync - running master mode
 2 - in sync - running  mastermode
 3 - in sync - running slave mode
 4 - in sync - running master mode (wait to reach state 2)
"
    ::= {spamISLog 6}

spamSBLog  OBJECT-TYPE
    SYNTAX      OCTET STRING
    MAX-ACCESS  read-write
    STATUS      current
    DESCRIPTION
"
Where to store messages from a blocked country. Recommended: spam folder ( spamlog ) &amp; sendAllSpam
"
    REFERENCE "Blocked Country"
    DEFVAL { "3" }
    ::= {Collecting 644}

syncStatspamSBLog  OBJECT-TYPE
    SYNTAX      OCTET STRING
    MAX-ACCESS  read-only
    STATUS      current
    DESCRIPTION
"
synchronization status for spamSBLog
-1 - spamSBLog could not be synchronized
 0 - synchronization not configured
 1 - out of sync - running master mode
 2 - in sync - running  mastermode
 3 - in sync - running slave mode
 4 - in sync - running master mode (wait to reach state 2)
"
    ::= {spamSBLog 5}

syncStatStrspamSBLog  OBJECT-TYPE
    SYNTAX      OCTET STRING
    MAX-ACCESS  read-only
    STATUS      current
    DESCRIPTION
"
synchronization status line from file assp_sync.cfg for spamSBLog
 0 - synchronization not configured
 1 - out of sync - running master mode
 2 - in sync - running  mastermode
 3 - in sync - running slave mode
 4 - in sync - running master mode (wait to reach state 2)
"
    ::= {spamSBLog 6}

spamMSLog  OBJECT-TYPE
    SYNTAX      OCTET STRING
    MAX-ACCESS  read-write
    STATUS      current
    DESCRIPTION
"
Where to store Message Scoring Limit rejected messages. Recommended: spam folder ( spamlog ) &amp; sendAllSpam
"
    REFERENCE "Message Limit Blocks"
    DEFVAL { "3" }
    ::= {Collecting 645}

syncStatspamMSLog  OBJECT-TYPE
    SYNTAX      OCTET STRING
    MAX-ACCESS  read-only
    STATUS      current
    DESCRIPTION
"
synchronization status for spamMSLog
-1 - spamMSLog could not be synchronized
 0 - synchronization not configured
 1 - out of sync - running master mode
 2 - in sync - running  mastermode
 3 - in sync - running slave mode
 4 - in sync - running master mode (wait to reach state 2)
"
    ::= {spamMSLog 5}

syncStatStrspamMSLog  OBJECT-TYPE
    SYNTAX      OCTET STRING
    MAX-ACCESS  read-only
    STATUS      current
    DESCRIPTION
"
synchronization status line from file assp_sync.cfg for spamMSLog
 0 - synchronization not configured
 1 - out of sync - running master mode
 2 - in sync - running  mastermode
 3 - in sync - running slave mode
 4 - in sync - running master mode (wait to reach state 2)
"
    ::= {spamMSLog 6}

spamPBLog  OBJECT-TYPE
    SYNTAX      OCTET STRING
    MAX-ACCESS  read-write
    STATUS      current
    DESCRIPTION
"
Where to store PB rejected messages. Recommended: spam folder ( spamlog ) &amp; sendAllSpam
"
    REFERENCE "PenaltyBox Blocks"
    DEFVAL { "3" }
    ::= {Collecting 646}

syncStatspamPBLog  OBJECT-TYPE
    SYNTAX      OCTET STRING
    MAX-ACCESS  read-only
    STATUS      current
    DESCRIPTION
"
synchronization status for spamPBLog
-1 - spamPBLog could not be synchronized
 0 - synchronization not configured
 1 - out of sync - running master mode
 2 - in sync - running  mastermode
 3 - in sync - running slave mode
 4 - in sync - running master mode (wait to reach state 2)
"
    ::= {spamPBLog 5}

syncStatStrspamPBLog  OBJECT-TYPE
    SYNTAX      OCTET STRING
    MAX-ACCESS  read-only
    STATUS      current
    DESCRIPTION
"
synchronization status line from file assp_sync.cfg for spamPBLog
 0 - synchronization not configured
 1 - out of sync - running master mode
 2 - in sync - running  mastermode
 3 - in sync - running slave mode
 4 - in sync - running master mode (wait to reach state 2)
"
    ::= {spamPBLog 6}

DKIMLog  OBJECT-TYPE
    SYNTAX      OCTET STRING
    MAX-ACCESS  read-write
    STATUS      current
    DESCRIPTION
"
Where to store DKIM rejected messages. Recommended: spam folder ( spamlog ) &amp; sendAllSpam
"
    REFERENCE "DKIM failed"
    DEFVAL { "3" }
    ::= {Collecting 647}

syncStatDKIMLog  OBJECT-TYPE
    SYNTAX      OCTET STRING
    MAX-ACCESS  read-only
    STATUS      current
    DESCRIPTION
"
synchronization status for DKIMLog
-1 - DKIMLog could not be synchronized
 0 - synchronization not configured
 1 - out of sync - running master mode
 2 - in sync - running  mastermode
 3 - in sync - running slave mode
 4 - in sync - running master mode (wait to reach state 2)
"
    ::= {DKIMLog 5}

syncStatStrDKIMLog  OBJECT-TYPE
    SYNTAX      OCTET STRING
    MAX-ACCESS  read-only
    STATUS      current
    DESCRIPTION
"
synchronization status line from file assp_sync.cfg for DKIMLog
 0 - synchronization not configured
 1 - out of sync - running master mode
 2 - in sync - running  mastermode
 3 - in sync - running slave mode
 4 - in sync - running master mode (wait to reach state 2)
"
    ::= {DKIMLog 6}

BackLog  OBJECT-TYPE
    SYNTAX      OCTET STRING
    MAX-ACCESS  read-write
    STATUS      current
    DESCRIPTION
"
Where to store backscatter (MSGID-signing, BATV, DNS-Backscatter) rejected messages. Recommended: no collection
"
    REFERENCE "Backscatter check failed"
    DEFVAL { "6" }
    ::= {Collecting 648}

syncStatBackLog  OBJECT-TYPE
    SYNTAX      OCTET STRING
    MAX-ACCESS  read-only
    STATUS      current
    DESCRIPTION
"
synchronization status for BackLog
-1 - BackLog could not be synchronized
 0 - synchronization not configured
 1 - out of sync - running master mode
 2 - in sync - running  mastermode
 3 - in sync - running slave mode
 4 - in sync - running master mode (wait to reach state 2)
"
    ::= {BackLog 5}

syncStatStrBackLog  OBJECT-TYPE
    SYNTAX      OCTET STRING
    MAX-ACCESS  read-only
    STATUS      current
    DESCRIPTION
"
synchronization status line from file assp_sync.cfg for BackLog
 0 - synchronization not configured
 1 - out of sync - running master mode
 2 - in sync - running  mastermode
 3 - in sync - running slave mode
 4 - in sync - running master mode (wait to reach state 2)
"
    ::= {BackLog 6}

freqNonSpam  OBJECT-TYPE
    SYNTAX      OCTET STRING
    MAX-ACCESS  read-write
    STATUS      current
    DESCRIPTION
"
Store every n'th non spam message. If you set the value to 10 then every 10th message is logged. These frequency settings are for ASSP users with a mature installation who experience heavy mail or spam volumes. Enter a larger value if the non spam corpus is being refreshed too quickly. Default Value = 1, log every message. Leave it at the default value 1, if you use BlockReports.
"
    REFERENCE "Non Spam Collection Frequency"
    DEFVAL { "1" }
    ::= {Collecting 649}

syncStatfreqNonSpam  OBJECT-TYPE
    SYNTAX      OCTET STRING
    MAX-ACCESS  read-only
    STATUS      current
    DESCRIPTION
"
synchronization status for freqNonSpam
-1 - freqNonSpam could not be synchronized
 0 - synchronization not configured
 1 - out of sync - running master mode
 2 - in sync - running  mastermode
 3 - in sync - running slave mode
 4 - in sync - running master mode (wait to reach state 2)
"
    ::= {freqNonSpam 5}

syncStatStrfreqNonSpam  OBJECT-TYPE
    SYNTAX      OCTET STRING
    MAX-ACCESS  read-only
    STATUS      current
    DESCRIPTION
"
synchronization status line from file assp_sync.cfg for freqNonSpam
 0 - synchronization not configured
 1 - out of sync - running master mode
 2 - in sync - running  mastermode
 3 - in sync - running slave mode
 4 - in sync - running master mode (wait to reach state 2)
"
    ::= {freqNonSpam 6}

freqSpam  OBJECT-TYPE
    SYNTAX      OCTET STRING
    MAX-ACCESS  read-write
    STATUS      current
    DESCRIPTION
"
Store every n'th spam message. The same as for non spam but helps prevent spam corpuses being skewed by flooding. It is recommended that this be set depending on spam volume. Default value = 1, log every message. Leave it at the default value 1, if you use BlockReports.
"
    REFERENCE "Spam Collection Frequency"
    DEFVAL { "1" }
    ::= {Collecting 650}

syncStatfreqSpam  OBJECT-TYPE
    SYNTAX      OCTET STRING
    MAX-ACCESS  read-only
    STATUS      current
    DESCRIPTION
"
synchronization status for freqSpam
-1 - freqSpam could not be synchronized
 0 - synchronization not configured
 1 - out of sync - running master mode
 2 - in sync - running  mastermode
 3 - in sync - running slave mode
 4 - in sync - running master mode (wait to reach state 2)
"
    ::= {freqSpam 5}

syncStatStrfreqSpam  OBJECT-TYPE
    SYNTAX      OCTET STRING
    MAX-ACCESS  read-only
    STATUS      current
    DESCRIPTION
"
synchronization status line from file assp_sync.cfg for freqSpam
 0 - synchronization not configured
 1 - out of sync - running master mode
 2 - in sync - running  mastermode
 3 - in sync - running slave mode
 4 - in sync - running master mode (wait to reach state 2)
"
    ::= {freqSpam 6}

MaxCorrectedDays  OBJECT-TYPE
    SYNTAX      OCTET STRING
    MAX-ACCESS  read-write
    STATUS      current
    DESCRIPTION
"
This is the number of days a error report will be kept in the correctedspam and correctednotspam folders. These folders are the longterm memory of ASSP, therefore the default is 10000 days (more than 27 years). To use different values for correctedspam and correctednotspam, define two space separated values - the first for correctedspam and the second for correctednotspam, like '1000 1500'. The rebuildspamdb task will ignore files older than this days (if not set to zero).
"
    REFERENCE "Max Corrected File Age"
    DEFVAL { "10000" }
    ::= {Collecting 859}

syncStatMaxCorrectedDays  OBJECT-TYPE
    SYNTAX      OCTET STRING
    MAX-ACCESS  read-only
    STATUS      current
    DESCRIPTION
"
synchronization status for MaxCorrectedDays
-1 - MaxCorrectedDays could not be synchronized
 0 - synchronization not configured
 1 - out of sync - running master mode
 2 - in sync - running  mastermode
 3 - in sync - running slave mode
 4 - in sync - running master mode (wait to reach state 2)
"
    ::= {MaxCorrectedDays 5}

syncStatStrMaxCorrectedDays  OBJECT-TYPE
    SYNTAX      OCTET STRING
    MAX-ACCESS  read-only
    STATUS      current
    DESCRIPTION
"
synchronization status line from file assp_sync.cfg for MaxCorrectedDays
 0 - synchronization not configured
 1 - out of sync - running master mode
 2 - in sync - running  mastermode
 3 - in sync - running slave mode
 4 - in sync - running master mode (wait to reach state 2)
"
    ::= {MaxCorrectedDays 6}

MaxAllowedDups  OBJECT-TYPE
    SYNTAX      OCTET STRING
    MAX-ACCESS  read-write
    STATUS      current
    DESCRIPTION
"
The maximum number of logged files with the same filename (subject) that are stored in the spam folder (spamlog), if UseSubjectsAsMaillogNames is selected. Default is 0. A low value reduces the number of possibly duplicate mails, assuming that mails with the same subject will have the same content. A value of 0 disables this feature. If this number of files with the same filename is reached, the oldest file with the same subject will be moved to the discarded folder, which has to be defined ( in addition to spamlog ) for this feature to work.
"
    REFERENCE "Max Number of Duplicate File Names"
    DEFVAL { "5" }
    ::= {Collecting 866}

syncStatMaxAllowedDups  OBJECT-TYPE
    SYNTAX      OCTET STRING
    MAX-ACCESS  read-only
    STATUS      current
    DESCRIPTION
"
synchronization status for MaxAllowedDups
-1 - MaxAllowedDups could not be synchronized
 0 - synchronization not configured
 1 - out of sync - running master mode
 2 - in sync - running  mastermode
 3 - in sync - running slave mode
 4 - in sync - running master mode (wait to reach state 2)
"
    ::= {MaxAllowedDups 5}

syncStatStrMaxAllowedDups  OBJECT-TYPE
    SYNTAX      OCTET STRING
    MAX-ACCESS  read-only
    STATUS      current
    DESCRIPTION
"
synchronization status line from file assp_sync.cfg for MaxAllowedDups
 0 - synchronization not configured
 1 - out of sync - running master mode
 2 - in sync - running  mastermode
 3 - in sync - running slave mode
 4 - in sync - running master mode (wait to reach state 2)
"
    ::= {MaxAllowedDups 6}

AllowedDupSubjectRe  OBJECT-TYPE
    SYNTAX      OCTET STRING
    MAX-ACCESS  read-write
    STATUS      current
    DESCRIPTION
"
Messages their subject matches this regular expression will be collected regardless the setting in MaxAllowedDups .
"
    REFERENCE "Regular Expression to Identify allowed duplicate Subjects*"
    DEFVAL { "" }
    ::= {Collecting 867}

syncStatAllowedDupSubjectRe  OBJECT-TYPE
    SYNTAX      OCTET STRING
    MAX-ACCESS  read-only
    STATUS      current
    DESCRIPTION
"
synchronization status for AllowedDupSubjectRe
-1 - AllowedDupSubjectRe could not be synchronized
 0 - synchronization not configured
 1 - out of sync - running master mode
 2 - in sync - running  mastermode
 3 - in sync - running slave mode
 4 - in sync - running master mode (wait to reach state 2)
"
    ::= {AllowedDupSubjectRe 5}

syncStatStrAllowedDupSubjectRe  OBJECT-TYPE
    SYNTAX      OCTET STRING
    MAX-ACCESS  read-only
    STATUS      current
    DESCRIPTION
"
synchronization status line from file assp_sync.cfg for AllowedDupSubjectRe
 0 - synchronization not configured
 1 - out of sync - running master mode
 2 - in sync - running  mastermode
 3 - in sync - running slave mode
 4 - in sync - running master mode (wait to reach state 2)
"
    ::= {AllowedDupSubjectRe 6}

UseUnicode4SubjectLogging  OBJECT-TYPE
    SYNTAX      OCTET STRING
    MAX-ACCESS  read-write
    STATUS      current
    DESCRIPTION
"
If you have switched on UseUnicode4SubjectLogging and your default (local language) characterset (please setup ConsoleCharset) needs 8 Bit like 'KOI8-r','CP-866','Windows-1251','Windows-1252','ISO-8859-X','X-Mac-Cyrillic','JIS_X0201' or any other (or is UTF-8) - and you want to have a readable subject in the maillog and on the console screen, you can switch on this option. The resolution of some characters written to the console could be incorrect depending on your operating system. This requires an installed  module in PERL.
"
    REFERENCE "Use Unicode to build Subjects in Maillog"
    DEFVAL { "" }
    ::= {Collecting 892}

syncStatUseUnicode4SubjectLogging  OBJECT-TYPE
    SYNTAX      OCTET STRING
    MAX-ACCESS  read-only
    STATUS      current
    DESCRIPTION
"
synchronization status for UseUnicode4SubjectLogging
-1 - UseUnicode4SubjectLogging could not be synchronized
 0 - synchronization not configured
 1 - out of sync - running master mode
 2 - in sync - running  mastermode
 3 - in sync - running slave mode
 4 - in sync - running master mode (wait to reach state 2)
"
    ::= {UseUnicode4SubjectLogging 5}

syncStatStrUseUnicode4SubjectLogging  OBJECT-TYPE
    SYNTAX      OCTET STRING
    MAX-ACCESS  read-only
    STATUS      current
    DESCRIPTION
"
synchronization status line from file assp_sync.cfg for UseUnicode4SubjectLogging
 0 - synchronization not configured
 1 - out of sync - running master mode
 2 - in sync - running  mastermode
 3 - in sync - running slave mode
 4 - in sync - running master mode (wait to reach state 2)
"
    ::= {UseUnicode4SubjectLogging 6}

noCollectRe  OBJECT-TYPE
    SYNTAX      OCTET STRING
    MAX-ACCESS  read-write
    STATUS      current
    DESCRIPTION
"
If the content of a collected file (incl. X-ASSP-... headers) matches this regular expression, it will be deleted from the collection after the mail is completely processed.
  If the ASSP_ARC plugin is used, the file will be deleted from the collection after it was archived. This is the only 'no collect' option which removes an already collected file, all other options will prevent assp from creating a collection file - if set to 'no collection'. The check is limited to MaxBytes or at max 100000 Bytes.
"
    REFERENCE "Do Not Collect Messages - Content Based*"
    DEFVAL { "" }
    ::= {Collecting 893}

syncStatnoCollectRe  OBJECT-TYPE
    SYNTAX      OCTET STRING
    MAX-ACCESS  read-only
    STATUS      current
    DESCRIPTION
"
synchronization status for noCollectRe
-1 - noCollectRe could not be synchronized
 0 - synchronization not configured
 1 - out of sync - running master mode
 2 - in sync - running  mastermode
 3 - in sync - running slave mode
 4 - in sync - running master mode (wait to reach state 2)
"
    ::= {noCollectRe 5}

syncStatStrnoCollectRe  OBJECT-TYPE
    SYNTAX      OCTET STRING
    MAX-ACCESS  read-only
    STATUS      current
    DESCRIPTION
"
synchronization status line from file assp_sync.cfg for noCollectRe
 0 - synchronization not configured
 1 - out of sync - running master mode
 2 - in sync - running  mastermode
 3 - in sync - running slave mode
 4 - in sync - running master mode (wait to reach state 2)
"
    ::= {noCollectRe 6}

Logging  OBJECT IDENTIFIER ::= {asspConfig 29}
Notify  OBJECT-TYPE
    SYNTAX      OCTET STRING
    MAX-ACCESS  read-write
    STATUS      current
    DESCRIPTION
"
Email address(es) to which you want ASSP to send a notification email per default, if a matching log entry ( NotifyRe , NoNotifyRe ) is found. Separate multiple entries by comma ','.
  NOTICE: that groups are not allowed to be used here!
"
    REFERENCE "Notification Email To"
    DEFVAL { "" }
    ::= {Logging 651}

syncStatNotify  OBJECT-TYPE
    SYNTAX      OCTET STRING
    MAX-ACCESS  read-only
    STATUS      current
    DESCRIPTION
"
synchronization status for Notify
-1 - Notify could not be synchronized
 0 - synchronization not configured
 1 - out of sync - running master mode
 2 - in sync - running  mastermode
 3 - in sync - running slave mode
 4 - in sync - running master mode (wait to reach state 2)
"
    ::= {Notify 5}

syncStatStrNotify  OBJECT-TYPE
    SYNTAX      OCTET STRING
    MAX-ACCESS  read-only
    STATUS      current
    DESCRIPTION
"
synchronization status line from file assp_sync.cfg for Notify
 0 - synchronization not configured
 1 - out of sync - running master mode
 2 - in sync - running  mastermode
 3 - in sync - running slave mode
 4 - in sync - running master mode (wait to reach state 2)
"
    ::= {Notify 6}

NotifyRe  OBJECT-TYPE
    SYNTAX      OCTET STRING
    MAX-ACCESS  read-write
    STATUS      current
    DESCRIPTION
"
Regular Expression to identify loglines for which a notification message should be send.
  useful entries are:
  Info: new assp version - to get informed about new available assp versions
  info: autoupdate: new assp version - to get informed about an autoupdate of the running script
  adminupdate: - for config changes
  admininfo: - for admin information
  option list file: - for option file reload
  error: - for any error
  warning: - for any warning
  restart - to detect a ASSP restart
  notification: too many recipients - for local frequency abuse once per day and sender
  warning: too many recipients - for every local frequency abuse
  MainThread started - to detect a start of ASSP
  Admin connection - for GUI logon
  You may define a comma separated list (after '=>') of recipients in every line, this will override the default recipient defined in 'Notify'.
  for example: adminupdate:=>user1@yourdomain.com,user2@yourdomain.com.
  NOTICE: that groups are not allowed to be used for the second parameter!
  As third parameter after a second ('=>') you can define the subject line for the notification message.
  for example: adminupdate:=>user1@yourdomain.com,user2@yourdomain.com=>configuration was changed
  or: adminupdate:=>=>configuration was changed.
"
    REFERENCE "Do Notify, if log entry matches*"
    DEFVAL { "" }
    ::= {Logging 652}

syncStatNotifyRe  OBJECT-TYPE
    SYNTAX      OCTET STRING
    MAX-ACCESS  read-only
    STATUS      current
    DESCRIPTION
"
synchronization status for NotifyRe
-1 - NotifyRe could not be synchronized
 0 - synchronization not configured
 1 - out of sync - running master mode
 2 - in sync - running  mastermode
 3 - in sync - running slave mode
 4 - in sync - running master mode (wait to reach state 2)
"
    ::= {NotifyRe 5}

syncStatStrNotifyRe  OBJECT-TYPE
    SYNTAX      OCTET STRING
    MAX-ACCESS  read-only
    STATUS      current
    DESCRIPTION
"
synchronization status line from file assp_sync.cfg for NotifyRe
 0 - synchronization not configured
 1 - out of sync - running master mode
 2 - in sync - running  mastermode
 3 - in sync - running slave mode
 4 - in sync - running master mode (wait to reach state 2)
"
    ::= {NotifyRe 6}

NoNotifyRe  OBJECT-TYPE
    SYNTAX      OCTET STRING
    MAX-ACCESS  read-write
    STATUS      current
    DESCRIPTION
"
Regular Expression to identify loglines for which no notification message should be send.
  for example:
  user root - if root does anything
  \[root.*?\] - if root changes the config
"
    REFERENCE "Do NOT Notify, if log entry matches*"
    DEFVAL { "" }
    ::= {Logging 653}

syncStatNoNotifyRe  OBJECT-TYPE
    SYNTAX      OCTET STRING
    MAX-ACCESS  read-only
    STATUS      current
    DESCRIPTION
"
synchronization status for NoNotifyRe
-1 - NoNotifyRe could not be synchronized
 0 - synchronization not configured
 1 - out of sync - running master mode
 2 - in sync - running  mastermode
 3 - in sync - running slave mode
 4 - in sync - running master mode (wait to reach state 2)
"
    ::= {NoNotifyRe 5}

syncStatStrNoNotifyRe  OBJECT-TYPE
    SYNTAX      OCTET STRING
    MAX-ACCESS  read-only
    STATUS      current
    DESCRIPTION
"
synchronization status line from file assp_sync.cfg for NoNotifyRe
 0 - synchronization not configured
 1 - out of sync - running master mode
 2 - in sync - running  mastermode
 3 - in sync - running slave mode
 4 - in sync - running master mode (wait to reach state 2)
"
    ::= {NoNotifyRe 6}

fileLogging  OBJECT-TYPE
    SYNTAX      OCTET STRING
    MAX-ACCESS  read-write
    STATUS      current
    DESCRIPTION
"
Show file names of collected spam/notspam in log. Will be automaticly set to on, if inclResendLink is not set to disabled.
"
    REFERENCE "File name logging"
    DEFVAL { "" }
    ::= {Logging 654}

syncStatfileLogging  OBJECT-TYPE
    SYNTAX      OCTET STRING
    MAX-ACCESS  read-only
    STATUS      current
    DESCRIPTION
"
synchronization status for fileLogging
-1 - fileLogging could not be synchronized
 0 - synchronization not configured
 1 - out of sync - running master mode
 2 - in sync - running  mastermode
 3 - in sync - running slave mode
 4 - in sync - running master mode (wait to reach state 2)
"
    ::= {fileLogging 5}

syncStatStrfileLogging  OBJECT-TYPE
    SYNTAX      OCTET STRING
    MAX-ACCESS  read-only
    STATUS      current
    DESCRIPTION
"
synchronization status line from file assp_sync.cfg for fileLogging
 0 - synchronization not configured
 1 - out of sync - running master mode
 2 - in sync - running  mastermode
 3 - in sync - running slave mode
 4 - in sync - running master mode (wait to reach state 2)
"
    ::= {fileLogging 6}

subjectLogging  OBJECT-TYPE
    SYNTAX      OCTET STRING
    MAX-ACCESS  read-write
    STATUS      current
    DESCRIPTION
"
Show subject of mail in log 
"
    REFERENCE "Subject logging"
    DEFVAL { "1" }
    ::= {Logging 655}

syncStatsubjectLogging  OBJECT-TYPE
    SYNTAX      OCTET STRING
    MAX-ACCESS  read-only
    STATUS      current
    DESCRIPTION
"
synchronization status for subjectLogging
-1 - subjectLogging could not be synchronized
 0 - synchronization not configured
 1 - out of sync - running master mode
 2 - in sync - running  mastermode
 3 - in sync - running slave mode
 4 - in sync - running master mode (wait to reach state 2)
"
    ::= {subjectLogging 5}

syncStatStrsubjectLogging  OBJECT-TYPE
    SYNTAX      OCTET STRING
    MAX-ACCESS  read-only
    STATUS      current
    DESCRIPTION
"
synchronization status line from file assp_sync.cfg for subjectLogging
 0 - synchronization not configured
 1 - out of sync - running master mode
 2 - in sync - running  mastermode
 3 - in sync - running slave mode
 4 - in sync - running master mode (wait to reach state 2)
"
    ::= {subjectLogging 6}

subjectStart  OBJECT-TYPE
    SYNTAX      OCTET STRING
    MAX-ACCESS  read-write
    STATUS      current
    DESCRIPTION
"
Start delimiter of subject in log 
"
    REFERENCE "Subject Start Delimiter"
    DEFVAL { "[" }
    ::= {Logging 656}

syncStatsubjectStart  OBJECT-TYPE
    SYNTAX      OCTET STRING
    MAX-ACCESS  read-only
    STATUS      current
    DESCRIPTION
"
synchronization status for subjectStart
-1 - subjectStart could not be synchronized
 0 - synchronization not configured
 1 - out of sync - running master mode
 2 - in sync - running  mastermode
 3 - in sync - running slave mode
 4 - in sync - running master mode (wait to reach state 2)
"
    ::= {subjectStart 5}

syncStatStrsubjectStart  OBJECT-TYPE
    SYNTAX      OCTET STRING
    MAX-ACCESS  read-only
    STATUS      current
    DESCRIPTION
"
synchronization status line from file assp_sync.cfg for subjectStart
 0 - synchronization not configured
 1 - out of sync - running master mode
 2 - in sync - running  mastermode
 3 - in sync - running slave mode
 4 - in sync - running master mode (wait to reach state 2)
"
    ::= {subjectStart 6}

subjectEnd  OBJECT-TYPE
    SYNTAX      OCTET STRING
    MAX-ACCESS  read-write
    STATUS      current
    DESCRIPTION
"
End delimiter of subject in log
"
    REFERENCE "Subject End Delimiter"
    DEFVAL { "]" }
    ::= {Logging 657}

syncStatsubjectEnd  OBJECT-TYPE
    SYNTAX      OCTET STRING
    MAX-ACCESS  read-only
    STATUS      current
    DESCRIPTION
"
synchronization status for subjectEnd
-1 - subjectEnd could not be synchronized
 0 - synchronization not configured
 1 - out of sync - running master mode
 2 - in sync - running  mastermode
 3 - in sync - running slave mode
 4 - in sync - running master mode (wait to reach state 2)
"
    ::= {subjectEnd 5}

syncStatStrsubjectEnd  OBJECT-TYPE
    SYNTAX      OCTET STRING
    MAX-ACCESS  read-only
    STATUS      current
    DESCRIPTION
"
synchronization status line from file assp_sync.cfg for subjectEnd
 0 - synchronization not configured
 1 - out of sync - running master mode
 2 - in sync - running  mastermode
 3 - in sync - running slave mode
 4 - in sync - running master mode (wait to reach state 2)
"
    ::= {subjectEnd 6}

regexLogging  OBJECT-TYPE
    SYNTAX      OCTET STRING
    MAX-ACCESS  read-write
    STATUS      current
    DESCRIPTION
"
Show matching regex in log, note that all lists (like eg. noprocessing-list) are used as regex. 
"
    REFERENCE "Regex Match logging"
    DEFVAL { "1" }
    ::= {Logging 658}

syncStatregexLogging  OBJECT-TYPE
    SYNTAX      OCTET STRING
    MAX-ACCESS  read-only
    STATUS      current
    DESCRIPTION
"
synchronization status for regexLogging
-1 - regexLogging could not be synchronized
 0 - synchronization not configured
 1 - out of sync - running master mode
 2 - in sync - running  mastermode
 3 - in sync - running slave mode
 4 - in sync - running master mode (wait to reach state 2)
"
    ::= {regexLogging 5}

syncStatStrregexLogging  OBJECT-TYPE
    SYNTAX      OCTET STRING
    MAX-ACCESS  read-only
    STATUS      current
    DESCRIPTION
"
synchronization status line from file assp_sync.cfg for regexLogging
 0 - synchronization not configured
 1 - out of sync - running master mode
 2 - in sync - running  mastermode
 3 - in sync - running slave mode
 4 - in sync - running master mode (wait to reach state 2)
"
    ::= {regexLogging 6}

WorkerLogging  OBJECT-TYPE
    SYNTAX      OCTET STRING
    MAX-ACCESS  read-write
    STATUS      current
    DESCRIPTION
"
Show Workername in Log. 
"
    REFERENCE "Worker logging"
    DEFVAL { "1" }
    ::= {Logging 659}

syncStatWorkerLogging  OBJECT-TYPE
    SYNTAX      OCTET STRING
    MAX-ACCESS  read-only
    STATUS      current
    DESCRIPTION
"
synchronization status for WorkerLogging
-1 - WorkerLogging could not be synchronized
 0 - synchronization not configured
 1 - out of sync - running master mode
 2 - in sync - running  mastermode
 3 - in sync - running slave mode
 4 - in sync - running master mode (wait to reach state 2)
"
    ::= {WorkerLogging 5}

syncStatStrWorkerLogging  OBJECT-TYPE
    SYNTAX      OCTET STRING
    MAX-ACCESS  read-only
    STATUS      current
    DESCRIPTION
"
synchronization status line from file assp_sync.cfg for WorkerLogging
 0 - synchronization not configured
 1 - out of sync - running master mode
 2 - in sync - running  mastermode
 3 - in sync - running slave mode
 4 - in sync - running master mode (wait to reach state 2)
"
    ::= {WorkerLogging 6}

ipmatchLogging  OBJECT-TYPE
    SYNTAX      OCTET STRING
    MAX-ACCESS  read-write
    STATUS      current
    DESCRIPTION
"
Enables logging of IP addresses matches in the maillog. Will show a comment instead of the range if there is text after the IP ranges (and before any numbersign)  eg. 182.82.10.0/24 AOL
"
    REFERENCE "IP Matches Logging"
    DEFVAL { "" }
    ::= {Logging 660}

syncStatipmatchLogging  OBJECT-TYPE
    SYNTAX      OCTET STRING
    MAX-ACCESS  read-only
    STATUS      current
    DESCRIPTION
"
synchronization status for ipmatchLogging
-1 - ipmatchLogging could not be synchronized
 0 - synchronization not configured
 1 - out of sync - running master mode
 2 - in sync - running  mastermode
 3 - in sync - running slave mode
 4 - in sync - running master mode (wait to reach state 2)
"
    ::= {ipmatchLogging 5}

syncStatStripmatchLogging  OBJECT-TYPE
    SYNTAX      OCTET STRING
    MAX-ACCESS  read-only
    STATUS      current
    DESCRIPTION
"
synchronization status line from file assp_sync.cfg for ipmatchLogging
 0 - synchronization not configured
 1 - out of sync - running master mode
 2 - in sync - running  mastermode
 3 - in sync - running slave mode
 4 - in sync - running master mode (wait to reach state 2)
"
    ::= {ipmatchLogging 6}

slmatchLogging  OBJECT-TYPE
    SYNTAX      OCTET STRING
    MAX-ACCESS  read-write
    STATUS      current
    DESCRIPTION
"
Enables logging of address matches in the maillog.
"
    REFERENCE "Logging Address Matches"
    DEFVAL { "" }
    ::= {Logging 661}

syncStatslmatchLogging  OBJECT-TYPE
    SYNTAX      OCTET STRING
    MAX-ACCESS  read-only
    STATUS      current
    DESCRIPTION
"
synchronization status for slmatchLogging
-1 - slmatchLogging could not be synchronized
 0 - synchronization not configured
 1 - out of sync - running master mode
 2 - in sync - running  mastermode
 3 - in sync - running slave mode
 4 - in sync - running master mode (wait to reach state 2)
"
    ::= {slmatchLogging 5}

syncStatStrslmatchLogging  OBJECT-TYPE
    SYNTAX      OCTET STRING
    MAX-ACCESS  read-only
    STATUS      current
    DESCRIPTION
"
synchronization status line from file assp_sync.cfg for slmatchLogging
 0 - synchronization not configured
 1 - out of sync - running master mode
 2 - in sync - running  mastermode
 3 - in sync - running slave mode
 4 - in sync - running master mode (wait to reach state 2)
"
    ::= {slmatchLogging 6}

AddRegexHeader  OBJECT-TYPE
    SYNTAX      OCTET STRING
    MAX-ACCESS  read-write
    STATUS      current
    DESCRIPTION
"

"
    REFERENCE "Add RegEx Match Header"
    DEFVAL { "" }
    ::= {Logging 662}

syncStatAddRegexHeader  OBJECT-TYPE
    SYNTAX      OCTET STRING
    MAX-ACCESS  read-only
    STATUS      current
    DESCRIPTION
"
synchronization status for AddRegexHeader
-1 - AddRegexHeader could not be synchronized
 0 - synchronization not configured
 1 - out of sync - running master mode
 2 - in sync - running  mastermode
 3 - in sync - running slave mode
 4 - in sync - running master mode (wait to reach state 2)
"
    ::= {AddRegexHeader 5}

syncStatStrAddRegexHeader  OBJECT-TYPE
    SYNTAX      OCTET STRING
    MAX-ACCESS  read-only
    STATUS      current
    DESCRIPTION
"
synchronization status line from file assp_sync.cfg for AddRegexHeader
 0 - synchronization not configured
 1 - out of sync - running master mode
 2 - in sync - running  mastermode
 3 - in sync - running slave mode
 4 - in sync - running master mode (wait to reach state 2)
"
    ::= {AddRegexHeader 6}

uniqeIDLogging  OBJECT-TYPE
    SYNTAX      OCTET STRING
    MAX-ACCESS  read-write
    STATUS      current
    DESCRIPTION
"
Add unique string to log  
"
    REFERENCE "Unique ID logging"
    DEFVAL { "1" }
    ::= {Logging 663}

syncStatuniqeIDLogging  OBJECT-TYPE
    SYNTAX      OCTET STRING
    MAX-ACCESS  read-only
    STATUS      current
    DESCRIPTION
"
synchronization status for uniqeIDLogging
-1 - uniqeIDLogging could not be synchronized
 0 - synchronization not configured
 1 - out of sync - running master mode
 2 - in sync - running  mastermode
 3 - in sync - running slave mode
 4 - in sync - running master mode (wait to reach state 2)
"
    ::= {uniqeIDLogging 5}

syncStatStruniqeIDLogging  OBJECT-TYPE
    SYNTAX      OCTET STRING
    MAX-ACCESS  read-only
    STATUS      current
    DESCRIPTION
"
synchronization status line from file assp_sync.cfg for uniqeIDLogging
 0 - synchronization not configured
 1 - out of sync - running master mode
 2 - in sync - running  mastermode
 3 - in sync - running slave mode
 4 - in sync - running master mode (wait to reach state 2)
"
    ::= {uniqeIDLogging 6}

uniqueIDPrefix  OBJECT-TYPE
    SYNTAX      OCTET STRING
    MAX-ACCESS  read-write
    STATUS      current
    DESCRIPTION
"
Prepend ID. For example: m1-
"
    REFERENCE "Prepend Unique ID logging"
    DEFVAL { "m1-" }
    ::= {Logging 664}

syncStatuniqueIDPrefix  OBJECT-TYPE
    SYNTAX      OCTET STRING
    MAX-ACCESS  read-only
    STATUS      current
    DESCRIPTION
"
synchronization status for uniqueIDPrefix
-1 - uniqueIDPrefix could not be synchronized
 0 - synchronization not configured
 1 - out of sync - running master mode
 2 - in sync - running  mastermode
 3 - in sync - running slave mode
 4 - in sync - running master mode (wait to reach state 2)
"
    ::= {uniqueIDPrefix 5}

syncStatStruniqueIDPrefix  OBJECT-TYPE
    SYNTAX      OCTET STRING
    MAX-ACCESS  read-only
    STATUS      current
    DESCRIPTION
"
synchronization status line from file assp_sync.cfg for uniqueIDPrefix
 0 - synchronization not configured
 1 - out of sync - running master mode
 2 - in sync - running  mastermode
 3 - in sync - running slave mode
 4 - in sync - running master mode (wait to reach state 2)
"
    ::= {uniqueIDPrefix 6}

tagLogging  OBJECT-TYPE
    SYNTAX      OCTET STRING
    MAX-ACCESS  read-write
    STATUS      current
    DESCRIPTION
"
Add spam tag to log.
"
    REFERENCE "Spam Tag Logging"
    DEFVAL { "1" }
    ::= {Logging 665}

syncStattagLogging  OBJECT-TYPE
    SYNTAX      OCTET STRING
    MAX-ACCESS  read-only
    STATUS      current
    DESCRIPTION
"
synchronization status for tagLogging
-1 - tagLogging could not be synchronized
 0 - synchronization not configured
 1 - out of sync - running master mode
 2 - in sync - running  mastermode
 3 - in sync - running slave mode
 4 - in sync - running master mode (wait to reach state 2)
"
    ::= {tagLogging 5}

syncStatStrtagLogging  OBJECT-TYPE
    SYNTAX      OCTET STRING
    MAX-ACCESS  read-only
    STATUS      current
    DESCRIPTION
"
synchronization status line from file assp_sync.cfg for tagLogging
 0 - synchronization not configured
 1 - out of sync - running master mode
 2 - in sync - running  mastermode
 3 - in sync - running slave mode
 4 - in sync - running master mode (wait to reach state 2)
"
    ::= {tagLogging 6}

replyLogging  OBJECT-TYPE
    SYNTAX      OCTET STRING
    MAX-ACCESS  read-write
    STATUS      current
    DESCRIPTION
"

"
    REFERENCE "SMTP Status Code Reply Logging"
    DEFVAL { "1" }
    ::= {Logging 666}

syncStatreplyLogging  OBJECT-TYPE
    SYNTAX      OCTET STRING
    MAX-ACCESS  read-only
    STATUS      current
    DESCRIPTION
"
synchronization status for replyLogging
-1 - replyLogging could not be synchronized
 0 - synchronization not configured
 1 - out of sync - running master mode
 2 - in sync - running  mastermode
 3 - in sync - running slave mode
 4 - in sync - running master mode (wait to reach state 2)
"
    ::= {replyLogging 5}

syncStatStrreplyLogging  OBJECT-TYPE
    SYNTAX      OCTET STRING
    MAX-ACCESS  read-only
    STATUS      current
    DESCRIPTION
"
synchronization status line from file assp_sync.cfg for replyLogging
 0 - synchronization not configured
 1 - out of sync - running master mode
 2 - in sync - running  mastermode
 3 - in sync - running slave mode
 4 - in sync - running master mode (wait to reach state 2)
"
    ::= {replyLogging 6}

expandedLogging  OBJECT-TYPE
    SYNTAX      OCTET STRING
    MAX-ACCESS  read-write
    STATUS      current
    DESCRIPTION
"

"
    REFERENCE "Logging Records include IP &amp; MailFrom"
    DEFVAL { "1" }
    ::= {Logging 667}

syncStatexpandedLogging  OBJECT-TYPE
    SYNTAX      OCTET STRING
    MAX-ACCESS  read-only
    STATUS      current
    DESCRIPTION
"
synchronization status for expandedLogging
-1 - expandedLogging could not be synchronized
 0 - synchronization not configured
 1 - out of sync - running master mode
 2 - in sync - running  mastermode
 3 - in sync - running slave mode
 4 - in sync - running master mode (wait to reach state 2)
"
    ::= {expandedLogging 5}

syncStatStrexpandedLogging  OBJECT-TYPE
    SYNTAX      OCTET STRING
    MAX-ACCESS  read-only
    STATUS      current
    DESCRIPTION
"
synchronization status line from file assp_sync.cfg for expandedLogging
 0 - synchronization not configured
 1 - out of sync - running master mode
 2 - in sync - running  mastermode
 3 - in sync - running slave mode
 4 - in sync - running master mode (wait to reach state 2)
"
    ::= {expandedLogging 6}

sysLog  OBJECT-TYPE
    SYNTAX      OCTET STRING
    MAX-ACCESS  read-write
    STATUS      current
    DESCRIPTION
"
Enables logging to UNIX or Network Syslog.
  Needs the Perl module Sys::Syslog for local UNIX/LINUX or Windows Eventlog logging.
  If enabled and useSysSyslog is enabled and any of sysLogIp or sysLogPort is not set, local UNIX/LINUX or Windows Eventlog logging is used. It is not recommended to log to the Windows Eventlog!
"
    REFERENCE "SYSLOG Centralized Logging"
    DEFVAL { "" }
    ::= {Logging 668}

syncStatsysLog  OBJECT-TYPE
    SYNTAX      OCTET STRING
    MAX-ACCESS  read-only
    STATUS      current
    DESCRIPTION
"
synchronization status for sysLog
-1 - sysLog could not be synchronized
 0 - synchronization not configured
 1 - out of sync - running master mode
 2 - in sync - running  mastermode
 3 - in sync - running slave mode
 4 - in sync - running master mode (wait to reach state 2)
"
    ::= {sysLog 5}

syncStatStrsysLog  OBJECT-TYPE
    SYNTAX      OCTET STRING
    MAX-ACCESS  read-only
    STATUS      current
    DESCRIPTION
"
synchronization status line from file assp_sync.cfg for sysLog
 0 - synchronization not configured
 1 - out of sync - running master mode
 2 - in sync - running  mastermode
 3 - in sync - running slave mode
 4 - in sync - running master mode (wait to reach state 2)
"
    ::= {sysLog 6}

sysLogPort  OBJECT-TYPE
    SYNTAX      OCTET STRING
    MAX-ACCESS  read-write
    STATUS      current
    DESCRIPTION
"
Port for Network Syslog logging.
"
    REFERENCE "Syslog Port (UDP)"
    DEFVAL { "514" }
    ::= {Logging 669}

syncStatsysLogPort  OBJECT-TYPE
    SYNTAX      OCTET STRING
    MAX-ACCESS  read-only
    STATUS      current
    DESCRIPTION
"
synchronization status for sysLogPort
-1 - sysLogPort could not be synchronized
 0 - synchronization not configured
 1 - out of sync - running master mode
 2 - in sync - running  mastermode
 3 - in sync - running slave mode
 4 - in sync - running master mode (wait to reach state 2)
"
    ::= {sysLogPort 5}

syncStatStrsysLogPort  OBJECT-TYPE
    SYNTAX      OCTET STRING
    MAX-ACCESS  read-only
    STATUS      current
    DESCRIPTION
"
synchronization status line from file assp_sync.cfg for sysLogPort
 0 - synchronization not configured
 1 - out of sync - running master mode
 2 - in sync - running  mastermode
 3 - in sync - running slave mode
 4 - in sync - running master mode (wait to reach state 2)
"
    ::= {sysLogPort 6}

SysLogFac  OBJECT-TYPE
    SYNTAX      OCTET STRING
    MAX-ACCESS  read-write
    STATUS      current
    DESCRIPTION
"
Syslog Facility. Valid are kern, user, mail, daemon, auth, syslog, lpr, news, uucp, cron, authpriv, ftp, local0, local1, local2, local3, local4, local5, local6
"
    REFERENCE "Syslog Facility"
    DEFVAL { "mail" }
    ::= {Logging 670}

syncStatSysLogFac  OBJECT-TYPE
    SYNTAX      OCTET STRING
    MAX-ACCESS  read-only
    STATUS      current
    DESCRIPTION
"
synchronization status for SysLogFac
-1 - SysLogFac could not be synchronized
 0 - synchronization not configured
 1 - out of sync - running master mode
 2 - in sync - running  mastermode
 3 - in sync - running slave mode
 4 - in sync - running master mode (wait to reach state 2)
"
    ::= {SysLogFac 5}

syncStatStrSysLogFac  OBJECT-TYPE
    SYNTAX      OCTET STRING
    MAX-ACCESS  read-only
    STATUS      current
    DESCRIPTION
"
synchronization status line from file assp_sync.cfg for SysLogFac
 0 - synchronization not configured
 1 - out of sync - running master mode
 2 - in sync - running  mastermode
 3 - in sync - running slave mode
 4 - in sync - running master mode (wait to reach state 2)
"
    ::= {SysLogFac 6}

sysLogIp  OBJECT-TYPE
    SYNTAX      OCTET STRING
    MAX-ACCESS  read-write
    STATUS      current
    DESCRIPTION
"
IP Address or hostname of your Network Syslog Daemon for Syslog logging.
"
    REFERENCE "Syslog IP"
    DEFVAL { "" }
    ::= {Logging 671}

syncStatsysLogIp  OBJECT-TYPE
    SYNTAX      OCTET STRING
    MAX-ACCESS  read-only
    STATUS      current
    DESCRIPTION
"
synchronization status for sysLogIp
-1 - sysLogIp could not be synchronized
 0 - synchronization not configured
 1 - out of sync - running master mode
 2 - in sync - running  mastermode
 3 - in sync - running slave mode
 4 - in sync - running master mode (wait to reach state 2)
"
    ::= {sysLogIp 5}

syncStatStrsysLogIp  OBJECT-TYPE
    SYNTAX      OCTET STRING
    MAX-ACCESS  read-only
    STATUS      current
    DESCRIPTION
"
synchronization status line from file assp_sync.cfg for sysLogIp
 0 - synchronization not configured
 1 - out of sync - running master mode
 2 - in sync - running  mastermode
 3 - in sync - running slave mode
 4 - in sync - running master mode (wait to reach state 2)
"
    ::= {sysLogIp 6}

asspLog  OBJECT-TYPE
    SYNTAX      OCTET STRING
    MAX-ACCESS  read-write
    STATUS      current
    DESCRIPTION
"
ASSP manages local logging. The logs (logfile) are stored inside the directory where ASSP is installed.
"
    REFERENCE "ASSP local logging"
    DEFVAL { "1" }
    ::= {Logging 672}

syncStatasspLog  OBJECT-TYPE
    SYNTAX      OCTET STRING
    MAX-ACCESS  read-only
    STATUS      current
    DESCRIPTION
"
synchronization status for asspLog
-1 - asspLog could not be synchronized
 0 - synchronization not configured
 1 - out of sync - running master mode
 2 - in sync - running  mastermode
 3 - in sync - running slave mode
 4 - in sync - running master mode (wait to reach state 2)
"
    ::= {asspLog 5}

syncStatStrasspLog  OBJECT-TYPE
    SYNTAX      OCTET STRING
    MAX-ACCESS  read-only
    STATUS      current
    DESCRIPTION
"
synchronization status line from file assp_sync.cfg for asspLog
 0 - synchronization not configured
 1 - out of sync - running master mode
 2 - in sync - running  mastermode
 3 - in sync - running slave mode
 4 - in sync - running master mode (wait to reach state 2)
"
    ::= {asspLog 6}

LogRollDays  OBJECT-TYPE
    SYNTAX      OCTET STRING
    MAX-ACCESS  read-write
    STATUS      current
    DESCRIPTION
"
ASSP closes and renames the log file after this number of days. Leave this at the default value 1, if you use BlockReporting.
"
    REFERENCE "Roll the Logfile How Often?"
    DEFVAL { "1" }
    ::= {Logging 673}

syncStatLogRollDays  OBJECT-TYPE
    SYNTAX      OCTET STRING
    MAX-ACCESS  read-only
    STATUS      current
    DESCRIPTION
"
synchronization status for LogRollDays
-1 - LogRollDays could not be synchronized
 0 - synchronization not configured
 1 - out of sync - running master mode
 2 - in sync - running  mastermode
 3 - in sync - running slave mode
 4 - in sync - running master mode (wait to reach state 2)
"
    ::= {LogRollDays 5}

syncStatStrLogRollDays  OBJECT-TYPE
    SYNTAX      OCTET STRING
    MAX-ACCESS  read-only
    STATUS      current
    DESCRIPTION
"
synchronization status line from file assp_sync.cfg for LogRollDays
 0 - synchronization not configured
 1 - out of sync - running master mode
 2 - in sync - running  mastermode
 3 - in sync - running slave mode
 4 - in sync - running master mode (wait to reach state 2)
"
    ::= {LogRollDays 6}

LogNameDate  OBJECT-TYPE
    SYNTAX      OCTET STRING
    MAX-ACCESS  read-write
    STATUS      current
    DESCRIPTION
"
The standard name for the logfile is YY-MM-DD.maillog.txt, use this option to set it to your needs.
 possible values are:
 YY-MM-DD (default)
 YYYY-MM-DD
 MM-DD
"
    REFERENCE "LogName Date Format"
    DEFVAL { "YY-MM-DD" }
    ::= {Logging 674}

syncStatLogNameDate  OBJECT-TYPE
    SYNTAX      OCTET STRING
    MAX-ACCESS  read-only
    STATUS      current
    DESCRIPTION
"
synchronization status for LogNameDate
-1 - LogNameDate could not be synchronized
 0 - synchronization not configured
 1 - out of sync - running master mode
 2 - in sync - running  mastermode
 3 - in sync - running slave mode
 4 - in sync - running master mode (wait to reach state 2)
"
    ::= {LogNameDate 5}

syncStatStrLogNameDate  OBJECT-TYPE
    SYNTAX      OCTET STRING
    MAX-ACCESS  read-only
    STATUS      current
    DESCRIPTION
"
synchronization status line from file assp_sync.cfg for LogNameDate
 0 - synchronization not configured
 1 - out of sync - running master mode
 2 - in sync - running  mastermode
 3 - in sync - running slave mode
 4 - in sync - running master mode (wait to reach state 2)
"
    ::= {LogNameDate 6}

silent  OBJECT-TYPE
    SYNTAX      OCTET STRING
    MAX-ACCESS  read-write
    STATUS      current
    DESCRIPTION
"
Checked means don't print log messages to the console. AsADaemon overrides this.
"
    REFERENCE "Silent Mode"
    DEFVAL { "" }
    ::= {Logging 675}

syncStatsilent  OBJECT-TYPE
    SYNTAX      OCTET STRING
    MAX-ACCESS  read-only
    STATUS      current
    DESCRIPTION
"
synchronization status for silent
-1 - silent could not be synchronized
 0 - synchronization not configured
 1 - out of sync - running master mode
 2 - in sync - running  mastermode
 3 - in sync - running slave mode
 4 - in sync - running master mode (wait to reach state 2)
"
    ::= {silent 5}

syncStatStrsilent  OBJECT-TYPE
    SYNTAX      OCTET STRING
    MAX-ACCESS  read-only
    STATUS      current
    DESCRIPTION
"
synchronization status line from file assp_sync.cfg for silent
 0 - synchronization not configured
 1 - out of sync - running master mode
 2 - in sync - running  mastermode
 3 - in sync - running slave mode
 4 - in sync - running master mode (wait to reach state 2)
"
    ::= {silent 6}

debug  OBJECT-TYPE
    SYNTAX      OCTET STRING
    MAX-ACCESS  read-write
    STATUS      current
    DESCRIPTION
"
Checked sends debugging info to a .dbg file. Debug is enabled for all Threads, all the time! debugIP and debugRE will be ignored!
  Leave this unchecked unless there is a program error you are trying to track down.
"
    REFERENCE "General Debug Mode"
    DEFVAL { "" }
    ::= {Logging 676}

syncStatdebug  OBJECT-TYPE
    SYNTAX      OCTET STRING
    MAX-ACCESS  read-only
    STATUS      current
    DESCRIPTION
"
synchronization status for debug
-1 - debug could not be synchronized
 0 - synchronization not configured
 1 - out of sync - running master mode
 2 - in sync - running  mastermode
 3 - in sync - running slave mode
 4 - in sync - running master mode (wait to reach state 2)
"
    ::= {debug 5}

syncStatStrdebug  OBJECT-TYPE
    SYNTAX      OCTET STRING
    MAX-ACCESS  read-only
    STATUS      current
    DESCRIPTION
"
synchronization status line from file assp_sync.cfg for debug
 0 - synchronization not configured
 1 - out of sync - running master mode
 2 - in sync - running  mastermode
 3 - in sync - running slave mode
 4 - in sync - running master mode (wait to reach state 2)
"
    ::= {debug 6}

debugIP  OBJECT-TYPE
    SYNTAX      OCTET STRING
    MAX-ACCESS  read-write
    STATUS      current
    DESCRIPTION
"
Enter IP addresses that you want to be debugged, separated by pipes (|). The local and the remote IP of the connection will be checked!
  Not blank sends debugging info to a .dbg file. Leave this blank unless there is a program error you are trying to track down.
  This can be IP address of the SMTP service monitoring agent. For example:  127.0.0.1|172.16.
"
    REFERENCE "Debug these IPs*"
    DEFVAL { "" }
    ::= {Logging 677}

syncStatdebugIP  OBJECT-TYPE
    SYNTAX      OCTET STRING
    MAX-ACCESS  read-only
    STATUS      current
    DESCRIPTION
"
synchronization status for debugIP
-1 - debugIP could not be synchronized
 0 - synchronization not configured
 1 - out of sync - running master mode
 2 - in sync - running  mastermode
 3 - in sync - running slave mode
 4 - in sync - running master mode (wait to reach state 2)
"
    ::= {debugIP 5}

syncStatStrdebugIP  OBJECT-TYPE
    SYNTAX      OCTET STRING
    MAX-ACCESS  read-only
    STATUS      current
    DESCRIPTION
"
synchronization status line from file assp_sync.cfg for debugIP
 0 - synchronization not configured
 1 - out of sync - running master mode
 2 - in sync - running  mastermode
 3 - in sync - running slave mode
 4 - in sync - running master mode (wait to reach state 2)
"
    ::= {debugIP 6}

debugRe  OBJECT-TYPE
    SYNTAX      OCTET STRING
    MAX-ACCESS  read-write
    STATUS      current
    DESCRIPTION
"
Put anything here to identify messages that you want to be debugged.  Not blank sends debugging info to a .dbg file. Leave this blank unless there is a program error you are trying to track down.
"
    REFERENCE "Regular Expression to Identify Debug-Messages*"
    DEFVAL { "" }
    ::= {Logging 678}

syncStatdebugRe  OBJECT-TYPE
    SYNTAX      OCTET STRING
    MAX-ACCESS  read-only
    STATUS      current
    DESCRIPTION
"
synchronization status for debugRe
-1 - debugRe could not be synchronized
 0 - synchronization not configured
 1 - out of sync - running master mode
 2 - in sync - running  mastermode
 3 - in sync - running slave mode
 4 - in sync - running master mode (wait to reach state 2)
"
    ::= {debugRe 5}

syncStatStrdebugRe  OBJECT-TYPE
    SYNTAX      OCTET STRING
    MAX-ACCESS  read-only
    STATUS      current
    DESCRIPTION
"
synchronization status line from file assp_sync.cfg for debugRe
 0 - synchronization not configured
 1 - out of sync - running master mode
 2 - in sync - running  mastermode
 3 - in sync - running slave mode
 4 - in sync - running master mode (wait to reach state 2)
"
    ::= {debugRe 6}

debugCode  OBJECT-TYPE
    SYNTAX      OCTET STRING
    MAX-ACCESS  read-write
    STATUS      current
    DESCRIPTION
"
Put a code line here, to detect messages that you want to debug. The code line has to return 0 or 1. A return of 1 will switch on debug.
  for example:
  $Con{$fh}->{isbounce}
  This code line will switch on debug for all bounce messages.
  ($Con{$fh}->{relayok} && $Con{$fh}->{isbounce})
  This code line will switch on debug for all outgoing bounce messages.
  ($Con{$fh}->{ispip} && $Con{$fh}->{cip} =~ /^193\.2\.1\./)
  This code line will switch on debug if the messages is from ISP and the IP of the server that was connected to the ISP begins with 193.2.1. .
  To use this option, you need to know the internal ASSP variables and their usage!
"
    REFERENCE "Run this Code to switch on Debug"
    DEFVAL { "" }
    ::= {Logging 679}

syncStatdebugCode  OBJECT-TYPE
    SYNTAX      OCTET STRING
    MAX-ACCESS  read-only
    STATUS      current
    DESCRIPTION
"
synchronization status for debugCode
-1 - debugCode could not be synchronized
 0 - synchronization not configured
 1 - out of sync - running master mode
 2 - in sync - running  mastermode
 3 - in sync - running slave mode
 4 - in sync - running master mode (wait to reach state 2)
"
    ::= {debugCode 5}

syncStatStrdebugCode  OBJECT-TYPE
    SYNTAX      OCTET STRING
    MAX-ACCESS  read-only
    STATUS      current
    DESCRIPTION
"
synchronization status line from file assp_sync.cfg for debugCode
 0 - synchronization not configured
 1 - out of sync - running master mode
 2 - in sync - running  mastermode
 3 - in sync - running slave mode
 4 - in sync - running master mode (wait to reach state 2)
"
    ::= {debugCode 6}

debugNoWriteBody  OBJECT-TYPE
    SYNTAX      OCTET STRING
    MAX-ACCESS  read-write
    STATUS      current
    DESCRIPTION
"
If selected, the sent message body data will not be written to the debug file.
"
    REFERENCE "Do not write Body to Debug"
    DEFVAL { "" }
    ::= {Logging 680}

syncStatdebugNoWriteBody  OBJECT-TYPE
    SYNTAX      OCTET STRING
    MAX-ACCESS  read-only
    STATUS      current
    DESCRIPTION
"
synchronization status for debugNoWriteBody
-1 - debugNoWriteBody could not be synchronized
 0 - synchronization not configured
 1 - out of sync - running master mode
 2 - in sync - running  mastermode
 3 - in sync - running slave mode
 4 - in sync - running master mode (wait to reach state 2)
"
    ::= {debugNoWriteBody 5}

syncStatStrdebugNoWriteBody  OBJECT-TYPE
    SYNTAX      OCTET STRING
    MAX-ACCESS  read-only
    STATUS      current
    DESCRIPTION
"
synchronization status line from file assp_sync.cfg for debugNoWriteBody
 0 - synchronization not configured
 1 - out of sync - running master mode
 2 - in sync - running  mastermode
 3 - in sync - running slave mode
 4 - in sync - running master mode (wait to reach state 2)
"
    ::= {debugNoWriteBody 6}

DataBaseDebug  OBJECT-TYPE
    SYNTAX      OCTET STRING
    MAX-ACCESS  read-write
    STATUS      current
    DESCRIPTION
"
Select to debug the database connections!
"
    REFERENCE "Database Connection Debug Mode"
    DEFVAL { "" }
    ::= {Logging 681}

syncStatDataBaseDebug  OBJECT-TYPE
    SYNTAX      OCTET STRING
    MAX-ACCESS  read-only
    STATUS      current
    DESCRIPTION
"
synchronization status for DataBaseDebug
-1 - DataBaseDebug could not be synchronized
 0 - synchronization not configured
 1 - out of sync - running master mode
 2 - in sync - running  mastermode
 3 - in sync - running slave mode
 4 - in sync - running master mode (wait to reach state 2)
"
    ::= {DataBaseDebug 5}

syncStatStrDataBaseDebug  OBJECT-TYPE
    SYNTAX      OCTET STRING
    MAX-ACCESS  read-only
    STATUS      current
    DESCRIPTION
"
synchronization status line from file assp_sync.cfg for DataBaseDebug
 0 - synchronization not configured
 1 - out of sync - running master mode
 2 - in sync - running  mastermode
 3 - in sync - running slave mode
 4 - in sync - running master mode (wait to reach state 2)
"
    ::= {DataBaseDebug 6}

ConTimeOutDebug  OBJECT-TYPE
    SYNTAX      OCTET STRING
    MAX-ACCESS  read-write
    STATUS      current
    DESCRIPTION
"
Select to debug SMTP connections that are running in to timeout!
"
    REFERENCE "Connection Timeout Debug Mode"
    DEFVAL { "" }
    ::= {Logging 682}

syncStatConTimeOutDebug  OBJECT-TYPE
    SYNTAX      OCTET STRING
    MAX-ACCESS  read-only
    STATUS      current
    DESCRIPTION
"
synchronization status for ConTimeOutDebug
-1 - ConTimeOutDebug could not be synchronized
 0 - synchronization not configured
 1 - out of sync - running master mode
 2 - in sync - running  mastermode
 3 - in sync - running slave mode
 4 - in sync - running master mode (wait to reach state 2)
"
    ::= {ConTimeOutDebug 5}

syncStatStrConTimeOutDebug  OBJECT-TYPE
    SYNTAX      OCTET STRING
    MAX-ACCESS  read-only
    STATUS      current
    DESCRIPTION
"
synchronization status line from file assp_sync.cfg for ConTimeOutDebug
 0 - synchronization not configured
 1 - out of sync - running master mode
 2 - in sync - running  mastermode
 3 - in sync - running slave mode
 4 - in sync - running master mode (wait to reach state 2)
"
    ::= {ConTimeOutDebug 6}

IgnoreMIMEErrors  OBJECT-TYPE
    SYNTAX      OCTET STRING
    MAX-ACCESS  read-write
    STATUS      current
    DESCRIPTION
"
If selected - Errors, based on wrong email MIME contents, will not be written to log!
"
    REFERENCE "Ignore MIME Errors"
    DEFVAL { "1" }
    ::= {Logging 683}

syncStatIgnoreMIMEErrors  OBJECT-TYPE
    SYNTAX      OCTET STRING
    MAX-ACCESS  read-only
    STATUS      current
    DESCRIPTION
"
synchronization status for IgnoreMIMEErrors
-1 - IgnoreMIMEErrors could not be synchronized
 0 - synchronization not configured
 1 - out of sync - running master mode
 2 - in sync - running  mastermode
 3 - in sync - running slave mode
 4 - in sync - running master mode (wait to reach state 2)
"
    ::= {IgnoreMIMEErrors 5}

syncStatStrIgnoreMIMEErrors  OBJECT-TYPE
    SYNTAX      OCTET STRING
    MAX-ACCESS  read-only
    STATUS      current
    DESCRIPTION
"
synchronization status line from file assp_sync.cfg for IgnoreMIMEErrors
 0 - synchronization not configured
 1 - out of sync - running master mode
 2 - in sync - running  mastermode
 3 - in sync - running slave mode
 4 - in sync - running master mode (wait to reach state 2)
"
    ::= {IgnoreMIMEErrors 6}

noLog  OBJECT-TYPE
    SYNTAX      OCTET STRING
    MAX-ACCESS  read-write
    STATUS      current
    DESCRIPTION
"
Enter IP addresses that you don't want to be logged, separated by pipes (|). The local and the remote IP of the connection will be checked!
  This can be IP address of the SMTP service monitoring agent. For example:  127.0.0.1|172.16.
"
    REFERENCE "Don't Log these IPs*"
    DEFVAL { "" }
    ::= {Logging 684}

syncStatnoLog  OBJECT-TYPE
    SYNTAX      OCTET STRING
    MAX-ACCESS  read-only
    STATUS      current
    DESCRIPTION
"
synchronization status for noLog
-1 - noLog could not be synchronized
 0 - synchronization not configured
 1 - out of sync - running master mode
 2 - in sync - running  mastermode
 3 - in sync - running slave mode
 4 - in sync - running master mode (wait to reach state 2)
"
    ::= {noLog 5}

syncStatStrnoLog  OBJECT-TYPE
    SYNTAX      OCTET STRING
    MAX-ACCESS  read-only
    STATUS      current
    DESCRIPTION
"
synchronization status line from file assp_sync.cfg for noLog
 0 - synchronization not configured
 1 - out of sync - running master mode
 2 - in sync - running  mastermode
 3 - in sync - running slave mode
 4 - in sync - running master mode (wait to reach state 2)
"
    ::= {noLog 6}

noLogRe  OBJECT-TYPE
    SYNTAX      OCTET STRING
    MAX-ACCESS  read-write
    STATUS      current
    DESCRIPTION
"
Put anything here to identify messages that you don't want to be logged.
"
    REFERENCE "Regular Expression to Identify NoLog-Messages*"
    DEFVAL { "" }
    ::= {Logging 685}

syncStatnoLogRe  OBJECT-TYPE
    SYNTAX      OCTET STRING
    MAX-ACCESS  read-only
    STATUS      current
    DESCRIPTION
"
synchronization status for noLogRe
-1 - noLogRe could not be synchronized
 0 - synchronization not configured
 1 - out of sync - running master mode
 2 - in sync - running  mastermode
 3 - in sync - running slave mode
 4 - in sync - running master mode (wait to reach state 2)
"
    ::= {noLogRe 5}

syncStatStrnoLogRe  OBJECT-TYPE
    SYNTAX      OCTET STRING
    MAX-ACCESS  read-only
    STATUS      current
    DESCRIPTION
"
synchronization status line from file assp_sync.cfg for noLogRe
 0 - synchronization not configured
 1 - out of sync - running master mode
 2 - in sync - running  mastermode
 3 - in sync - running slave mode
 4 - in sync - running master mode (wait to reach state 2)
"
    ::= {noLogRe 6}

allLogRe  OBJECT-TYPE
    SYNTAX      OCTET STRING
    MAX-ACCESS  read-write
    STATUS      current
    DESCRIPTION
"
Put anything here to identify messages from/to addresses you want to look at for problem solving. Messages identified will also be set to StoreCompleteMail.
"
    REFERENCE "Regular Expression to Identify Messages from/to Problematic Addresses *"
    DEFVAL { "" }
    ::= {Logging 686}

syncStatallLogRe  OBJECT-TYPE
    SYNTAX      OCTET STRING
    MAX-ACCESS  read-only
    STATUS      current
    DESCRIPTION
"
synchronization status for allLogRe
-1 - allLogRe could not be synchronized
 0 - synchronization not configured
 1 - out of sync - running master mode
 2 - in sync - running  mastermode
 3 - in sync - running slave mode
 4 - in sync - running master mode (wait to reach state 2)
"
    ::= {allLogRe 5}

syncStatStrallLogRe  OBJECT-TYPE
    SYNTAX      OCTET STRING
    MAX-ACCESS  read-only
    STATUS      current
    DESCRIPTION
"
synchronization status line from file assp_sync.cfg for allLogRe
 0 - synchronization not configured
 1 - out of sync - running master mode
 2 - in sync - running  mastermode
 3 - in sync - running slave mode
 4 - in sync - running master mode (wait to reach state 2)
"
    ::= {allLogRe 6}

ConnectionLog  OBJECT-TYPE
    SYNTAX      OCTET STRING
    MAX-ACCESS  read-write
    STATUS      current
    DESCRIPTION
"

"
    REFERENCE "Connections Logging"
    DEFVAL { "0" }
    ::= {Logging 687}

syncStatConnectionLog  OBJECT-TYPE
    SYNTAX      OCTET STRING
    MAX-ACCESS  read-only
    STATUS      current
    DESCRIPTION
"
synchronization status for ConnectionLog
-1 - ConnectionLog could not be synchronized
 0 - synchronization not configured
 1 - out of sync - running master mode
 2 - in sync - running  mastermode
 3 - in sync - running slave mode
 4 - in sync - running master mode (wait to reach state 2)
"
    ::= {ConnectionLog 5}

syncStatStrConnectionLog  OBJECT-TYPE
    SYNTAX      OCTET STRING
    MAX-ACCESS  read-only
    STATUS      current
    DESCRIPTION
"
synchronization status line from file assp_sync.cfg for ConnectionLog
 0 - synchronization not configured
 1 - out of sync - running master mode
 2 - in sync - running  mastermode
 3 - in sync - running slave mode
 4 - in sync - running master mode (wait to reach state 2)
"
    ::= {ConnectionLog 6}

SessionLog  OBJECT-TYPE
    SYNTAX      OCTET STRING
    MAX-ACCESS  read-write
    STATUS      current
    DESCRIPTION
"

"
    REFERENCE "Session Limit Logging"
    DEFVAL { "1" }
    ::= {Logging 688}

syncStatSessionLog  OBJECT-TYPE
    SYNTAX      OCTET STRING
    MAX-ACCESS  read-only
    STATUS      current
    DESCRIPTION
"
synchronization status for SessionLog
-1 - SessionLog could not be synchronized
 0 - synchronization not configured
 1 - out of sync - running master mode
 2 - in sync - running  mastermode
 3 - in sync - running slave mode
 4 - in sync - running master mode (wait to reach state 2)
"
    ::= {SessionLog 5}

syncStatStrSessionLog  OBJECT-TYPE
    SYNTAX      OCTET STRING
    MAX-ACCESS  read-only
    STATUS      current
    DESCRIPTION
"
synchronization status line from file assp_sync.cfg for SessionLog
 0 - synchronization not configured
 1 - out of sync - running master mode
 2 - in sync - running  mastermode
 3 - in sync - running slave mode
 4 - in sync - running master mode (wait to reach state 2)
"
    ::= {SessionLog 6}

denySMTPLog  OBJECT-TYPE
    SYNTAX      OCTET STRING
    MAX-ACCESS  read-write
    STATUS      current
    DESCRIPTION
"

"
    REFERENCE "Enables Logging for 'Deny SMTP Connections From'"
    DEFVAL { "1" }
    ::= {Logging 689}

syncStatdenySMTPLog  OBJECT-TYPE
    SYNTAX      OCTET STRING
    MAX-ACCESS  read-only
    STATUS      current
    DESCRIPTION
"
synchronization status for denySMTPLog
-1 - denySMTPLog could not be synchronized
 0 - synchronization not configured
 1 - out of sync - running master mode
 2 - in sync - running  mastermode
 3 - in sync - running slave mode
 4 - in sync - running master mode (wait to reach state 2)
"
    ::= {denySMTPLog 5}

syncStatStrdenySMTPLog  OBJECT-TYPE
    SYNTAX      OCTET STRING
    MAX-ACCESS  read-only
    STATUS      current
    DESCRIPTION
"
synchronization status line from file assp_sync.cfg for denySMTPLog
 0 - synchronization not configured
 1 - out of sync - running master mode
 2 - in sync - running  mastermode
 3 - in sync - running slave mode
 4 - in sync - running master mode (wait to reach state 2)
"
    ::= {denySMTPLog 6}

RWLLog  OBJECT-TYPE
    SYNTAX      OCTET STRING
    MAX-ACCESS  read-write
    STATUS      current
    DESCRIPTION
"

"
    REFERENCE "Enable RWL logging"
    DEFVAL { "1" }
    ::= {Logging 690}

syncStatRWLLog  OBJECT-TYPE
    SYNTAX      OCTET STRING
    MAX-ACCESS  read-only
    STATUS      current
    DESCRIPTION
"
synchronization status for RWLLog
-1 - RWLLog could not be synchronized
 0 - synchronization not configured
 1 - out of sync - running master mode
 2 - in sync - running  mastermode
 3 - in sync - running slave mode
 4 - in sync - running master mode (wait to reach state 2)
"
    ::= {RWLLog 5}

syncStatStrRWLLog  OBJECT-TYPE
    SYNTAX      OCTET STRING
    MAX-ACCESS  read-only
    STATUS      current
    DESCRIPTION
"
synchronization status line from file assp_sync.cfg for RWLLog
 0 - synchronization not configured
 1 - out of sync - running master mode
 2 - in sync - running  mastermode
 3 - in sync - running slave mode
 4 - in sync - running master mode (wait to reach state 2)
"
    ::= {RWLLog 6}

LDAPLog  OBJECT-TYPE
    SYNTAX      OCTET STRING
    MAX-ACCESS  read-write
    STATUS      current
    DESCRIPTION
"
ATTENTION: diagnostic will possibly write credital information in clear text to the log!
"
    REFERENCE "Enable LDAP logging"
    DEFVAL { "1" }
    ::= {Logging 691}

syncStatLDAPLog  OBJECT-TYPE
    SYNTAX      OCTET STRING
    MAX-ACCESS  read-only
    STATUS      current
    DESCRIPTION
"
synchronization status for LDAPLog
-1 - LDAPLog could not be synchronized
 0 - synchronization not configured
 1 - out of sync - running master mode
 2 - in sync - running  mastermode
 3 - in sync - running slave mode
 4 - in sync - running master mode (wait to reach state 2)
"
    ::= {LDAPLog 5}

syncStatStrLDAPLog  OBJECT-TYPE
    SYNTAX      OCTET STRING
    MAX-ACCESS  read-only
    STATUS      current
    DESCRIPTION
"
synchronization status line from file assp_sync.cfg for LDAPLog
 0 - synchronization not configured
 1 - out of sync - running master mode
 2 - in sync - running  mastermode
 3 - in sync - running slave mode
 4 - in sync - running master mode (wait to reach state 2)
"
    ::= {LDAPLog 6}

VRFYLog  OBJECT-TYPE
    SYNTAX      OCTET STRING
    MAX-ACCESS  read-write
    STATUS      current
    DESCRIPTION
"

"
    REFERENCE "Enable VRFY logging"
    DEFVAL { "1" }
    ::= {Logging 692}

syncStatVRFYLog  OBJECT-TYPE
    SYNTAX      OCTET STRING
    MAX-ACCESS  read-only
    STATUS      current
    DESCRIPTION
"
synchronization status for VRFYLog
-1 - VRFYLog could not be synchronized
 0 - synchronization not configured
 1 - out of sync - running master mode
 2 - in sync - running  mastermode
 3 - in sync - running slave mode
 4 - in sync - running master mode (wait to reach state 2)
"
    ::= {VRFYLog 5}

syncStatStrVRFYLog  OBJECT-TYPE
    SYNTAX      OCTET STRING
    MAX-ACCESS  read-only
    STATUS      current
    DESCRIPTION
"
synchronization status line from file assp_sync.cfg for VRFYLog
 0 - synchronization not configured
 1 - out of sync - running master mode
 2 - in sync - running  mastermode
 3 - in sync - running slave mode
 4 - in sync - running master mode (wait to reach state 2)
"
    ::= {VRFYLog 6}

ValidateUserLog  OBJECT-TYPE
    SYNTAX      OCTET STRING
    MAX-ACCESS  read-write
    STATUS      current
    DESCRIPTION
"

"
    REFERENCE "Enable User Validation logging"
    DEFVAL { "1" }
    ::= {Logging 693}

syncStatValidateUserLog  OBJECT-TYPE
    SYNTAX      OCTET STRING
    MAX-ACCESS  read-only
    STATUS      current
    DESCRIPTION
"
synchronization status for ValidateUserLog
-1 - ValidateUserLog could not be synchronized
 0 - synchronization not configured
 1 - out of sync - running master mode
 2 - in sync - running  mastermode
 3 - in sync - running slave mode
 4 - in sync - running master mode (wait to reach state 2)
"
    ::= {ValidateUserLog 5}

syncStatStrValidateUserLog  OBJECT-TYPE
    SYNTAX      OCTET STRING
    MAX-ACCESS  read-only
    STATUS      current
    DESCRIPTION
"
synchronization status line from file assp_sync.cfg for ValidateUserLog
 0 - synchronization not configured
 1 - out of sync - running master mode
 2 - in sync - running  mastermode
 3 - in sync - running slave mode
 4 - in sync - running master mode (wait to reach state 2)
"
    ::= {ValidateUserLog 6}

PenaltyLog  OBJECT-TYPE
    SYNTAX      OCTET STRING
    MAX-ACCESS  read-write
    STATUS      current
    DESCRIPTION
"

"
    REFERENCE "Enable PenaltyBox logging"
    DEFVAL { "1" }
    ::= {Logging 694}

syncStatPenaltyLog  OBJECT-TYPE
    SYNTAX      OCTET STRING
    MAX-ACCESS  read-only
    STATUS      current
    DESCRIPTION
"
synchronization status for PenaltyLog
-1 - PenaltyLog could not be synchronized
 0 - synchronization not configured
 1 - out of sync - running master mode
 2 - in sync - running  mastermode
 3 - in sync - running slave mode
 4 - in sync - running master mode (wait to reach state 2)
"
    ::= {PenaltyLog 5}

syncStatStrPenaltyLog  OBJECT-TYPE
    SYNTAX      OCTET STRING
    MAX-ACCESS  read-only
    STATUS      current
    DESCRIPTION
"
synchronization status line from file assp_sync.cfg for PenaltyLog
 0 - synchronization not configured
 1 - out of sync - running master mode
 2 - in sync - running  mastermode
 3 - in sync - running slave mode
 4 - in sync - running master mode (wait to reach state 2)
"
    ::= {PenaltyLog 6}

PenaltyExtremeLog  OBJECT-TYPE
    SYNTAX      OCTET STRING
    MAX-ACCESS  read-write
    STATUS      current
    DESCRIPTION
"

"
    REFERENCE "Enable PenaltyBox logging"
    DEFVAL { "1" }
    ::= {Logging 695}

syncStatPenaltyExtremeLog  OBJECT-TYPE
    SYNTAX      OCTET STRING
    MAX-ACCESS  read-only
    STATUS      current
    DESCRIPTION
"
synchronization status for PenaltyExtremeLog
-1 - PenaltyExtremeLog could not be synchronized
 0 - synchronization not configured
 1 - out of sync - running master mode
 2 - in sync - running  mastermode
 3 - in sync - running slave mode
 4 - in sync - running master mode (wait to reach state 2)
"
    ::= {PenaltyExtremeLog 5}

syncStatStrPenaltyExtremeLog  OBJECT-TYPE
    SYNTAX      OCTET STRING
    MAX-ACCESS  read-only
    STATUS      current
    DESCRIPTION
"
synchronization status line from file assp_sync.cfg for PenaltyExtremeLog
 0 - synchronization not configured
 1 - out of sync - running master mode
 2 - in sync - running  mastermode
 3 - in sync - running slave mode
 4 - in sync - running master mode (wait to reach state 2)
"
    ::= {PenaltyExtremeLog 6}

MessageLog  OBJECT-TYPE
    SYNTAX      OCTET STRING
    MAX-ACCESS  read-write
    STATUS      current
    DESCRIPTION
"

"
    REFERENCE "Enable Message Scoring logging"
    DEFVAL { "1" }
    ::= {Logging 696}

syncStatMessageLog  OBJECT-TYPE
    SYNTAX      OCTET STRING
    MAX-ACCESS  read-only
    STATUS      current
    DESCRIPTION
"
synchronization status for MessageLog
-1 - MessageLog could not be synchronized
 0 - synchronization not configured
 1 - out of sync - running master mode
 2 - in sync - running  mastermode
 3 - in sync - running slave mode
 4 - in sync - running master mode (wait to reach state 2)
"
    ::= {MessageLog 5}

syncStatStrMessageLog  OBJECT-TYPE
    SYNTAX      OCTET STRING
    MAX-ACCESS  read-only
    STATUS      current
    DESCRIPTION
"
synchronization status line from file assp_sync.cfg for MessageLog
 0 - synchronization not configured
 1 - out of sync - running master mode
 2 - in sync - running  mastermode
 3 - in sync - running slave mode
 4 - in sync - running master mode (wait to reach state 2)
"
    ::= {MessageLog 6}

MSGIDsigLog  OBJECT-TYPE
    SYNTAX      OCTET STRING
    MAX-ACCESS  read-write
    STATUS      current
    DESCRIPTION
"

"
    REFERENCE "Enable Message-ID signing logging"
    DEFVAL { "1" }
    ::= {Logging 697}

syncStatMSGIDsigLog  OBJECT-TYPE
    SYNTAX      OCTET STRING
    MAX-ACCESS  read-only
    STATUS      current
    DESCRIPTION
"
synchronization status for MSGIDsigLog
-1 - MSGIDsigLog could not be synchronized
 0 - synchronization not configured
 1 - out of sync - running master mode
 2 - in sync - running  mastermode
 3 - in sync - running slave mode
 4 - in sync - running master mode (wait to reach state 2)
"
    ::= {MSGIDsigLog 5}

syncStatStrMSGIDsigLog  OBJECT-TYPE
    SYNTAX      OCTET STRING
    MAX-ACCESS  read-only
    STATUS      current
    DESCRIPTION
"
synchronization status line from file assp_sync.cfg for MSGIDsigLog
 0 - synchronization not configured
 1 - out of sync - running master mode
 2 - in sync - running  mastermode
 3 - in sync - running slave mode
 4 - in sync - running master mode (wait to reach state 2)
"
    ::= {MSGIDsigLog 6}

BacksctrLog  OBJECT-TYPE
    SYNTAX      OCTET STRING
    MAX-ACCESS  read-write
    STATUS      current
    DESCRIPTION
"

"
    REFERENCE "Enable DNS-Backscatter detection logging"
    DEFVAL { "1" }
    ::= {Logging 698}

syncStatBacksctrLog  OBJECT-TYPE
    SYNTAX      OCTET STRING
    MAX-ACCESS  read-only
    STATUS      current
    DESCRIPTION
"
synchronization status for BacksctrLog
-1 - BacksctrLog could not be synchronized
 0 - synchronization not configured
 1 - out of sync - running master mode
 2 - in sync - running  mastermode
 3 - in sync - running slave mode
 4 - in sync - running master mode (wait to reach state 2)
"
    ::= {BacksctrLog 5}

syncStatStrBacksctrLog  OBJECT-TYPE
    SYNTAX      OCTET STRING
    MAX-ACCESS  read-only
    STATUS      current
    DESCRIPTION
"
synchronization status line from file assp_sync.cfg for BacksctrLog
 0 - synchronization not configured
 1 - out of sync - running master mode
 2 - in sync - running  mastermode
 3 - in sync - running slave mode
 4 - in sync - running master mode (wait to reach state 2)
"
    ::= {BacksctrLog 6}

BATVLog  OBJECT-TYPE
    SYNTAX      OCTET STRING
    MAX-ACCESS  read-write
    STATUS      current
    DESCRIPTION
"

"
    REFERENCE "Enable BATV logging"
    DEFVAL { "1" }
    ::= {Logging 699}

syncStatBATVLog  OBJECT-TYPE
    SYNTAX      OCTET STRING
    MAX-ACCESS  read-only
    STATUS      current
    DESCRIPTION
"
synchronization status for BATVLog
-1 - BATVLog could not be synchronized
 0 - synchronization not configured
 1 - out of sync - running master mode
 2 - in sync - running  mastermode
 3 - in sync - running slave mode
 4 - in sync - running master mode (wait to reach state 2)
"
    ::= {BATVLog 5}

syncStatStrBATVLog  OBJECT-TYPE
    SYNTAX      OCTET STRING
    MAX-ACCESS  read-only
    STATUS      current
    DESCRIPTION
"
synchronization status line from file assp_sync.cfg for BATVLog
 0 - synchronization not configured
 1 - out of sync - running master mode
 2 - in sync - running  mastermode
 3 - in sync - running slave mode
 4 - in sync - running master mode (wait to reach state 2)
"
    ::= {BATVLog 6}

ValidateSenderLog  OBJECT-TYPE
    SYNTAX      OCTET STRING
    MAX-ACCESS  read-write
    STATUS      current
    DESCRIPTION
"

"
    REFERENCE "Enable Validate Sender Logging"
    DEFVAL { "1" }
    ::= {Logging 700}

syncStatValidateSenderLog  OBJECT-TYPE
    SYNTAX      OCTET STRING
    MAX-ACCESS  read-only
    STATUS      current
    DESCRIPTION
"
synchronization status for ValidateSenderLog
-1 - ValidateSenderLog could not be synchronized
 0 - synchronization not configured
 1 - out of sync - running master mode
 2 - in sync - running  mastermode
 3 - in sync - running slave mode
 4 - in sync - running master mode (wait to reach state 2)
"
    ::= {ValidateSenderLog 5}

syncStatStrValidateSenderLog  OBJECT-TYPE
    SYNTAX      OCTET STRING
    MAX-ACCESS  read-only
    STATUS      current
    DESCRIPTION
"
synchronization status line from file assp_sync.cfg for ValidateSenderLog
 0 - synchronization not configured
 1 - out of sync - running master mode
 2 - in sync - running  mastermode
 3 - in sync - running slave mode
 4 - in sync - running master mode (wait to reach state 2)
"
    ::= {ValidateSenderLog 6}

SenderBaseLog  OBJECT-TYPE
    SYNTAX      OCTET STRING
    MAX-ACCESS  read-write
    STATUS      current
    DESCRIPTION
"

"
    REFERENCE "Enable SenderBase Logging"
    DEFVAL { "1" }
    ::= {Logging 701}

syncStatSenderBaseLog  OBJECT-TYPE
    SYNTAX      OCTET STRING
    MAX-ACCESS  read-only
    STATUS      current
    DESCRIPTION
"
synchronization status for SenderBaseLog
-1 - SenderBaseLog could not be synchronized
 0 - synchronization not configured
 1 - out of sync - running master mode
 2 - in sync - running  mastermode
 3 - in sync - running slave mode
 4 - in sync - running master mode (wait to reach state 2)
"
    ::= {SenderBaseLog 5}

syncStatStrSenderBaseLog  OBJECT-TYPE
    SYNTAX      OCTET STRING
    MAX-ACCESS  read-only
    STATUS      current
    DESCRIPTION
"
synchronization status line from file assp_sync.cfg for SenderBaseLog
 0 - synchronization not configured
 1 - out of sync - running master mode
 2 - in sync - running  mastermode
 3 - in sync - running slave mode
 4 - in sync - running master mode (wait to reach state 2)
"
    ::= {SenderBaseLog 6}

DelayLog  OBJECT-TYPE
    SYNTAX      OCTET STRING
    MAX-ACCESS  read-write
    STATUS      current
    DESCRIPTION
"

"
    REFERENCE "Enable Greylisting/Delaying logging"
    DEFVAL { "1" }
    ::= {Logging 702}

syncStatDelayLog  OBJECT-TYPE
    SYNTAX      OCTET STRING
    MAX-ACCESS  read-only
    STATUS      current
    DESCRIPTION
"
synchronization status for DelayLog
-1 - DelayLog could not be synchronized
 0 - synchronization not configured
 1 - out of sync - running master mode
 2 - in sync - running  mastermode
 3 - in sync - running slave mode
 4 - in sync - running master mode (wait to reach state 2)
"
    ::= {DelayLog 5}

syncStatStrDelayLog  OBJECT-TYPE
    SYNTAX      OCTET STRING
    MAX-ACCESS  read-only
    STATUS      current
    DESCRIPTION
"
synchronization status line from file assp_sync.cfg for DelayLog
 0 - synchronization not configured
 1 - out of sync - running master mode
 2 - in sync - running  mastermode
 3 - in sync - running slave mode
 4 - in sync - running master mode (wait to reach state 2)
"
    ::= {DelayLog 6}

BombLog  OBJECT-TYPE
    SYNTAX      OCTET STRING
    MAX-ACCESS  read-write
    STATUS      current
    DESCRIPTION
"
If set to verbose, the reporting to the logfile and the X-ASSP- scoring header will show the complete list of all hits. Otherwise only the highest match will be shown.
"
    REFERENCE "Enable Bomb logging"
    DEFVAL { "1" }
    ::= {Logging 703}

syncStatBombLog  OBJECT-TYPE
    SYNTAX      OCTET STRING
    MAX-ACCESS  read-only
    STATUS      current
    DESCRIPTION
"
synchronization status for BombLog
-1 - BombLog could not be synchronized
 0 - synchronization not configured
 1 - out of sync - running master mode
 2 - in sync - running  mastermode
 3 - in sync - running slave mode
 4 - in sync - running master mode (wait to reach state 2)
"
    ::= {BombLog 5}

syncStatStrBombLog  OBJECT-TYPE
    SYNTAX      OCTET STRING
    MAX-ACCESS  read-only
    STATUS      current
    DESCRIPTION
"
synchronization status line from file assp_sync.cfg for BombLog
 0 - synchronization not configured
 1 - out of sync - running master mode
 2 - in sync - running  mastermode
 3 - in sync - running slave mode
 4 - in sync - running master mode (wait to reach state 2)
"
    ::= {BombLog 6}

AttachmentLog  OBJECT-TYPE
    SYNTAX      OCTET STRING
    MAX-ACCESS  read-write
    STATUS      current
    DESCRIPTION
"

"
    REFERENCE "Enable Attachment logging"
    DEFVAL { "1" }
    ::= {Logging 704}

syncStatAttachmentLog  OBJECT-TYPE
    SYNTAX      OCTET STRING
    MAX-ACCESS  read-only
    STATUS      current
    DESCRIPTION
"
synchronization status for AttachmentLog
-1 - AttachmentLog could not be synchronized
 0 - synchronization not configured
 1 - out of sync - running master mode
 2 - in sync - running  mastermode
 3 - in sync - running slave mode
 4 - in sync - running master mode (wait to reach state 2)
"
    ::= {AttachmentLog 5}

syncStatStrAttachmentLog  OBJECT-TYPE
    SYNTAX      OCTET STRING
    MAX-ACCESS  read-only
    STATUS      current
    DESCRIPTION
"
synchronization status line from file assp_sync.cfg for AttachmentLog
 0 - synchronization not configured
 1 - out of sync - running master mode
 2 - in sync - running  mastermode
 3 - in sync - running slave mode
 4 - in sync - running master mode (wait to reach state 2)
"
    ::= {AttachmentLog 6}

SPFLog  OBJECT-TYPE
    SYNTAX      OCTET STRING
    MAX-ACCESS  read-write
    STATUS      current
    DESCRIPTION
"

"
    REFERENCE "Enable SPF logging"
    DEFVAL { "1" }
    ::= {Logging 705}

syncStatSPFLog  OBJECT-TYPE
    SYNTAX      OCTET STRING
    MAX-ACCESS  read-only
    STATUS      current
    DESCRIPTION
"
synchronization status for SPFLog
-1 - SPFLog could not be synchronized
 0 - synchronization not configured
 1 - out of sync - running master mode
 2 - in sync - running  mastermode
 3 - in sync - running slave mode
 4 - in sync - running master mode (wait to reach state 2)
"
    ::= {SPFLog 5}

syncStatStrSPFLog  OBJECT-TYPE
    SYNTAX      OCTET STRING
    MAX-ACCESS  read-only
    STATUS      current
    DESCRIPTION
"
synchronization status line from file assp_sync.cfg for SPFLog
 0 - synchronization not configured
 1 - out of sync - running master mode
 2 - in sync - running  mastermode
 3 - in sync - running slave mode
 4 - in sync - running master mode (wait to reach state 2)
"
    ::= {SPFLog 6}

RBLLog  OBJECT-TYPE
    SYNTAX      OCTET STRING
    MAX-ACCESS  read-write
    STATUS      current
    DESCRIPTION
"

"
    REFERENCE "Enable DNSBL logging"
    DEFVAL { "1" }
    ::= {Logging 706}

syncStatRBLLog  OBJECT-TYPE
    SYNTAX      OCTET STRING
    MAX-ACCESS  read-only
    STATUS      current
    DESCRIPTION
"
synchronization status for RBLLog
-1 - RBLLog could not be synchronized
 0 - synchronization not configured
 1 - out of sync - running master mode
 2 - in sync - running  mastermode
 3 - in sync - running slave mode
 4 - in sync - running master mode (wait to reach state 2)
"
    ::= {RBLLog 5}

syncStatStrRBLLog  OBJECT-TYPE
    SYNTAX      OCTET STRING
    MAX-ACCESS  read-only
    STATUS      current
    DESCRIPTION
"
synchronization status line from file assp_sync.cfg for RBLLog
 0 - synchronization not configured
 1 - out of sync - running master mode
 2 - in sync - running  mastermode
 3 - in sync - running slave mode
 4 - in sync - running master mode (wait to reach state 2)
"
    ::= {RBLLog 6}

URIBLLog  OBJECT-TYPE
    SYNTAX      OCTET STRING
    MAX-ACCESS  read-write
    STATUS      current
    DESCRIPTION
"

"
    REFERENCE "Enable URIBL logging"
    DEFVAL { "1" }
    ::= {Logging 707}

syncStatURIBLLog  OBJECT-TYPE
    SYNTAX      OCTET STRING
    MAX-ACCESS  read-only
    STATUS      current
    DESCRIPTION
"
synchronization status for URIBLLog
-1 - URIBLLog could not be synchronized
 0 - synchronization not configured
 1 - out of sync - running master mode
 2 - in sync - running  mastermode
 3 - in sync - running slave mode
 4 - in sync - running master mode (wait to reach state 2)
"
    ::= {URIBLLog 5}

syncStatStrURIBLLog  OBJECT-TYPE
    SYNTAX      OCTET STRING
    MAX-ACCESS  read-only
    STATUS      current
    DESCRIPTION
"
synchronization status line from file assp_sync.cfg for URIBLLog
 0 - synchronization not configured
 1 - out of sync - running master mode
 2 - in sync - running  mastermode
 3 - in sync - running slave mode
 4 - in sync - running master mode (wait to reach state 2)
"
    ::= {URIBLLog 6}

ScanLog  OBJECT-TYPE
    SYNTAX      OCTET STRING
    MAX-ACCESS  read-write
    STATUS      current
    DESCRIPTION
"

"
    REFERENCE "Enable ClamAV logging"
    DEFVAL { "1" }
    ::= {Logging 708}

syncStatScanLog  OBJECT-TYPE
    SYNTAX      OCTET STRING
    MAX-ACCESS  read-only
    STATUS      current
    DESCRIPTION
"
synchronization status for ScanLog
-1 - ScanLog could not be synchronized
 0 - synchronization not configured
 1 - out of sync - running master mode
 2 - in sync - running  mastermode
 3 - in sync - running slave mode
 4 - in sync - running master mode (wait to reach state 2)
"
    ::= {ScanLog 5}

syncStatStrScanLog  OBJECT-TYPE
    SYNTAX      OCTET STRING
    MAX-ACCESS  read-only
    STATUS      current
    DESCRIPTION
"
synchronization status line from file assp_sync.cfg for ScanLog
 0 - synchronization not configured
 1 - out of sync - running master mode
 2 - in sync - running  mastermode
 3 - in sync - running slave mode
 4 - in sync - running master mode (wait to reach state 2)
"
    ::= {ScanLog 6}

DKIMlogging  OBJECT-TYPE
    SYNTAX      OCTET STRING
    MAX-ACCESS  read-write
    STATUS      current
    DESCRIPTION
"

"
    REFERENCE "Enable DKIM logging"
    DEFVAL { "1" }
    ::= {Logging 709}

syncStatDKIMlogging  OBJECT-TYPE
    SYNTAX      OCTET STRING
    MAX-ACCESS  read-only
    STATUS      current
    DESCRIPTION
"
synchronization status for DKIMlogging
-1 - DKIMlogging could not be synchronized
 0 - synchronization not configured
 1 - out of sync - running master mode
 2 - in sync - running  mastermode
 3 - in sync - running slave mode
 4 - in sync - running master mode (wait to reach state 2)
"
    ::= {DKIMlogging 5}

syncStatStrDKIMlogging  OBJECT-TYPE
    SYNTAX      OCTET STRING
    MAX-ACCESS  read-only
    STATUS      current
    DESCRIPTION
"
synchronization status line from file assp_sync.cfg for DKIMlogging
 0 - synchronization not configured
 1 - out of sync - running master mode
 2 - in sync - running  mastermode
 3 - in sync - running slave mode
 4 - in sync - running master mode (wait to reach state 2)
"
    ::= {DKIMlogging 6}

WorkerLog  OBJECT-TYPE
    SYNTAX      OCTET STRING
    MAX-ACCESS  read-write
    STATUS      current
    DESCRIPTION
"

"
    REFERENCE "Enable thread action logging"
    DEFVAL { "0" }
    ::= {Logging 710}

syncStatWorkerLog  OBJECT-TYPE
    SYNTAX      OCTET STRING
    MAX-ACCESS  read-only
    STATUS      current
    DESCRIPTION
"
synchronization status for WorkerLog
-1 - WorkerLog could not be synchronized
 0 - synchronization not configured
 1 - out of sync - running master mode
 2 - in sync - running  mastermode
 3 - in sync - running slave mode
 4 - in sync - running master mode (wait to reach state 2)
"
    ::= {WorkerLog 5}

syncStatStrWorkerLog  OBJECT-TYPE
    SYNTAX      OCTET STRING
    MAX-ACCESS  read-only
    STATUS      current
    DESCRIPTION
"
synchronization status line from file assp_sync.cfg for WorkerLog
 0 - synchronization not configured
 1 - out of sync - running master mode
 2 - in sync - running  mastermode
 3 - in sync - running slave mode
 4 - in sync - running master mode (wait to reach state 2)
"
    ::= {WorkerLog 6}

SignalLog  OBJECT-TYPE
    SYNTAX      OCTET STRING
    MAX-ACCESS  read-write
    STATUS      current
    DESCRIPTION
"
nolog will handle the Perl signals without any output (this should be never set!!!), standard will write a message to log, verbose will write a message to log and to file debugSignal.txt
"
    REFERENCE "Enable central Perl-signal logging"
    DEFVAL { "1" }
    ::= {Logging 711}

syncStatSignalLog  OBJECT-TYPE
    SYNTAX      OCTET STRING
    MAX-ACCESS  read-only
    STATUS      current
    DESCRIPTION
"
synchronization status for SignalLog
-1 - SignalLog could not be synchronized
 0 - synchronization not configured
 1 - out of sync - running master mode
 2 - in sync - running  mastermode
 3 - in sync - running slave mode
 4 - in sync - running master mode (wait to reach state 2)
"
    ::= {SignalLog 5}

syncStatStrSignalLog  OBJECT-TYPE
    SYNTAX      OCTET STRING
    MAX-ACCESS  read-only
    STATUS      current
    DESCRIPTION
"
synchronization status line from file assp_sync.cfg for SignalLog
 0 - synchronization not configured
 1 - out of sync - running master mode
 2 - in sync - running  mastermode
 3 - in sync - running slave mode
 4 - in sync - running master mode (wait to reach state 2)
"
    ::= {SignalLog 6}

BayesianLog  OBJECT-TYPE
    SYNTAX      OCTET STRING
    MAX-ACCESS  read-write
    STATUS      current
    DESCRIPTION
"
Enables verbose logging of  Bayesian checks in the maillog.
"
    REFERENCE "Enable Bayesian Logging"
    DEFVAL { "1" }
    ::= {Logging 712}

syncStatBayesianLog  OBJECT-TYPE
    SYNTAX      OCTET STRING
    MAX-ACCESS  read-only
    STATUS      current
    DESCRIPTION
"
synchronization status for BayesianLog
-1 - BayesianLog could not be synchronized
 0 - synchronization not configured
 1 - out of sync - running master mode
 2 - in sync - running  mastermode
 3 - in sync - running slave mode
 4 - in sync - running master mode (wait to reach state 2)
"
    ::= {BayesianLog 5}

syncStatStrBayesianLog  OBJECT-TYPE
    SYNTAX      OCTET STRING
    MAX-ACCESS  read-only
    STATUS      current
    DESCRIPTION
"
synchronization status line from file assp_sync.cfg for BayesianLog
 0 - synchronization not configured
 1 - out of sync - running master mode
 2 - in sync - running  mastermode
 3 - in sync - running slave mode
 4 - in sync - running master mode (wait to reach state 2)
"
    ::= {BayesianLog 6}

ConvLog  OBJECT-TYPE
    SYNTAX      OCTET STRING
    MAX-ACCESS  read-write
    STATUS      current
    DESCRIPTION
"

"
    REFERENCE "Enable Conversion logging"
    DEFVAL { "1" }
    ::= {Logging 713}

syncStatConvLog  OBJECT-TYPE
    SYNTAX      OCTET STRING
    MAX-ACCESS  read-only
    STATUS      current
    DESCRIPTION
"
synchronization status for ConvLog
-1 - ConvLog could not be synchronized
 0 - synchronization not configured
 1 - out of sync - running master mode
 2 - in sync - running  mastermode
 3 - in sync - running slave mode
 4 - in sync - running master mode (wait to reach state 2)
"
    ::= {ConvLog 5}

syncStatStrConvLog  OBJECT-TYPE
    SYNTAX      OCTET STRING
    MAX-ACCESS  read-only
    STATUS      current
    DESCRIPTION
"
synchronization status line from file assp_sync.cfg for ConvLog
 0 - synchronization not configured
 1 - out of sync - running master mode
 2 - in sync - running  mastermode
 3 - in sync - running slave mode
 4 - in sync - running master mode (wait to reach state 2)
"
    ::= {ConvLog 6}

MaintenanceLog  OBJECT-TYPE
    SYNTAX      OCTET STRING
    MAX-ACCESS  read-write
    STATUS      current
    DESCRIPTION
"

"
    REFERENCE "Enable Maintenance logging"
    DEFVAL { "1" }
    ::= {Logging 714}

syncStatMaintenanceLog  OBJECT-TYPE
    SYNTAX      OCTET STRING
    MAX-ACCESS  read-only
    STATUS      current
    DESCRIPTION
"
synchronization status for MaintenanceLog
-1 - MaintenanceLog could not be synchronized
 0 - synchronization not configured
 1 - out of sync - running master mode
 2 - in sync - running  mastermode
 3 - in sync - running slave mode
 4 - in sync - running master mode (wait to reach state 2)
"
    ::= {MaintenanceLog 5}

syncStatStrMaintenanceLog  OBJECT-TYPE
    SYNTAX      OCTET STRING
    MAX-ACCESS  read-only
    STATUS      current
    DESCRIPTION
"
synchronization status line from file assp_sync.cfg for MaintenanceLog
 0 - synchronization not configured
 1 - out of sync - running master mode
 2 - in sync - running  mastermode
 3 - in sync - running slave mode
 4 - in sync - running master mode (wait to reach state 2)
"
    ::= {MaintenanceLog 6}

PerformanceLog  OBJECT-TYPE
    SYNTAX      OCTET STRING
    MAX-ACCESS  read-write
    STATUS      current
    DESCRIPTION
"

"
    REFERENCE "Enable Performance logging"
    DEFVAL { "1" }
    ::= {Logging 715}

syncStatPerformanceLog  OBJECT-TYPE
    SYNTAX      OCTET STRING
    MAX-ACCESS  read-only
    STATUS      current
    DESCRIPTION
"
synchronization status for PerformanceLog
-1 - PerformanceLog could not be synchronized
 0 - synchronization not configured
 1 - out of sync - running master mode
 2 - in sync - running  mastermode
 3 - in sync - running slave mode
 4 - in sync - running master mode (wait to reach state 2)
"
    ::= {PerformanceLog 5}

syncStatStrPerformanceLog  OBJECT-TYPE
    SYNTAX      OCTET STRING
    MAX-ACCESS  read-only
    STATUS      current
    DESCRIPTION
"
synchronization status line from file assp_sync.cfg for PerformanceLog
 0 - synchronization not configured
 1 - out of sync - running master mode
 2 - in sync - running  mastermode
 3 - in sync - running slave mode
 4 - in sync - running master mode (wait to reach state 2)
"
    ::= {PerformanceLog 6}

ReportLog  OBJECT-TYPE
    SYNTAX      OCTET STRING
    MAX-ACCESS  read-write
    STATUS      current
    DESCRIPTION
"

"
    REFERENCE "Enable Report logging"
    DEFVAL { "1" }
    ::= {Logging 716}

syncStatReportLog  OBJECT-TYPE
    SYNTAX      OCTET STRING
    MAX-ACCESS  read-only
    STATUS      current
    DESCRIPTION
"
synchronization status for ReportLog
-1 - ReportLog could not be synchronized
 0 - synchronization not configured
 1 - out of sync - running master mode
 2 - in sync - running  mastermode
 3 - in sync - running slave mode
 4 - in sync - running master mode (wait to reach state 2)
"
    ::= {ReportLog 5}

syncStatStrReportLog  OBJECT-TYPE
    SYNTAX      OCTET STRING
    MAX-ACCESS  read-only
    STATUS      current
    DESCRIPTION
"
synchronization status line from file assp_sync.cfg for ReportLog
 0 - synchronization not configured
 1 - out of sync - running master mode
 2 - in sync - running  mastermode
 3 - in sync - running slave mode
 4 - in sync - running master mode (wait to reach state 2)
"
    ::= {ReportLog 6}

ScheduleLog  OBJECT-TYPE
    SYNTAX      OCTET STRING
    MAX-ACCESS  read-write
    STATUS      current
    DESCRIPTION
"

"
    REFERENCE "Enable Scheduler logging"
    DEFVAL { "1" }
    ::= {Logging 717}

syncStatScheduleLog  OBJECT-TYPE
    SYNTAX      OCTET STRING
    MAX-ACCESS  read-only
    STATUS      current
    DESCRIPTION
"
synchronization status for ScheduleLog
-1 - ScheduleLog could not be synchronized
 0 - synchronization not configured
 1 - out of sync - running master mode
 2 - in sync - running  mastermode
 3 - in sync - running slave mode
 4 - in sync - running master mode (wait to reach state 2)
"
    ::= {ScheduleLog 5}

syncStatStrScheduleLog  OBJECT-TYPE
    SYNTAX      OCTET STRING
    MAX-ACCESS  read-only
    STATUS      current
    DESCRIPTION
"
synchronization status line from file assp_sync.cfg for ScheduleLog
 0 - synchronization not configured
 1 - out of sync - running master mode
 2 - in sync - running  mastermode
 3 - in sync - running slave mode
 4 - in sync - running master mode (wait to reach state 2)
"
    ::= {ScheduleLog 6}

Showmaxreplies  OBJECT-TYPE
    SYNTAX      OCTET STRING
    MAX-ACCESS  read-write
    STATUS      current
    DESCRIPTION
"
Show hits until maxreplies instead of stopping at maxhits (RBL,URIBL,RWL).
"
    REFERENCE "Show All Possible Hits "
    DEFVAL { "" }
    ::= {Logging 718}

syncStatShowmaxreplies  OBJECT-TYPE
    SYNTAX      OCTET STRING
    MAX-ACCESS  read-only
    STATUS      current
    DESCRIPTION
"
synchronization status for Showmaxreplies
-1 - Showmaxreplies could not be synchronized
 0 - synchronization not configured
 1 - out of sync - running master mode
 2 - in sync - running  mastermode
 3 - in sync - running slave mode
 4 - in sync - running master mode (wait to reach state 2)
"
    ::= {Showmaxreplies 5}

syncStatStrShowmaxreplies  OBJECT-TYPE
    SYNTAX      OCTET STRING
    MAX-ACCESS  read-only
    STATUS      current
    DESCRIPTION
"
synchronization status line from file assp_sync.cfg for Showmaxreplies
 0 - synchronization not configured
 1 - out of sync - running master mode
 2 - in sync - running  mastermode
 3 - in sync - running slave mode
 4 - in sync - running master mode (wait to reach state 2)
"
    ::= {Showmaxreplies 6}

RegExLength  OBJECT-TYPE
    SYNTAX      OCTET STRING
    MAX-ACCESS  read-write
    STATUS      current
    DESCRIPTION
"
Defines how many bytes of a matching Regular Expression will be shown in the log
  Some matching Regular Expressions are too long for one line. Default: 32
"
    REFERENCE "RegEx Length in Log"
    DEFVAL { "32" }
    ::= {Logging 719}

syncStatRegExLength  OBJECT-TYPE
    SYNTAX      OCTET STRING
    MAX-ACCESS  read-only
    STATUS      current
    DESCRIPTION
"
synchronization status for RegExLength
-1 - RegExLength could not be synchronized
 0 - synchronization not configured
 1 - out of sync - running master mode
 2 - in sync - running  mastermode
 3 - in sync - running slave mode
 4 - in sync - running master mode (wait to reach state 2)
"
    ::= {RegExLength 5}

syncStatStrRegExLength  OBJECT-TYPE
    SYNTAX      OCTET STRING
    MAX-ACCESS  read-only
    STATUS      current
    DESCRIPTION
"
synchronization status line from file assp_sync.cfg for RegExLength
 0 - synchronization not configured
 1 - out of sync - running master mode
 2 - in sync - running  mastermode
 3 - in sync - running slave mode
 4 - in sync - running master mode (wait to reach state 2)
"
    ::= {RegExLength 6}

sendNoopInfo  OBJECT-TYPE
    SYNTAX      OCTET STRING
    MAX-ACCESS  read-write
    STATUS      current
    DESCRIPTION
"
Checked means you want ASSP to send a 'NOOP Connection from IP' message to your SMTP server.
  
  
  
"
    REFERENCE "Send NOOP Info"
    DEFVAL { "" }
    ::= {Logging 720}

syncStatsendNoopInfo  OBJECT-TYPE
    SYNTAX      OCTET STRING
    MAX-ACCESS  read-only
    STATUS      current
    DESCRIPTION
"
synchronization status for sendNoopInfo
-1 - sendNoopInfo could not be synchronized
 0 - synchronization not configured
 1 - out of sync - running master mode
 2 - in sync - running  mastermode
 3 - in sync - running slave mode
 4 - in sync - running master mode (wait to reach state 2)
"
    ::= {sendNoopInfo 5}

syncStatStrsendNoopInfo  OBJECT-TYPE
    SYNTAX      OCTET STRING
    MAX-ACCESS  read-only
    STATUS      current
    DESCRIPTION
"
synchronization status line from file assp_sync.cfg for sendNoopInfo
 0 - synchronization not configured
 1 - out of sync - running master mode
 2 - in sync - running  mastermode
 3 - in sync - running slave mode
 4 - in sync - running master mode (wait to reach state 2)
"
    ::= {sendNoopInfo 6}

noLogLineRe  OBJECT-TYPE
    SYNTAX      OCTET STRING
    MAX-ACCESS  read-write
    STATUS      current
    DESCRIPTION
"
Put anything here to identify log Lines that you don't want to be logged.
"
    REFERENCE "Regular Expression to Identify skipped Log Lines*"
    DEFVAL { "" }
    ::= {Logging 868}

syncStatnoLogLineRe  OBJECT-TYPE
    SYNTAX      OCTET STRING
    MAX-ACCESS  read-only
    STATUS      current
    DESCRIPTION
"
synchronization status for noLogLineRe
-1 - noLogLineRe could not be synchronized
 0 - synchronization not configured
 1 - out of sync - running master mode
 2 - in sync - running  mastermode
 3 - in sync - running slave mode
 4 - in sync - running master mode (wait to reach state 2)
"
    ::= {noLogLineRe 5}

syncStatStrnoLogLineRe  OBJECT-TYPE
    SYNTAX      OCTET STRING
    MAX-ACCESS  read-only
    STATUS      current
    DESCRIPTION
"
synchronization status line from file assp_sync.cfg for noLogLineRe
 0 - synchronization not configured
 1 - out of sync - running master mode
 2 - in sync - running  mastermode
 3 - in sync - running slave mode
 4 - in sync - running master mode (wait to reach state 2)
"
    ::= {noLogLineRe 6}

LogDateFormat  OBJECT-TYPE
    SYNTAX      OCTET STRING
    MAX-ACCESS  read-write
    STATUS      current
    DESCRIPTION
"
Use this option to set the logdate. The default value is 'MMM-DD-YY hh:mm:ss'. The following (case sensitive !) replacements will be done:
 YYYY - year four digits
 YY - year two digits
 MMM - month (three charactes) alpha numeric - like Oct Nov Dec
 MM - month numeric two digits
 DDD - day (three charactes) alpha numeric - like Mon Tue Fri
 DD - day numeric two digits
 hh - hour two digits
 mm - minute two digits
 ss - second two digits
 NOTICE: If you change this value, BlockReports and Griplist-uploads will not work for log entries in the past (from now)!
 A value has to be defined for every part of the date/time, the date must be the first part. Allowed separators in date part are '_ -./' - in time part '-_.:' .
"
    REFERENCE "Date/Time Format in LogDate"
    DEFVAL { "MMM-DD-YY hh:mm:ss" }
    ::= {Logging 869}

syncStatLogDateFormat  OBJECT-TYPE
    SYNTAX      OCTET STRING
    MAX-ACCESS  read-only
    STATUS      current
    DESCRIPTION
"
synchronization status for LogDateFormat
-1 - LogDateFormat could not be synchronized
 0 - synchronization not configured
 1 - out of sync - running master mode
 2 - in sync - running  mastermode
 3 - in sync - running slave mode
 4 - in sync - running master mode (wait to reach state 2)
"
    ::= {LogDateFormat 5}

syncStatStrLogDateFormat  OBJECT-TYPE
    SYNTAX      OCTET STRING
    MAX-ACCESS  read-only
    STATUS      current
    DESCRIPTION
"
synchronization status line from file assp_sync.cfg for LogDateFormat
 0 - synchronization not configured
 1 - out of sync - running master mode
 2 - in sync - running  mastermode
 3 - in sync - running slave mode
 4 - in sync - running master mode (wait to reach state 2)
"
    ::= {LogDateFormat 6}

LogDateLang  OBJECT-TYPE
    SYNTAX      OCTET STRING
    MAX-ACCESS  read-write
    STATUS      current
    DESCRIPTION
"
Select the language for the day and month if LogDateFormat contains DDD and/or MMM.
  NOTICE: If you change this value, BlockReports and Griplist-uploads will not work for log entries in the past (from now)!
"
    REFERENCE "Date/Time Language"
    DEFVAL { "0" }
    ::= {Logging 870}

syncStatLogDateLang  OBJECT-TYPE
    SYNTAX      OCTET STRING
    MAX-ACCESS  read-only
    STATUS      current
    DESCRIPTION
"
synchronization status for LogDateLang
-1 - LogDateLang could not be synchronized
 0 - synchronization not configured
 1 - out of sync - running master mode
 2 - in sync - running  mastermode
 3 - in sync - running slave mode
 4 - in sync - running master mode (wait to reach state 2)
"
    ::= {LogDateLang 5}

syncStatStrLogDateLang  OBJECT-TYPE
    SYNTAX      OCTET STRING
    MAX-ACCESS  read-only
    STATUS      current
    DESCRIPTION
"
synchronization status line from file assp_sync.cfg for LogDateLang
 0 - synchronization not configured
 1 - out of sync - running master mode
 2 - in sync - running  mastermode
 3 - in sync - running slave mode
 4 - in sync - running master mode (wait to reach state 2)
"
    ::= {LogDateLang 6}

SNMPLog  OBJECT-TYPE
    SYNTAX      OCTET STRING
    MAX-ACCESS  read-write
    STATUS      current
    DESCRIPTION
"

"
    REFERENCE "Enable SNMP logging"
    DEFVAL { "1" }
    ::= {Logging 942}

syncStatSNMPLog  OBJECT-TYPE
    SYNTAX      OCTET STRING
    MAX-ACCESS  read-only
    STATUS      current
    DESCRIPTION
"
synchronization status for SNMPLog
-1 - SNMPLog could not be synchronized
 0 - synchronization not configured
 1 - out of sync - running master mode
 2 - in sync - running  mastermode
 3 - in sync - running slave mode
 4 - in sync - running master mode (wait to reach state 2)
"
    ::= {SNMPLog 5}

syncStatStrSNMPLog  OBJECT-TYPE
    SYNTAX      OCTET STRING
    MAX-ACCESS  read-only
    STATUS      current
    DESCRIPTION
"
synchronization status line from file assp_sync.cfg for SNMPLog
 0 - synchronization not configured
 1 - out of sync - running master mode
 2 - in sync - running  mastermode
 3 - in sync - running slave mode
 4 - in sync - running master mode (wait to reach state 2)
"
    ::= {SNMPLog 6}

LDAPSetup  OBJECT IDENTIFIER ::= {asspConfig 30}
LDAPHost  OBJECT-TYPE
    SYNTAX      OCTET STRING
    MAX-ACCESS  read-write
    STATUS      current
    DESCRIPTION
"
Enter the DNS-name(s) or IP address(es) of the server(s) that run(s) the  database. Second entry is backup. For example: localhost. Separate entries with pipes: LDAP-1.domain.com|LDAP-2.domain.com . To use a different than the default LDAP port, define host:port.
"
    REFERENCE "LDAP Host(s)"
    DEFVAL { "localhost" }
    ::= {LDAPSetup 721}

syncStatLDAPHost  OBJECT-TYPE
    SYNTAX      OCTET STRING
    MAX-ACCESS  read-only
    STATUS      current
    DESCRIPTION
"
synchronization status for LDAPHost
-1 - LDAPHost could not be synchronized
 0 - synchronization not configured
 1 - out of sync - running master mode
 2 - in sync - running  mastermode
 3 - in sync - running slave mode
 4 - in sync - running master mode (wait to reach state 2)
"
    ::= {LDAPHost 5}

syncStatStrLDAPHost  OBJECT-TYPE
    SYNTAX      OCTET STRING
    MAX-ACCESS  read-only
    STATUS      current
    DESCRIPTION
"
synchronization status line from file assp_sync.cfg for LDAPHost
 0 - synchronization not configured
 1 - out of sync - running master mode
 2 - in sync - running  mastermode
 3 - in sync - running slave mode
 4 - in sync - running master mode (wait to reach state 2)
"
    ::= {LDAPHost 6}

DoLDAPSSL  OBJECT-TYPE
    SYNTAX      OCTET STRING
    MAX-ACCESS  read-write
    STATUS      current
    DESCRIPTION
"
ASSP will use 'ldaps (SSL port 636)' instead of ldap (port 389) or 'ldaps (TLS over port 389)'. The Perl module  must be installed to use SSL or TLS!
"
    REFERENCE "Use SSL with LDAP (ldaps)"
    DEFVAL { "0" }
    ::= {LDAPSetup 722}

syncStatDoLDAPSSL  OBJECT-TYPE
    SYNTAX      OCTET STRING
    MAX-ACCESS  read-only
    STATUS      current
    DESCRIPTION
"
synchronization status for DoLDAPSSL
-1 - DoLDAPSSL could not be synchronized
 0 - synchronization not configured
 1 - out of sync - running master mode
 2 - in sync - running  mastermode
 3 - in sync - running slave mode
 4 - in sync - running master mode (wait to reach state 2)
"
    ::= {DoLDAPSSL 5}

syncStatStrDoLDAPSSL  OBJECT-TYPE
    SYNTAX      OCTET STRING
    MAX-ACCESS  read-only
    STATUS      current
    DESCRIPTION
"
synchronization status line from file assp_sync.cfg for DoLDAPSSL
 0 - synchronization not configured
 1 - out of sync - running master mode
 2 - in sync - running  mastermode
 3 - in sync - running slave mode
 4 - in sync - running master mode (wait to reach state 2)
"
    ::= {DoLDAPSSL 6}

LDAPtimeout  OBJECT-TYPE
    SYNTAX      OCTET STRING
    MAX-ACCESS  read-write
    STATUS      current
    DESCRIPTION
"
timeout when connecting to the remote server. The default is 15 seconds.
"
    REFERENCE "LDAP Query Timeout"
    DEFVAL { "15" }
    ::= {LDAPSetup 723}

syncStatLDAPtimeout  OBJECT-TYPE
    SYNTAX      OCTET STRING
    MAX-ACCESS  read-only
    STATUS      current
    DESCRIPTION
"
synchronization status for LDAPtimeout
-1 - LDAPtimeout could not be synchronized
 0 - synchronization not configured
 1 - out of sync - running master mode
 2 - in sync - running  mastermode
 3 - in sync - running slave mode
 4 - in sync - running master mode (wait to reach state 2)
"
    ::= {LDAPtimeout 5}

syncStatStrLDAPtimeout  OBJECT-TYPE
    SYNTAX      OCTET STRING
    MAX-ACCESS  read-only
    STATUS      current
    DESCRIPTION
"
synchronization status line from file assp_sync.cfg for LDAPtimeout
 0 - synchronization not configured
 1 - out of sync - running master mode
 2 - in sync - running  mastermode
 3 - in sync - running slave mode
 4 - in sync - running master mode (wait to reach state 2)
"
    ::= {LDAPtimeout 6}

LDAPLogin  OBJECT-TYPE
    SYNTAX      OCTET STRING
    MAX-ACCESS  read-write
    STATUS      current
    DESCRIPTION
"
Most LDAP servers require a login and password before they allow queries.Enter the DN specification for a user with sufficient permissions here.For example: cn=Administrator,cn=Users,DC=yourcompany,DC=com
"
    REFERENCE "LDAP Login"
    DEFVAL { "" }
    ::= {LDAPSetup 724}

syncStatLDAPLogin  OBJECT-TYPE
    SYNTAX      OCTET STRING
    MAX-ACCESS  read-only
    STATUS      current
    DESCRIPTION
"
synchronization status for LDAPLogin
-1 - LDAPLogin could not be synchronized
 0 - synchronization not configured
 1 - out of sync - running master mode
 2 - in sync - running  mastermode
 3 - in sync - running slave mode
 4 - in sync - running master mode (wait to reach state 2)
"
    ::= {LDAPLogin 5}

syncStatStrLDAPLogin  OBJECT-TYPE
    SYNTAX      OCTET STRING
    MAX-ACCESS  read-only
    STATUS      current
    DESCRIPTION
"
synchronization status line from file assp_sync.cfg for LDAPLogin
 0 - synchronization not configured
 1 - out of sync - running master mode
 2 - in sync - running  mastermode
 3 - in sync - running slave mode
 4 - in sync - running master mode (wait to reach state 2)
"
    ::= {LDAPLogin 6}

LDAPPassword  OBJECT-TYPE
    SYNTAX      OCTET STRING
    MAX-ACCESS  read-write
    STATUS      current
    DESCRIPTION
"
Enter the password for the specified LDAP login here.
"
    REFERENCE "LDAP Password"
    DEFVAL { "" }
    ::= {LDAPSetup 725}

syncStatLDAPPassword  OBJECT-TYPE
    SYNTAX      OCTET STRING
    MAX-ACCESS  read-only
    STATUS      current
    DESCRIPTION
"
synchronization status for LDAPPassword
-1 - LDAPPassword could not be synchronized
 0 - synchronization not configured
 1 - out of sync - running master mode
 2 - in sync - running  mastermode
 3 - in sync - running slave mode
 4 - in sync - running master mode (wait to reach state 2)
"
    ::= {LDAPPassword 5}

syncStatStrLDAPPassword  OBJECT-TYPE
    SYNTAX      OCTET STRING
    MAX-ACCESS  read-only
    STATUS      current
    DESCRIPTION
"
synchronization status line from file assp_sync.cfg for LDAPPassword
 0 - synchronization not configured
 1 - out of sync - running master mode
 2 - in sync - running  mastermode
 3 - in sync - running slave mode
 4 - in sync - running master mode (wait to reach state 2)
"
    ::= {LDAPPassword 6}

LDAPVersion  OBJECT-TYPE
    SYNTAX      OCTET STRING
    MAX-ACCESS  read-write
    STATUS      current
    DESCRIPTION
"
Enter the version for the specified LDAP here.
"
    REFERENCE "LDAP Version"
    DEFVAL { "3" }
    ::= {LDAPSetup 726}

syncStatLDAPVersion  OBJECT-TYPE
    SYNTAX      OCTET STRING
    MAX-ACCESS  read-only
    STATUS      current
    DESCRIPTION
"
synchronization status for LDAPVersion
-1 - LDAPVersion could not be synchronized
 0 - synchronization not configured
 1 - out of sync - running master mode
 2 - in sync - running  mastermode
 3 - in sync - running slave mode
 4 - in sync - running master mode (wait to reach state 2)
"
    ::= {LDAPVersion 5}

syncStatStrLDAPVersion  OBJECT-TYPE
    SYNTAX      OCTET STRING
    MAX-ACCESS  read-only
    STATUS      current
    DESCRIPTION
"
synchronization status line from file assp_sync.cfg for LDAPVersion
 0 - synchronization not configured
 1 - out of sync - running master mode
 2 - in sync - running  mastermode
 3 - in sync - running slave mode
 4 - in sync - running master mode (wait to reach state 2)
"
    ::= {LDAPVersion 6}

LDAPRoot  OBJECT-TYPE
    SYNTAX      OCTET STRING
    MAX-ACCESS  read-write
    STATUS      current
    DESCRIPTION
"
The LDAP lookup will use this container and all sub-containers to match the local email address query.The literal DOMAIN is replaced by the domain part of SMTP recipient (eg. domain.com) during the search.For example: DC=yourcompany,DC=com.If you use DOMAIN here, you must check 'LDAP failures return false' below or non local domains will be treated as local.
"
    REFERENCE "LDAP Root container for Local Addresses"
    DEFVAL { "" }
    ::= {LDAPSetup 727}

syncStatLDAPRoot  OBJECT-TYPE
    SYNTAX      OCTET STRING
    MAX-ACCESS  read-only
    STATUS      current
    DESCRIPTION
"
synchronization status for LDAPRoot
-1 - LDAPRoot could not be synchronized
 0 - synchronization not configured
 1 - out of sync - running master mode
 2 - in sync - running  mastermode
 3 - in sync - running slave mode
 4 - in sync - running master mode (wait to reach state 2)
"
    ::= {LDAPRoot 5}

syncStatStrLDAPRoot  OBJECT-TYPE
    SYNTAX      OCTET STRING
    MAX-ACCESS  read-only
    STATUS      current
    DESCRIPTION
"
synchronization status line from file assp_sync.cfg for LDAPRoot
 0 - synchronization not configured
 1 - out of sync - running master mode
 2 - in sync - running  mastermode
 3 - in sync - running slave mode
 4 - in sync - running master mode (wait to reach state 2)
"
    ::= {LDAPRoot 6}

ldLDAPFilter  OBJECT-TYPE
    SYNTAX      OCTET STRING
    MAX-ACCESS  read-write
    STATUS      current
    DESCRIPTION
"
This filter is used to query the LDAP database. This strongly depends on the LDAP structure.The filter must return an entry if the domain must be relayed.
  The literal DOMAIN is replaced by the domain name during the search.
  for example: (&amp;(|(|(|(|(&amp;(objectclass=user)(objectcategory=person))(objectcategory=group))(objectclass=publicfolder))(!(objectclass=contact)))(objectclass=msExchDynamicDistributionList))(proxyaddresses=smtp:*@DOMAIN))
"
    REFERENCE "LDAP Filter for Local Domains"
    DEFVAL { "" }
    ::= {LDAPSetup 728}

syncStatldLDAPFilter  OBJECT-TYPE
    SYNTAX      OCTET STRING
    MAX-ACCESS  read-only
    STATUS      current
    DESCRIPTION
"
synchronization status for ldLDAPFilter
-1 - ldLDAPFilter could not be synchronized
 0 - synchronization not configured
 1 - out of sync - running master mode
 2 - in sync - running  mastermode
 3 - in sync - running slave mode
 4 - in sync - running master mode (wait to reach state 2)
"
    ::= {ldLDAPFilter 5}

syncStatStrldLDAPFilter  OBJECT-TYPE
    SYNTAX      OCTET STRING
    MAX-ACCESS  read-only
    STATUS      current
    DESCRIPTION
"
synchronization status line from file assp_sync.cfg for ldLDAPFilter
 0 - synchronization not configured
 1 - out of sync - running master mode
 2 - in sync - running  mastermode
 3 - in sync - running slave mode
 4 - in sync - running master mode (wait to reach state 2)
"
    ::= {ldLDAPFilter 6}

LDAPFilter  OBJECT-TYPE
    SYNTAX      OCTET STRING
    MAX-ACCESS  read-write
    STATUS      current
    DESCRIPTION
"
This filter is used to query the LDAP database. This strongly depends on the LDAP structure.The filter must return an entry if the recipient address matches with that of any user.The literal EMAILADDRESS is replaced by the fully qualified SMTP recipient (eg. user@domain.com) during the search.The literal USERNAME is replaced by the user part of SMTP recipient (eg. user) during the search.The literal DOMAIN is replaced by the domain part of SMTP recipient (eg. domain.com) during the search.For example: (proxyaddresses=smtp:EMAILADDRESS) or (|(mail=EMAILADDRESS)(mailaddress=EMAILADDRESS)) or
 (&amp;(|(|(|(|(&amp;(objectclass=user)(objectcategory=person))(objectcategory=group))(objectclass=publicfolder))(!(objectclass=contact)))(objectclass=msExchDynamicDistributionList))(proxyaddresses=smtp:EMAILADDRESS))
"
    REFERENCE "LDAP Filter for Local Addresses"
    DEFVAL { "" }
    ::= {LDAPSetup 729}

syncStatLDAPFilter  OBJECT-TYPE
    SYNTAX      OCTET STRING
    MAX-ACCESS  read-only
    STATUS      current
    DESCRIPTION
"
synchronization status for LDAPFilter
-1 - LDAPFilter could not be synchronized
 0 - synchronization not configured
 1 - out of sync - running master mode
 2 - in sync - running  mastermode
 3 - in sync - running slave mode
 4 - in sync - running master mode (wait to reach state 2)
"
    ::= {LDAPFilter 5}

syncStatStrLDAPFilter  OBJECT-TYPE
    SYNTAX      OCTET STRING
    MAX-ACCESS  read-only
    STATUS      current
    DESCRIPTION
"
synchronization status line from file assp_sync.cfg for LDAPFilter
 0 - synchronization not configured
 1 - out of sync - running master mode
 2 - in sync - running  mastermode
 3 - in sync - running slave mode
 4 - in sync - running master mode (wait to reach state 2)
"
    ::= {LDAPFilter 6}

LDAPcrossCheckInterval  OBJECT-TYPE
    SYNTAX      OCTET STRING
    MAX-ACCESS  read-write
    STATUS      current
    DESCRIPTION
"
Delete outdated entries from the LDAP/VRFY cache. Check the LDAP cache to the LDAP server and/or VRFY-MTA and delete not existing entries.
  Defaults to 12 hours. Is only used, if ldaplistdb is defined in the database section!
"
    REFERENCE "Clean Up local LDAP/VRFY Database <sup>s</sup>"
    DEFVAL { "12" }
    ::= {LDAPSetup 730}

syncStatLDAPcrossCheckInterval  OBJECT-TYPE
    SYNTAX      OCTET STRING
    MAX-ACCESS  read-only
    STATUS      current
    DESCRIPTION
"
synchronization status for LDAPcrossCheckInterval
-1 - LDAPcrossCheckInterval could not be synchronized
 0 - synchronization not configured
 1 - out of sync - running master mode
 2 - in sync - running  mastermode
 3 - in sync - running slave mode
 4 - in sync - running master mode (wait to reach state 2)
"
    ::= {LDAPcrossCheckInterval 5}

syncStatStrLDAPcrossCheckInterval  OBJECT-TYPE
    SYNTAX      OCTET STRING
    MAX-ACCESS  read-only
    STATUS      current
    DESCRIPTION
"
synchronization status line from file assp_sync.cfg for LDAPcrossCheckInterval
 0 - synchronization not configured
 1 - out of sync - running master mode
 2 - in sync - running  mastermode
 3 - in sync - running slave mode
 4 - in sync - running master mode (wait to reach state 2)
"
    ::= {LDAPcrossCheckInterval 6}

LDAPShowDB  OBJECT-TYPE
    SYNTAX      OCTET STRING
    MAX-ACCESS  read-write
    STATUS      current
    DESCRIPTION
"
The directory/file with the LDAP cache database file. If you change ldaplistdb in section Filepath you must change it here too.
"
    REFERENCE "Show local LDAP Database"
    DEFVAL { "file:ldaplist" }
    ::= {LDAPSetup 731}

forceLDAPcrossCheck  OBJECT-TYPE
    SYNTAX      OCTET STRING
    MAX-ACCESS  read-write
    STATUS      current
    DESCRIPTION
"
ASSP will force to run a LDAP/VRFY-CrossCheck now!&nbsp;
"
    REFERENCE "force to run LDAP/VRFY-CrossCheck - now."
    DEFVAL { "" }
    ::= {LDAPSetup 732}

MaxLDAPlistDays  OBJECT-TYPE
    SYNTAX      OCTET STRING
    MAX-ACCESS  read-write
    STATUS      current
    DESCRIPTION
"
This is the number of days an address will be kept on the local LDAP/VRFY cache without any email to this address.
"
    REFERENCE "Max LDAP/VRFY cache Days"
    DEFVAL { "30" }
    ::= {LDAPSetup 733}

syncStatMaxLDAPlistDays  OBJECT-TYPE
    SYNTAX      OCTET STRING
    MAX-ACCESS  read-only
    STATUS      current
    DESCRIPTION
"
synchronization status for MaxLDAPlistDays
-1 - MaxLDAPlistDays could not be synchronized
 0 - synchronization not configured
 1 - out of sync - running master mode
 2 - in sync - running  mastermode
 3 - in sync - running slave mode
 4 - in sync - running master mode (wait to reach state 2)
"
    ::= {MaxLDAPlistDays 5}

syncStatStrMaxLDAPlistDays  OBJECT-TYPE
    SYNTAX      OCTET STRING
    MAX-ACCESS  read-only
    STATUS      current
    DESCRIPTION
"
synchronization status line from file assp_sync.cfg for MaxLDAPlistDays
 0 - synchronization not configured
 1 - out of sync - running master mode
 2 - in sync - running  mastermode
 3 - in sync - running slave mode
 4 - in sync - running master mode (wait to reach state 2)
"
    ::= {MaxLDAPlistDays 6}

LDAPFail  OBJECT-TYPE
    SYNTAX      OCTET STRING
    MAX-ACCESS  read-write
    STATUS      current
    DESCRIPTION
"
If checked, when an error occurs in LDAP or VRFY lookups, the test fails.
"
    REFERENCE "LDAP/VRFY failures return false"
    DEFVAL { "" }
    ::= {LDAPSetup 734}

syncStatLDAPFail  OBJECT-TYPE
    SYNTAX      OCTET STRING
    MAX-ACCESS  read-only
    STATUS      current
    DESCRIPTION
"
synchronization status for LDAPFail
-1 - LDAPFail could not be synchronized
 0 - synchronization not configured
 1 - out of sync - running master mode
 2 - in sync - running  mastermode
 3 - in sync - running slave mode
 4 - in sync - running master mode (wait to reach state 2)
"
    ::= {LDAPFail 5}

syncStatStrLDAPFail  OBJECT-TYPE
    SYNTAX      OCTET STRING
    MAX-ACCESS  read-only
    STATUS      current
    DESCRIPTION
"
synchronization status line from file assp_sync.cfg for LDAPFail
 0 - synchronization not configured
 1 - out of sync - running master mode
 2 - in sync - running  mastermode
 3 - in sync - running slave mode
 4 - in sync - running master mode (wait to reach state 2)
"
    ::= {LDAPFail 6}

ldLDAPRoot  OBJECT-TYPE
    SYNTAX      OCTET STRING
    MAX-ACCESS  read-write
    STATUS      current
    DESCRIPTION
"
The LDAP lookup will use this container and all sub-containers to match the local domain query.The literal DOMAIN is replaced by the domain part of SMTP recipient (eg. domain.com) during the search.For example: DC=yourcompany,DC=com.If you use DOMAIN here, you must check 'LDAP failures return false' below or non local domains will be treated as local. If not defined, LDAPRoot will be used.
"
    REFERENCE "LDAP Root container for Local Domains"
    DEFVAL { "" }
    ::= {LDAPSetup 935}

syncStatldLDAPRoot  OBJECT-TYPE
    SYNTAX      OCTET STRING
    MAX-ACCESS  read-only
    STATUS      current
    DESCRIPTION
"
synchronization status for ldLDAPRoot
-1 - ldLDAPRoot could not be synchronized
 0 - synchronization not configured
 1 - out of sync - running master mode
 2 - in sync - running  mastermode
 3 - in sync - running slave mode
 4 - in sync - running master mode (wait to reach state 2)
"
    ::= {ldLDAPRoot 5}

syncStatStrldLDAPRoot  OBJECT-TYPE
    SYNTAX      OCTET STRING
    MAX-ACCESS  read-only
    STATUS      current
    DESCRIPTION
"
synchronization status line from file assp_sync.cfg for ldLDAPRoot
 0 - synchronization not configured
 1 - out of sync - running master mode
 2 - in sync - running  mastermode
 3 - in sync - running slave mode
 4 - in sync - running master mode (wait to reach state 2)
"
    ::= {ldLDAPRoot 6}

DNSSetup  OBJECT IDENTIFIER ::= {asspConfig 31}
DNSReuseSocket  OBJECT-TYPE
    SYNTAX      OCTET STRING
    MAX-ACCESS  read-write
    STATUS      current
    DESCRIPTION
"
If selected, assp will try to reuse DNS-UDP sockets as long as this is possible. Otherwise each DNS-query will create a new UDP socket for each DNS-Server. It is recommended to set this to on, because assp could use DNS-queries very extensive, which possibly forces the assp system and/or your DNS-servers to run out of available UDP sockets.
"
    REFERENCE "Reuse DNS UDP Sockets"
    DEFVAL { "1" }
    ::= {DNSSetup 477}

syncStatDNSReuseSocket  OBJECT-TYPE
    SYNTAX      OCTET STRING
    MAX-ACCESS  read-only
    STATUS      current
    DESCRIPTION
"
synchronization status for DNSReuseSocket
-1 - DNSReuseSocket could not be synchronized
 0 - synchronization not configured
 1 - out of sync - running master mode
 2 - in sync - running  mastermode
 3 - in sync - running slave mode
 4 - in sync - running master mode (wait to reach state 2)
"
    ::= {DNSReuseSocket 5}

syncStatStrDNSReuseSocket  OBJECT-TYPE
    SYNTAX      OCTET STRING
    MAX-ACCESS  read-only
    STATUS      current
    DESCRIPTION
"
synchronization status line from file assp_sync.cfg for DNSReuseSocket
 0 - synchronization not configured
 1 - out of sync - running master mode
 2 - in sync - running  mastermode
 3 - in sync - running slave mode
 4 - in sync - running master mode (wait to reach state 2)
"
    ::= {DNSReuseSocket 6}

UseLocalDNS  OBJECT-TYPE
    SYNTAX      OCTET STRING
    MAX-ACCESS  read-write
    STATUS      current
    DESCRIPTION
"
Use system default local DNS Name Servers. To use system default local DNS Servers and the configured DNSServers (below), unselect this option and define the system default local DNS Servers in addition below!
  To debug the DNS queries, switch on DebugSPF, even you don't use the SFF-check.
  All configured or local DNS Name Servers will be checked this may take some time if the servers are responding slow- please wait after apply changes!
"
    REFERENCE "Use Local DNS"
    DEFVAL { "1" }
    ::= {DNSSetup 735}

syncStatUseLocalDNS  OBJECT-TYPE
    SYNTAX      OCTET STRING
    MAX-ACCESS  read-only
    STATUS      current
    DESCRIPTION
"
synchronization status for UseLocalDNS
-1 - UseLocalDNS could not be synchronized
 0 - synchronization not configured
 1 - out of sync - running master mode
 2 - in sync - running  mastermode
 3 - in sync - running slave mode
 4 - in sync - running master mode (wait to reach state 2)
"
    ::= {UseLocalDNS 5}

syncStatStrUseLocalDNS  OBJECT-TYPE
    SYNTAX      OCTET STRING
    MAX-ACCESS  read-only
    STATUS      current
    DESCRIPTION
"
synchronization status line from file assp_sync.cfg for UseLocalDNS
 0 - synchronization not configured
 1 - out of sync - running master mode
 2 - in sync - running  mastermode
 3 - in sync - running slave mode
 4 - in sync - running master mode (wait to reach state 2)
"
    ::= {UseLocalDNS 6}

DNSResponseLog  OBJECT-TYPE
    SYNTAX      OCTET STRING
    MAX-ACCESS  read-write
    STATUS      current
    DESCRIPTION
"
You can use this to arrange DNSServers for better performance. Put the fastest first.
"
    REFERENCE "Show DNS Name Servers Response Time in Log"
    DEFVAL { "0" }
    ::= {DNSSetup 736}

syncStatDNSResponseLog  OBJECT-TYPE
    SYNTAX      OCTET STRING
    MAX-ACCESS  read-only
    STATUS      current
    DESCRIPTION
"
synchronization status for DNSResponseLog
-1 - DNSResponseLog could not be synchronized
 0 - synchronization not configured
 1 - out of sync - running master mode
 2 - in sync - running  mastermode
 3 - in sync - running slave mode
 4 - in sync - running master mode (wait to reach state 2)
"
    ::= {DNSResponseLog 5}

syncStatStrDNSResponseLog  OBJECT-TYPE
    SYNTAX      OCTET STRING
    MAX-ACCESS  read-only
    STATUS      current
    DESCRIPTION
"
synchronization status line from file assp_sync.cfg for DNSResponseLog
 0 - synchronization not configured
 1 - out of sync - running master mode
 2 - in sync - running  mastermode
 3 - in sync - running slave mode
 4 - in sync - running master mode (wait to reach state 2)
"
    ::= {DNSResponseLog 6}

DNSServers  OBJECT-TYPE
    SYNTAX      OCTET STRING
    MAX-ACCESS  read-write
    STATUS      current
    DESCRIPTION
"
DNS Name Servers IP's to use for DNSBL(RBL), RWL, URIBL, PTR, SPF2, SenderBase, NS, and DMARC lookups. Separate multiple entries by '|' or leave blank to use system defaults. At least TWO DNS-servers should be defined or used by the system! For example: 208.67.222.222|208.67.220.220 ().
  An DNS-query for the domain 'sourceforge.net' is used per default to measure the speed of the used DNS-servers. If you want assp to use another domain or hostname for this, append '=>domain.tld' at the end of the line - like: 208.67.222.222|208.67.220.220=>myhost.com
  To define the domain if you use the local DNS-servers 'UseLocalDNS' without defining any DNS-servers here, simply write '=>myhost.com'.
  To debug the DNS queries, switch on DebugSPF, even you don't use the SFF-check.
  NOTICE: don't define any public , ISP or open DNS-Servers (eg 208.67.222.222 208.67.220.220 8.8.8.8 8.8.4.4) , if you use any of the following assp checks: DNSBL(RBL), RWL, URIBL, SenderBase ! It is recommended in EVERY case to install (and to use) two local DNS-Servers!
  All configured or local DNS Name Servers will be checked this may take some time if the servers are responding slow - please wait after apply changes!
"
    REFERENCE "DNS Name Servers*"
    DEFVAL { "208.67.222.222|208.67.220.220" }
    ::= {DNSSetup 737}

syncStatDNSServers  OBJECT-TYPE
    SYNTAX      OCTET STRING
    MAX-ACCESS  read-only
    STATUS      current
    DESCRIPTION
"
synchronization status for DNSServers
-1 - DNSServers could not be synchronized
 0 - synchronization not configured
 1 - out of sync - running master mode
 2 - in sync - running  mastermode
 3 - in sync - running slave mode
 4 - in sync - running master mode (wait to reach state 2)
"
    ::= {DNSServers 5}

syncStatStrDNSServers  OBJECT-TYPE
    SYNTAX      OCTET STRING
    MAX-ACCESS  read-only
    STATUS      current
    DESCRIPTION
"
synchronization status line from file assp_sync.cfg for DNSServers
 0 - synchronization not configured
 1 - out of sync - running master mode
 2 - in sync - running  mastermode
 3 - in sync - running slave mode
 4 - in sync - running master mode (wait to reach state 2)
"
    ::= {DNSServers 6}

DNStimeout  OBJECT-TYPE
    SYNTAX      OCTET STRING
    MAX-ACCESS  read-write
    STATUS      current
    DESCRIPTION
"
Global DNS Query Timeout for DNSBL, RWL, URIBL, PTR, SPF, MX and A record lookups. The default is 2 seconds.
"
    REFERENCE "DNS Query Timeout"
    DEFVAL { "2" }
    ::= {DNSSetup 738}

syncStatDNStimeout  OBJECT-TYPE
    SYNTAX      OCTET STRING
    MAX-ACCESS  read-only
    STATUS      current
    DESCRIPTION
"
synchronization status for DNStimeout
-1 - DNStimeout could not be synchronized
 0 - synchronization not configured
 1 - out of sync - running master mode
 2 - in sync - running  mastermode
 3 - in sync - running slave mode
 4 - in sync - running master mode (wait to reach state 2)
"
    ::= {DNStimeout 5}

syncStatStrDNStimeout  OBJECT-TYPE
    SYNTAX      OCTET STRING
    MAX-ACCESS  read-only
    STATUS      current
    DESCRIPTION
"
synchronization status line from file assp_sync.cfg for DNStimeout
 0 - synchronization not configured
 1 - out of sync - running master mode
 2 - in sync - running  mastermode
 3 - in sync - running slave mode
 4 - in sync - running master mode (wait to reach state 2)
"
    ::= {DNStimeout 6}

DNSretry  OBJECT-TYPE
    SYNTAX      OCTET STRING
    MAX-ACCESS  read-write
    STATUS      current
    DESCRIPTION
"
Global DNS Query Retry. Set the number of times to try the query. The default is 1.
"
    REFERENCE "DNS Query Retry"
    DEFVAL { "1" }
    ::= {DNSSetup 739}

syncStatDNSretry  OBJECT-TYPE
    SYNTAX      OCTET STRING
    MAX-ACCESS  read-only
    STATUS      current
    DESCRIPTION
"
synchronization status for DNSretry
-1 - DNSretry could not be synchronized
 0 - synchronization not configured
 1 - out of sync - running master mode
 2 - in sync - running  mastermode
 3 - in sync - running slave mode
 4 - in sync - running master mode (wait to reach state 2)
"
    ::= {DNSretry 5}

syncStatStrDNSretry  OBJECT-TYPE
    SYNTAX      OCTET STRING
    MAX-ACCESS  read-only
    STATUS      current
    DESCRIPTION
"
synchronization status line from file assp_sync.cfg for DNSretry
 0 - synchronization not configured
 1 - out of sync - running master mode
 2 - in sync - running  mastermode
 3 - in sync - running slave mode
 4 - in sync - running master mode (wait to reach state 2)
"
    ::= {DNSretry 6}

DNSretrans  OBJECT-TYPE
    SYNTAX      OCTET STRING
    MAX-ACCESS  read-write
    STATUS      current
    DESCRIPTION
"
Global DNS Query Retransmission Interval. Set the retransmission interval. The default is 1.
  
"
    REFERENCE "DNS Query Retrans"
    DEFVAL { "1" }
    ::= {DNSSetup 740}

syncStatDNSretrans  OBJECT-TYPE
    SYNTAX      OCTET STRING
    MAX-ACCESS  read-only
    STATUS      current
    DESCRIPTION
"
synchronization status for DNSretrans
-1 - DNSretrans could not be synchronized
 0 - synchronization not configured
 1 - out of sync - running master mode
 2 - in sync - running  mastermode
 3 - in sync - running slave mode
 4 - in sync - running master mode (wait to reach state 2)
"
    ::= {DNSretrans 5}

syncStatStrDNSretrans  OBJECT-TYPE
    SYNTAX      OCTET STRING
    MAX-ACCESS  read-only
    STATUS      current
    DESCRIPTION
"
synchronization status line from file assp_sync.cfg for DNSretrans
 0 - synchronization not configured
 1 - out of sync - running master mode
 2 - in sync - running  mastermode
 3 - in sync - running slave mode
 4 - in sync - running master mode (wait to reach state 2)
"
    ::= {DNSretrans 6}

maxDNSRespDist  OBJECT-TYPE
    SYNTAX      OCTET STRING
    MAX-ACCESS  read-write
    STATUS      current
    DESCRIPTION
"
Maximum DNS Server responstime change in milliseconds before the query order of the name servers should be changed.
"
    REFERENCE "Maximum DNS Responstime change"
    DEFVAL { "50" }
    ::= {DNSSetup 980}

syncStatmaxDNSRespDist  OBJECT-TYPE
    SYNTAX      OCTET STRING
    MAX-ACCESS  read-only
    STATUS      current
    DESCRIPTION
"
synchronization status for maxDNSRespDist
-1 - maxDNSRespDist could not be synchronized
 0 - synchronization not configured
 1 - out of sync - running master mode
 2 - in sync - running  mastermode
 3 - in sync - running slave mode
 4 - in sync - running master mode (wait to reach state 2)
"
    ::= {maxDNSRespDist 5}

syncStatStrmaxDNSRespDist  OBJECT-TYPE
    SYNTAX      OCTET STRING
    MAX-ACCESS  read-only
    STATUS      current
    DESCRIPTION
"
synchronization status line from file assp_sync.cfg for maxDNSRespDist
 0 - synchronization not configured
 1 - out of sync - running master mode
 2 - in sync - running  mastermode
 3 - in sync - running slave mode
 4 - in sync - running master mode (wait to reach state 2)
"
    ::= {maxDNSRespDist 6}

ServerSetup  OBJECT IDENTIFIER ::= {asspConfig 32}
ConsoleCharset  OBJECT-TYPE
    SYNTAX      OCTET STRING
    MAX-ACCESS  read-write
    STATUS      current
    DESCRIPTION
"
Set the characterset/codepage for the console output to your local needs. Default is 'System Default' - default conversion. To display nonASCII characters on the console screen, setup UseUnicode4MaillogNames . Restart is required!
"
    REFERENCE "Charset for STDOUT and STDERR"
    DEFVAL { "0" }
    ::= {ServerSetup 741}

syncStatConsoleCharset  OBJECT-TYPE
    SYNTAX      OCTET STRING
    MAX-ACCESS  read-only
    STATUS      current
    DESCRIPTION
"
synchronization status for ConsoleCharset
-1 - ConsoleCharset could not be synchronized
 0 - synchronization not configured
 1 - out of sync - running master mode
 2 - in sync - running  mastermode
 3 - in sync - running slave mode
 4 - in sync - running master mode (wait to reach state 2)
"
    ::= {ConsoleCharset 5}

syncStatStrConsoleCharset  OBJECT-TYPE
    SYNTAX      OCTET STRING
    MAX-ACCESS  read-only
    STATUS      current
    DESCRIPTION
"
synchronization status line from file assp_sync.cfg for ConsoleCharset
 0 - synchronization not configured
 1 - out of sync - running master mode
 2 - in sync - running  mastermode
 3 - in sync - running slave mode
 4 - in sync - running master mode (wait to reach state 2)
"
    ::= {ConsoleCharset 6}

send250OK  OBJECT-TYPE
    SYNTAX      OCTET STRING
    MAX-ACCESS  read-write
    STATUS      current
    DESCRIPTION
"
Set this checkbox if you want ASSP to reply with '250 OK' instead of SMTP error code '554 5.7.1'. This will turn ASSP in some form of tarpit. 
"
    REFERENCE "Send 250 OK"
    DEFVAL { "" }
    ::= {ServerSetup 743}

syncStatsend250OK  OBJECT-TYPE
    SYNTAX      OCTET STRING
    MAX-ACCESS  read-only
    STATUS      current
    DESCRIPTION
"
synchronization status for send250OK
-1 - send250OK could not be synchronized
 0 - synchronization not configured
 1 - out of sync - running master mode
 2 - in sync - running  mastermode
 3 - in sync - running slave mode
 4 - in sync - running master mode (wait to reach state 2)
"
    ::= {send250OK 5}

syncStatStrsend250OK  OBJECT-TYPE
    SYNTAX      OCTET STRING
    MAX-ACCESS  read-only
    STATUS      current
    DESCRIPTION
"
synchronization status line from file assp_sync.cfg for send250OK
 0 - synchronization not configured
 1 - out of sync - running master mode
 2 - in sync - running  mastermode
 3 - in sync - running slave mode
 4 - in sync - running master mode (wait to reach state 2)
"
    ::= {send250OK 6}

AsADaemon  OBJECT-TYPE
    SYNTAX      OCTET STRING
    MAX-ACCESS  read-write
    STATUS      current
    DESCRIPTION
"
In Linux/BSD/Unix/OSX fork and close file handles. 
 Similar to the command 'perl assp.pl &amp;', but better.
 If 'externaly controlled' is selected, ASSP simply ends and you have to restart assp from your daemon or watchdog script
 If 'run AutoRestartCmd on restart and wait' is selected, assp starts the OS command defined in AutoRestartCmd - assp will NOT ! automaticaly terminate - the started command has to terminate/kill and to (re)start assp - like 'service assp restart'!
 If 'run AutoRestartCmd on restart and exit' is selected, assp starts the OS command defined in AutoRestartCmd and terminates immediatly!
   requires ASSP restart
"
    REFERENCE "Run ASSP as a Daemon"
    DEFVAL { "0" }
    ::= {ServerSetup 744}

syncStatAsADaemon  OBJECT-TYPE
    SYNTAX      OCTET STRING
    MAX-ACCESS  read-only
    STATUS      current
    DESCRIPTION
"
synchronization status for AsADaemon
-1 - AsADaemon could not be synchronized
 0 - synchronization not configured
 1 - out of sync - running master mode
 2 - in sync - running  mastermode
 3 - in sync - running slave mode
 4 - in sync - running master mode (wait to reach state 2)
"
    ::= {AsADaemon 5}

syncStatStrAsADaemon  OBJECT-TYPE
    SYNTAX      OCTET STRING
    MAX-ACCESS  read-only
    STATUS      current
    DESCRIPTION
"
synchronization status line from file assp_sync.cfg for AsADaemon
 0 - synchronization not configured
 1 - out of sync - running master mode
 2 - in sync - running  mastermode
 3 - in sync - running slave mode
 4 - in sync - running master mode (wait to reach state 2)
"
    ::= {AsADaemon 6}

runAsUser  OBJECT-TYPE
    SYNTAX      OCTET STRING
    MAX-ACCESS  read-write
    STATUS      current
    DESCRIPTION
"
The *nix user name to assume after startup (*nix only). use the autorestart features carefull, because any restart from inside ASSP will be done with the permission of this user! Examples: assp, nobody
   requires ASSP restart
"
    REFERENCE "Run as UID"
    DEFVAL { "" }
    ::= {ServerSetup 745}

syncStatrunAsUser  OBJECT-TYPE
    SYNTAX      OCTET STRING
    MAX-ACCESS  read-only
    STATUS      current
    DESCRIPTION
"
synchronization status for runAsUser
-1 - runAsUser could not be synchronized
 0 - synchronization not configured
 1 - out of sync - running master mode
 2 - in sync - running  mastermode
 3 - in sync - running slave mode
 4 - in sync - running master mode (wait to reach state 2)
"
    ::= {runAsUser 5}

syncStatStrrunAsUser  OBJECT-TYPE
    SYNTAX      OCTET STRING
    MAX-ACCESS  read-only
    STATUS      current
    DESCRIPTION
"
synchronization status line from file assp_sync.cfg for runAsUser
 0 - synchronization not configured
 1 - out of sync - running master mode
 2 - in sync - running  mastermode
 3 - in sync - running slave mode
 4 - in sync - running master mode (wait to reach state 2)
"
    ::= {runAsUser 6}

runAsGroup  OBJECT-TYPE
    SYNTAX      OCTET STRING
    MAX-ACCESS  read-write
    STATUS      current
    DESCRIPTION
"
The *nix group to assume after startup (*nix only).Examples: assp, nobody
   requires ASSP restart
"
    REFERENCE "Run as GID"
    DEFVAL { "" }
    ::= {ServerSetup 746}

syncStatrunAsGroup  OBJECT-TYPE
    SYNTAX      OCTET STRING
    MAX-ACCESS  read-only
    STATUS      current
    DESCRIPTION
"
synchronization status for runAsGroup
-1 - runAsGroup could not be synchronized
 0 - synchronization not configured
 1 - out of sync - running master mode
 2 - in sync - running  mastermode
 3 - in sync - running slave mode
 4 - in sync - running master mode (wait to reach state 2)
"
    ::= {runAsGroup 5}

syncStatStrrunAsGroup  OBJECT-TYPE
    SYNTAX      OCTET STRING
    MAX-ACCESS  read-only
    STATUS      current
    DESCRIPTION
"
synchronization status line from file assp_sync.cfg for runAsGroup
 0 - synchronization not configured
 1 - out of sync - running master mode
 2 - in sync - running  mastermode
 3 - in sync - running slave mode
 4 - in sync - running master mode (wait to reach state 2)
"
    ::= {runAsGroup 6}

ChangeRoot  OBJECT-TYPE
    SYNTAX      OCTET STRING
    MAX-ACCESS  read-write
    STATUS      current
    DESCRIPTION
"
The new root directory to which ASSP should chroot (*nix only). If blank, no chroot jail will be used. Note: if you use this feature, be sure to copy or link the etc/protocols file in your chroot jail.
   requires ASSP restart
"
    REFERENCE "Change Root"
    DEFVAL { "" }
    ::= {ServerSetup 747}

syncStatChangeRoot  OBJECT-TYPE
    SYNTAX      OCTET STRING
    MAX-ACCESS  read-only
    STATUS      current
    DESCRIPTION
"
synchronization status for ChangeRoot
-1 - ChangeRoot could not be synchronized
 0 - synchronization not configured
 1 - out of sync - running master mode
 2 - in sync - running  mastermode
 3 - in sync - running slave mode
 4 - in sync - running master mode (wait to reach state 2)
"
    ::= {ChangeRoot 5}

syncStatStrChangeRoot  OBJECT-TYPE
    SYNTAX      OCTET STRING
    MAX-ACCESS  read-only
    STATUS      current
    DESCRIPTION
"
synchronization status line from file assp_sync.cfg for ChangeRoot
 0 - synchronization not configured
 1 - out of sync - running master mode
 2 - in sync - running  mastermode
 3 - in sync - running slave mode
 4 - in sync - running master mode (wait to reach state 2)
"
    ::= {ChangeRoot 6}

setFilePermOnStart  OBJECT-TYPE
    SYNTAX      OCTET STRING
    MAX-ACCESS  read-write
    STATUS      current
    DESCRIPTION
"
If set, ASSP sets the permission of all ASSP- files and directories at startup to full (0777) - without any function on windows systems!
"
    REFERENCE "Set ASSP File Permission on Startup"
    DEFVAL { "" }
    ::= {ServerSetup 748}

syncStatsetFilePermOnStart  OBJECT-TYPE
    SYNTAX      OCTET STRING
    MAX-ACCESS  read-only
    STATUS      current
    DESCRIPTION
"
synchronization status for setFilePermOnStart
-1 - setFilePermOnStart could not be synchronized
 0 - synchronization not configured
 1 - out of sync - running master mode
 2 - in sync - running  mastermode
 3 - in sync - running slave mode
 4 - in sync - running master mode (wait to reach state 2)
"
    ::= {setFilePermOnStart 5}

syncStatStrsetFilePermOnStart  OBJECT-TYPE
    SYNTAX      OCTET STRING
    MAX-ACCESS  read-only
    STATUS      current
    DESCRIPTION
"
synchronization status line from file assp_sync.cfg for setFilePermOnStart
 0 - synchronization not configured
 1 - out of sync - running master mode
 2 - in sync - running  mastermode
 3 - in sync - running slave mode
 4 - in sync - running master mode (wait to reach state 2)
"
    ::= {setFilePermOnStart 6}

checkFilePermOnStart  OBJECT-TYPE
    SYNTAX      OCTET STRING
    MAX-ACCESS  read-write
    STATUS      current
    DESCRIPTION
"
If set, ASSP checks the permission of all ASSP- files and directories at startup - all files must be writable for the running job - the minimum permission is 0600 - without any function on windows systems!
"
    REFERENCE "Check ASSP File Permission on Startup"
    DEFVAL { "" }
    ::= {ServerSetup 749}

syncStatcheckFilePermOnStart  OBJECT-TYPE
    SYNTAX      OCTET STRING
    MAX-ACCESS  read-only
    STATUS      current
    DESCRIPTION
"
synchronization status for checkFilePermOnStart
-1 - checkFilePermOnStart could not be synchronized
 0 - synchronization not configured
 1 - out of sync - running master mode
 2 - in sync - running  mastermode
 3 - in sync - running slave mode
 4 - in sync - running master mode (wait to reach state 2)
"
    ::= {checkFilePermOnStart 5}

syncStatStrcheckFilePermOnStart  OBJECT-TYPE
    SYNTAX      OCTET STRING
    MAX-ACCESS  read-only
    STATUS      current
    DESCRIPTION
"
synchronization status line from file assp_sync.cfg for checkFilePermOnStart
 0 - synchronization not configured
 1 - out of sync - running master mode
 2 - in sync - running  mastermode
 3 - in sync - running slave mode
 4 - in sync - running master mode (wait to reach state 2)
"
    ::= {checkFilePermOnStart 6}

AutoRestart  OBJECT-TYPE
    SYNTAX      OCTET STRING
    MAX-ACCESS  read-write
    STATUS      current
    DESCRIPTION
"
If ASSP detects a main exception and it runs not as service or daemon, it will try to restart it self automaticly!  If running as daemon on nix/MAC , ASSP uses the action defined in AsADaemon to restart.
"
    REFERENCE "Automatic Restart after Exception"
    DEFVAL { "" }
    ::= {ServerSetup 750}

syncStatAutoRestart  OBJECT-TYPE
    SYNTAX      OCTET STRING
    MAX-ACCESS  read-only
    STATUS      current
    DESCRIPTION
"
synchronization status for AutoRestart
-1 - AutoRestart could not be synchronized
 0 - synchronization not configured
 1 - out of sync - running master mode
 2 - in sync - running  mastermode
 3 - in sync - running slave mode
 4 - in sync - running master mode (wait to reach state 2)
"
    ::= {AutoRestart 5}

syncStatStrAutoRestart  OBJECT-TYPE
    SYNTAX      OCTET STRING
    MAX-ACCESS  read-only
    STATUS      current
    DESCRIPTION
"
synchronization status line from file assp_sync.cfg for AutoRestart
 0 - synchronization not configured
 1 - out of sync - running master mode
 2 - in sync - running  mastermode
 3 - in sync - running slave mode
 4 - in sync - running master mode (wait to reach state 2)
"
    ::= {AutoRestart 6}

AutoRestartAfterCodeChange  OBJECT-TYPE
    SYNTAX      OCTET STRING
    MAX-ACCESS  read-write
    STATUS      current
    DESCRIPTION
"
If selected, ASSP will restart it self, if it detects a new or changed running script. An automatic restart will not be done, if ASSP is not running as a service on windows or as daemon on linux/MAC, and AutoRestartCmd is not configured. If running as daemon on linux/MAC ( AsADaemon ) ASSP simply ends - you have to restart assp from your daemon script. Leave this field empty to disable the feature. Possible values are 'immed and 1...23' . If set to 'immed', assp will restart within some seconds after a detected code change. If set to '1...23' the restart will be scheduled to that hour. A restart at 00:00 is not supported.
"
    REFERENCE "Automatic Restart ASSP on new or changed Script"
    DEFVAL { "" }
    ::= {ServerSetup 751}

syncStatAutoRestartAfterCodeChange  OBJECT-TYPE
    SYNTAX      OCTET STRING
    MAX-ACCESS  read-only
    STATUS      current
    DESCRIPTION
"
synchronization status for AutoRestartAfterCodeChange
-1 - AutoRestartAfterCodeChange could not be synchronized
 0 - synchronization not configured
 1 - out of sync - running master mode
 2 - in sync - running  mastermode
 3 - in sync - running slave mode
 4 - in sync - running master mode (wait to reach state 2)
"
    ::= {AutoRestartAfterCodeChange 5}

syncStatStrAutoRestartAfterCodeChange  OBJECT-TYPE
    SYNTAX      OCTET STRING
    MAX-ACCESS  read-only
    STATUS      current
    DESCRIPTION
"
synchronization status line from file assp_sync.cfg for AutoRestartAfterCodeChange
 0 - synchronization not configured
 1 - out of sync - running master mode
 2 - in sync - running  mastermode
 3 - in sync - running slave mode
 4 - in sync - running master mode (wait to reach state 2)
"
    ::= {AutoRestartAfterCodeChange 6}

AutoRestartCmd  OBJECT-TYPE
    SYNTAX      OCTET STRING
    MAX-ACCESS  read-write
    STATUS      current
    DESCRIPTION
"
The OS level shell-command that is used to autorestart ASSP, if it runs not as a service or daemon! A possible value for your system is:cmd.exe /C start 'ASSPSMTP restarted' 'C:\Perl\bin\perl.exe' 'C:\assp\assp.pl' 'C:/assp'</font>Leave this field blank, if ASSP runs inside an external loop (inside the OS like assp.sh or assp.cmd). If running on NIX systems and runAsUser and/or runAsGroup is used, don't forget to switch back to root permissions in the script!
"
    REFERENCE "OS-shell command for AutoRestart"
    DEFVAL { "" }
    ::= {ServerSetup 752}

syncStatAutoRestartCmd  OBJECT-TYPE
    SYNTAX      OCTET STRING
    MAX-ACCESS  read-only
    STATUS      current
    DESCRIPTION
"
synchronization status for AutoRestartCmd
-1 - AutoRestartCmd could not be synchronized
 0 - synchronization not configured
 1 - out of sync - running master mode
 2 - in sync - running  mastermode
 3 - in sync - running slave mode
 4 - in sync - running master mode (wait to reach state 2)
"
    ::= {AutoRestartCmd 5}

syncStatStrAutoRestartCmd  OBJECT-TYPE
    SYNTAX      OCTET STRING
    MAX-ACCESS  read-only
    STATUS      current
    DESCRIPTION
"
synchronization status line from file assp_sync.cfg for AutoRestartCmd
 0 - synchronization not configured
 1 - out of sync - running master mode
 2 - in sync - running  mastermode
 3 - in sync - running slave mode
 4 - in sync - running master mode (wait to reach state 2)
"
    ::= {AutoRestartCmd 6}

RestartEvery  OBJECT-TYPE
    SYNTAX      OCTET STRING
    MAX-ACCESS  read-write
    STATUS      current
    DESCRIPTION
"
ASSP will automatically terminate and restart after this many seconds. Use this setting to periodically reload configuration data, combat potential memory leaks, or perform shutdown/startup processes. This will only work properly if ASSP runs as a Windows service or in a script that restarts it after it stops or AutoRestartCmd is configured. Alternative to this field you can use ReStartSchedule, to schedule restarts.
"
    REFERENCE "Restart Timeout"
    DEFVAL { "0" }
    ::= {ServerSetup 753}

syncStatRestartEvery  OBJECT-TYPE
    SYNTAX      OCTET STRING
    MAX-ACCESS  read-only
    STATUS      current
    DESCRIPTION
"
synchronization status for RestartEvery
-1 - RestartEvery could not be synchronized
 0 - synchronization not configured
 1 - out of sync - running master mode
 2 - in sync - running  mastermode
 3 - in sync - running slave mode
 4 - in sync - running master mode (wait to reach state 2)
"
    ::= {RestartEvery 5}

syncStatStrRestartEvery  OBJECT-TYPE
    SYNTAX      OCTET STRING
    MAX-ACCESS  read-only
    STATUS      current
    DESCRIPTION
"
synchronization status line from file assp_sync.cfg for RestartEvery
 0 - synchronization not configured
 1 - out of sync - running master mode
 2 - in sync - running  mastermode
 3 - in sync - running slave mode
 4 - in sync - running master mode (wait to reach state 2)
"
    ::= {RestartEvery 6}

ReStartSchedule  OBJECT-TYPE
    SYNTAX      OCTET STRING
    MAX-ACCESS  read-write
    STATUS      current
    DESCRIPTION
"
If not set to 'noschedule' (noschedule is default), ASSP uses scheduled times to shutdown or restart ( AutoRestartCmd )! The syntax is the same like in ! To disable this Scheduler leave this field blank! Never write quotes in to this field!
This requires an installed  module in PERL.
Time and Date specification

Entry is the specification of the scheduled time in crontab format,
which contains five mandatory time and date fields.
Entry can be either a plain string, which contains
a whitespace separated time and date specification.

The time and date fields are (taken mostly from 'Vixie' cron):

<table BORDER CELLSPACING=0 CELLPADDING=4 WIDTH='50%' >
<tr><td>field</td><td>values</td></tr>
<tr><td>minute</td><td>0-59</td></tr>
<tr><td>hour</td><td>0-23</td></tr>
<tr><td>day of month</td><td>1-31</td></tr>
<tr><td>month</td><td>1-12 (or as names)</td></tr>
<tr><td>day of week</td><td>0-7 (0 or 7 is Sunday, or as names )</td></tr>
<tr><td>seconds</td><td>0-59 (optional) not supported inside ASSP !!!</td></tr>
</table>

 A field may be an asterisk (*), which always stands for
 'first-last'.

 Ranges of numbers are  allowed.  Ranges are two numbers
 separated  with  a  hyphen.   The  specified  range  is
 inclusive.   For example, 8-11  for an  'hours' entry
 specifies execution at hours 8, 9, 10 and 11.

 Lists  are allowed.   A list  is a  set of  numbers (or
 ranges)  separated by  commas.   Examples: '1,2,5,9',
 '0-4,8-12'.

 Step  values can  be used  in conjunction  with ranges.
 Following a range with '/<number>' specifies skips of
 the  numbers value  through the  range.   For example,
 '0-23/2' can  be used in  the hours field  to specify
 command execution every  other hour (the alternative in
 the V7 standard is '0,2,4,6,8,10,12,14,16,18,20,22').
 Steps are  also permitted after an asterisk,  so if you
 want to say 'every two hours', just use '*/2'.

 Names can also  be used for the 'month'  and 'day of
 week'  fields.  Use  the  first three  letters of  the
 particular day or month (case doesn't matter).

 Note:
       The day of a command's execution can be specified
       by two fields  -- day of month, and  day of week.
       If both fields are restricted (ie, aren't *), the
       command will be run when either field matches the
       current  time.  For  example, '30  4 1,15  * 5'
       would cause a command to be run at 4:30 am on the
       1st and 15th of each month, plus every Friday

Examples:

<table BORDER CELLSPACING=0 CELLPADDING=4 WIDTH='80%' >
<tr><td>8 0 * * *</td><td>==></td><td>8 minutes after midnight, every day</td></tr>
<tr><td>5 11 * * Sat,Sun</td><td>==></td><td>at 11:05 on each Saturday and Sunday</td></tr>
<tr><td>0-59/5 * * * *</td><td>==></td><td>every five minutes</td></tr>
<tr><td>42 12 3 Feb Sat</td><td>==></td><td>at 12:42 on 3rd of February and on each Saturday in February</td></tr>
<tr><td>32 11 * * * 0-30/2</td><td>==></td><td>11:32:00, 11:32:02, ... 11:32:30 every day</td></tr>
</table>

In addition, ranges or lists of names are allowed.
If you want to define multiple entries separate them by '|'
"
    REFERENCE "Schedule Cron time for ASSP Restart"
    DEFVAL { "noschedule" }
    ::= {ServerSetup 754}

syncStatReStartSchedule  OBJECT-TYPE
    SYNTAX      OCTET STRING
    MAX-ACCESS  read-only
    STATUS      current
    DESCRIPTION
"
synchronization status for ReStartSchedule
-1 - ReStartSchedule could not be synchronized
 0 - synchronization not configured
 1 - out of sync - running master mode
 2 - in sync - running  mastermode
 3 - in sync - running slave mode
 4 - in sync - running master mode (wait to reach state 2)
"
    ::= {ReStartSchedule 5}

syncStatStrReStartSchedule  OBJECT-TYPE
    SYNTAX      OCTET STRING
    MAX-ACCESS  read-only
    STATUS      current
    DESCRIPTION
"
synchronization status line from file assp_sync.cfg for ReStartSchedule
 0 - synchronization not configured
 1 - out of sync - running master mode
 2 - in sync - running  mastermode
 3 - in sync - running slave mode
 4 - in sync - running master mode (wait to reach state 2)
"
    ::= {ReStartSchedule 6}

myName  OBJECT-TYPE
    SYNTAX      OCTET STRING
    MAX-ACCESS  read-write
    STATUS      current
    DESCRIPTION
"
ASSP will identify itself by this name in the email 'Received:' header and in the helo when sending report-replies. Usually the fully qualified domain name of the host.Examples: assp.mydomain.com, ASSP.nospam
"
    REFERENCE "My Name"
    DEFVAL { "ASSP.nospam" }
    ::= {ServerSetup 755}

myHelo  OBJECT-TYPE
    SYNTAX      OCTET STRING
    MAX-ACCESS  read-write
    STATUS      current
    DESCRIPTION
"
How ASSP will identify itself when connecting to the target MTA.
  transparent - the Helo of the sender will be used
  use myName - myName will be used
  use FQDN - fully qualified domain name of the host assp is running on
"
    REFERENCE "My Helo"
    DEFVAL { "0" }
    ::= {ServerSetup 756}

syncStatmyHelo  OBJECT-TYPE
    SYNTAX      OCTET STRING
    MAX-ACCESS  read-only
    STATUS      current
    DESCRIPTION
"
synchronization status for myHelo
-1 - myHelo could not be synchronized
 0 - synchronization not configured
 1 - out of sync - running master mode
 2 - in sync - running  mastermode
 3 - in sync - running slave mode
 4 - in sync - running master mode (wait to reach state 2)
"
    ::= {myHelo 5}

syncStatStrmyHelo  OBJECT-TYPE
    SYNTAX      OCTET STRING
    MAX-ACCESS  read-only
    STATUS      current
    DESCRIPTION
"
synchronization status line from file assp_sync.cfg for myHelo
 0 - synchronization not configured
 1 - out of sync - running master mode
 2 - in sync - running  mastermode
 3 - in sync - running slave mode
 4 - in sync - running master mode (wait to reach state 2)
"
    ::= {myHelo 6}

asspCfg  OBJECT-TYPE
    SYNTAX      OCTET STRING
    MAX-ACCESS  read-write
    STATUS      current
    DESCRIPTION
"
For internal use only - it is assp.cfg file. Do not change this value.
"
    REFERENCE "assp.cfg*"
    DEFVAL { "file:assp.cfg" }
    ::= {ServerSetup 757}

AutoReloadCfg  OBJECT-TYPE
    SYNTAX      OCTET STRING
    MAX-ACCESS  read-write
    STATUS      current
    DESCRIPTION
"
If selected and the assp.cfg file is changed externaly, ASSP will reload the configuration from the file automaticly.
"
    REFERENCE "Automatic Reload ConfigFile"
    DEFVAL { "" }
    ::= {ServerSetup 758}

syncStatAutoReloadCfg  OBJECT-TYPE
    SYNTAX      OCTET STRING
    MAX-ACCESS  read-only
    STATUS      current
    DESCRIPTION
"
synchronization status for AutoReloadCfg
-1 - AutoReloadCfg could not be synchronized
 0 - synchronization not configured
 1 - out of sync - running master mode
 2 - in sync - running  mastermode
 3 - in sync - running slave mode
 4 - in sync - running master mode (wait to reach state 2)
"
    ::= {AutoReloadCfg 5}

syncStatStrAutoReloadCfg  OBJECT-TYPE
    SYNTAX      OCTET STRING
    MAX-ACCESS  read-only
    STATUS      current
    DESCRIPTION
"
synchronization status line from file assp_sync.cfg for AutoReloadCfg
 0 - synchronization not configured
 1 - out of sync - running master mode
 2 - in sync - running  mastermode
 3 - in sync - running slave mode
 4 - in sync - running master mode (wait to reach state 2)
"
    ::= {AutoReloadCfg 6}

asspCfgVersion  OBJECT-TYPE
    SYNTAX      OCTET STRING
    MAX-ACCESS  read-write
    STATUS      current
    DESCRIPTION
"
ASSP will identify the assp.cfg file. Do not change this.
"
    REFERENCE "assp.cfg version"
    DEFVAL { "" }
    ::= {ServerSetup 759}

proxyserver  OBJECT-TYPE
    SYNTAX      OCTET STRING
    MAX-ACCESS  read-write
    STATUS      current
    DESCRIPTION
"
The Proxy Server to use when uploading global statistics and downloading the greylist.Examples: 192.168.0.1:8080, 192.168.0.1
"
    REFERENCE "Proxy Server"
    DEFVAL { "" }
    ::= {ServerSetup 760}

syncStatproxyserver  OBJECT-TYPE
    SYNTAX      OCTET STRING
    MAX-ACCESS  read-only
    STATUS      current
    DESCRIPTION
"
synchronization status for proxyserver
-1 - proxyserver could not be synchronized
 0 - synchronization not configured
 1 - out of sync - running master mode
 2 - in sync - running  mastermode
 3 - in sync - running slave mode
 4 - in sync - running master mode (wait to reach state 2)
"
    ::= {proxyserver 5}

syncStatStrproxyserver  OBJECT-TYPE
    SYNTAX      OCTET STRING
    MAX-ACCESS  read-only
    STATUS      current
    DESCRIPTION
"
synchronization status line from file assp_sync.cfg for proxyserver
 0 - synchronization not configured
 1 - out of sync - running master mode
 2 - in sync - running  mastermode
 3 - in sync - running slave mode
 4 - in sync - running master mode (wait to reach state 2)
"
    ::= {proxyserver 6}

proxyuser  OBJECT-TYPE
    SYNTAX      OCTET STRING
    MAX-ACCESS  read-write
    STATUS      current
    DESCRIPTION
"
The Proxy-UserName that is used to authenticate to the proxy.
"
    REFERENCE "Proxy User"
    DEFVAL { "" }
    ::= {ServerSetup 761}

syncStatproxyuser  OBJECT-TYPE
    SYNTAX      OCTET STRING
    MAX-ACCESS  read-only
    STATUS      current
    DESCRIPTION
"
synchronization status for proxyuser
-1 - proxyuser could not be synchronized
 0 - synchronization not configured
 1 - out of sync - running master mode
 2 - in sync - running  mastermode
 3 - in sync - running slave mode
 4 - in sync - running master mode (wait to reach state 2)
"
    ::= {proxyuser 5}

syncStatStrproxyuser  OBJECT-TYPE
    SYNTAX      OCTET STRING
    MAX-ACCESS  read-only
    STATUS      current
    DESCRIPTION
"
synchronization status line from file assp_sync.cfg for proxyuser
 0 - synchronization not configured
 1 - out of sync - running master mode
 2 - in sync - running  mastermode
 3 - in sync - running slave mode
 4 - in sync - running master mode (wait to reach state 2)
"
    ::= {proxyuser 6}

proxypass  OBJECT-TYPE
    SYNTAX      OCTET STRING
    MAX-ACCESS  read-write
    STATUS      current
    DESCRIPTION
"
The password for Proxy-UserName that is used to authenticate to the proxy.
"
    REFERENCE "Proxy Password"
    DEFVAL { "" }
    ::= {ServerSetup 762}

syncStatproxypass  OBJECT-TYPE
    SYNTAX      OCTET STRING
    MAX-ACCESS  read-only
    STATUS      current
    DESCRIPTION
"
synchronization status for proxypass
-1 - proxypass could not be synchronized
 0 - synchronization not configured
 1 - out of sync - running master mode
 2 - in sync - running  mastermode
 3 - in sync - running slave mode
 4 - in sync - running master mode (wait to reach state 2)
"
    ::= {proxypass 5}

syncStatStrproxypass  OBJECT-TYPE
    SYNTAX      OCTET STRING
    MAX-ACCESS  read-only
    STATUS      current
    DESCRIPTION
"
synchronization status line from file assp_sync.cfg for proxypass
 0 - synchronization not configured
 1 - out of sync - running master mode
 2 - in sync - running  mastermode
 3 - in sync - running slave mode
 4 - in sync - running master mode (wait to reach state 2)
"
    ::= {proxypass 6}

webAdminPort  OBJECT-TYPE
    SYNTAX      OCTET STRING
    MAX-ACCESS  read-write
    STATUS      current
    DESCRIPTION
"
The port on which ASSP will listen for http connections to the web administration interface. If you change this, after you click Apply you must change the URL on your browser to reconnect. You may also supply an IP address or hostname to limit connections to a specific interface. Separate multiple entries by pipe '|'!Examples: 55555, 192.168.0.5:12345, myhost:12345, 192.168.0.5:22345|myhost:12345
"
    REFERENCE "Web Admin Port"
    DEFVAL { "55555" }
    ::= {ServerSetup 763}

syncStatwebAdminPort  OBJECT-TYPE
    SYNTAX      OCTET STRING
    MAX-ACCESS  read-only
    STATUS      current
    DESCRIPTION
"
synchronization status for webAdminPort
-1 - webAdminPort could not be synchronized
 0 - synchronization not configured
 1 - out of sync - running master mode
 2 - in sync - running  mastermode
 3 - in sync - running slave mode
 4 - in sync - running master mode (wait to reach state 2)
"
    ::= {webAdminPort 5}

syncStatStrwebAdminPort  OBJECT-TYPE
    SYNTAX      OCTET STRING
    MAX-ACCESS  read-only
    STATUS      current
    DESCRIPTION
"
synchronization status line from file assp_sync.cfg for webAdminPort
 0 - synchronization not configured
 1 - out of sync - running master mode
 2 - in sync - running  mastermode
 3 - in sync - running slave mode
 4 - in sync - running master mode (wait to reach state 2)
"
    ::= {webAdminPort 6}

enableWebAdminSSL  OBJECT-TYPE
    SYNTAX      OCTET STRING
    MAX-ACCESS  read-write
    STATUS      current
    DESCRIPTION
"
If selected the web admin interface will be only accessable via https. If you change this, after you click Apply you must change the URL on your browser to reconnect.
  This requires an installed  module in PERL.
  A server-certificate-file 'certs/server-cert.pem' and a server-key-file 'certs/server-key.pem' must exist and must be valid!
  If you do not have valid certificates, you may generate both files online with  or you may use OpenSSL to generate ! More configuration options are webSSLRequireCientCert, SSLWEBCertVerifyCB and SSLWEBConfigure .
"
    REFERENCE "Use https instead of http"
    DEFVAL { "" }
    ::= {ServerSetup 764}

syncStatenableWebAdminSSL  OBJECT-TYPE
    SYNTAX      OCTET STRING
    MAX-ACCESS  read-only
    STATUS      current
    DESCRIPTION
"
synchronization status for enableWebAdminSSL
-1 - enableWebAdminSSL could not be synchronized
 0 - synchronization not configured
 1 - out of sync - running master mode
 2 - in sync - running  mastermode
 3 - in sync - running slave mode
 4 - in sync - running master mode (wait to reach state 2)
"
    ::= {enableWebAdminSSL 5}

syncStatStrenableWebAdminSSL  OBJECT-TYPE
    SYNTAX      OCTET STRING
    MAX-ACCESS  read-only
    STATUS      current
    DESCRIPTION
"
synchronization status line from file assp_sync.cfg for enableWebAdminSSL
 0 - synchronization not configured
 1 - out of sync - running master mode
 2 - in sync - running  mastermode
 3 - in sync - running slave mode
 4 - in sync - running master mode (wait to reach state 2)
"
    ::= {enableWebAdminSSL 6}

webAdminPassword  OBJECT-TYPE
    SYNTAX      OCTET STRING
    MAX-ACCESS  read-write
    STATUS      current
    DESCRIPTION
"
The password for the web administration interface for user root(minimum of 5 characters).
  DO NOT use the digits '45' as the first two characters of the password or you will be not able to login ever again!
  If root is logged on, no other logins are allowed. Always use the 'logoff'-button as root to terminate the session - closing the browser without logoff could cause other session to be disallowed.
"
    REFERENCE "Web Admin Password - Masterpassword (root)"
    DEFVAL { "nospam4me" }
    ::= {ServerSetup 765}

syncStatwebAdminPassword  OBJECT-TYPE
    SYNTAX      OCTET STRING
    MAX-ACCESS  read-only
    STATUS      current
    DESCRIPTION
"
synchronization status for webAdminPassword
-1 - webAdminPassword could not be synchronized
 0 - synchronization not configured
 1 - out of sync - running master mode
 2 - in sync - running  mastermode
 3 - in sync - running slave mode
 4 - in sync - running master mode (wait to reach state 2)
"
    ::= {webAdminPassword 5}

syncStatStrwebAdminPassword  OBJECT-TYPE
    SYNTAX      OCTET STRING
    MAX-ACCESS  read-only
    STATUS      current
    DESCRIPTION
"
synchronization status line from file assp_sync.cfg for webAdminPassword
 0 - synchronization not configured
 1 - out of sync - running master mode
 2 - in sync - running  mastermode
 3 - in sync - running slave mode
 4 - in sync - running master mode (wait to reach state 2)
"
    ::= {webAdminPassword 6}

allowAdminConnectionsFrom  OBJECT-TYPE
    SYNTAX      OCTET STRING
    MAX-ACCESS  read-write
    STATUS      current
    DESCRIPTION
"
An optional list of IP addresses and/or hostnames from which you will accept web admin connections. Blank means accept connections from any IP address. Note: if you make a mistake here, you may disable your web administration interface and be forced to manualy edit your configuration file to fix it.Examples:
  127.0.0.1|172.16.
"
    REFERENCE "Only Allow Admin Connections From*"
    DEFVAL { "" }
    ::= {ServerSetup 766}

syncStatallowAdminConnectionsFrom  OBJECT-TYPE
    SYNTAX      OCTET STRING
    MAX-ACCESS  read-only
    STATUS      current
    DESCRIPTION
"
synchronization status for allowAdminConnectionsFrom
-1 - allowAdminConnectionsFrom could not be synchronized
 0 - synchronization not configured
 1 - out of sync - running master mode
 2 - in sync - running  mastermode
 3 - in sync - running slave mode
 4 - in sync - running master mode (wait to reach state 2)
"
    ::= {allowAdminConnectionsFrom 5}

syncStatStrallowAdminConnectionsFrom  OBJECT-TYPE
    SYNTAX      OCTET STRING
    MAX-ACCESS  read-only
    STATUS      current
    DESCRIPTION
"
synchronization status line from file assp_sync.cfg for allowAdminConnectionsFrom
 0 - synchronization not configured
 1 - out of sync - running master mode
 2 - in sync - running  mastermode
 3 - in sync - running slave mode
 4 - in sync - running master mode (wait to reach state 2)
"
    ::= {allowAdminConnectionsFrom 6}

webStatPort  OBJECT-TYPE
    SYNTAX      OCTET STRING
    MAX-ACCESS  read-write
    STATUS      current
    DESCRIPTION
"
The port on which ASSP will listen for http or telnet connections to the statistics interface. You may also supply an IP address to limit connections to a specific interface. Only one value is supported!
   The stats are available via browser or telnet (or telnet similar socket). Using telnet, press ENTER two times to get the healthy state ('$Config{webStatHealthyResp} [CRLF]' or '$Config{webStatNotHealthyResp} [CRLF]' in a single line), this is the recommended methode to get the 'UP'-state of assp from nagios or any other external script.
   Type 'stat[ENTER][ENTER]' to get the STATS in raw text where each line is terminated with '[CR]LF' (CR is send in any case, if the request contains CR).
   The HTML output are LF terminated STAT lines.Examples: 55553, 192.168.0.5:12345
"
    REFERENCE "Raw Statistics Port"
    DEFVAL { "55553" }
    ::= {ServerSetup 767}

syncStatwebStatPort  OBJECT-TYPE
    SYNTAX      OCTET STRING
    MAX-ACCESS  read-only
    STATUS      current
    DESCRIPTION
"
synchronization status for webStatPort
-1 - webStatPort could not be synchronized
 0 - synchronization not configured
 1 - out of sync - running master mode
 2 - in sync - running  mastermode
 3 - in sync - running slave mode
 4 - in sync - running master mode (wait to reach state 2)
"
    ::= {webStatPort 5}

syncStatStrwebStatPort  OBJECT-TYPE
    SYNTAX      OCTET STRING
    MAX-ACCESS  read-only
    STATUS      current
    DESCRIPTION
"
synchronization status line from file assp_sync.cfg for webStatPort
 0 - synchronization not configured
 1 - out of sync - running master mode
 2 - in sync - running  mastermode
 3 - in sync - running slave mode
 4 - in sync - running master mode (wait to reach state 2)
"
    ::= {webStatPort 6}

enableWebStatSSL  OBJECT-TYPE
    SYNTAX      OCTET STRING
    MAX-ACCESS  read-write
    STATUS      current
    DESCRIPTION
"
The web stat interface will be only accessable via https.
  This requires an installed  module in PERL.
  A server-certificate-file 'certs/server-cert.pem' and a server-key-file 'certs/server-key.pem' must exits and must be valid! More configuration options are statSSLRequireClientCert, SSLSTATCertVerifyCB and SSLSTATConfigure .
"
    REFERENCE "Use https instead of http"
    DEFVAL { "" }
    ::= {ServerSetup 768}

syncStatenableWebStatSSL  OBJECT-TYPE
    SYNTAX      OCTET STRING
    MAX-ACCESS  read-only
    STATUS      current
    DESCRIPTION
"
synchronization status for enableWebStatSSL
-1 - enableWebStatSSL could not be synchronized
 0 - synchronization not configured
 1 - out of sync - running master mode
 2 - in sync - running  mastermode
 3 - in sync - running slave mode
 4 - in sync - running master mode (wait to reach state 2)
"
    ::= {enableWebStatSSL 5}

syncStatStrenableWebStatSSL  OBJECT-TYPE
    SYNTAX      OCTET STRING
    MAX-ACCESS  read-only
    STATUS      current
    DESCRIPTION
"
synchronization status line from file assp_sync.cfg for enableWebStatSSL
 0 - synchronization not configured
 1 - out of sync - running master mode
 2 - in sync - running  mastermode
 3 - in sync - running slave mode
 4 - in sync - running master mode (wait to reach state 2)
"
    ::= {enableWebStatSSL 6}

allowStatConnectionsFrom  OBJECT-TYPE
    SYNTAX      OCTET STRING
    MAX-ACCESS  read-write
    STATUS      current
    DESCRIPTION
"
An optional list of IP addresses from which you will accept raw statistical connections. Blank means accept connections from any IP address. Examples:
 127.0.0.1|172.16.
"
    REFERENCE "Only Allow Raw Statistics Connections From*"
    DEFVAL { "127.0.0.1" }
    ::= {ServerSetup 769}

syncStatallowStatConnectionsFrom  OBJECT-TYPE
    SYNTAX      OCTET STRING
    MAX-ACCESS  read-only
    STATUS      current
    DESCRIPTION
"
synchronization status for allowStatConnectionsFrom
-1 - allowStatConnectionsFrom could not be synchronized
 0 - synchronization not configured
 1 - out of sync - running master mode
 2 - in sync - running  mastermode
 3 - in sync - running slave mode
 4 - in sync - running master mode (wait to reach state 2)
"
    ::= {allowStatConnectionsFrom 5}

syncStatStrallowStatConnectionsFrom  OBJECT-TYPE
    SYNTAX      OCTET STRING
    MAX-ACCESS  read-only
    STATUS      current
    DESCRIPTION
"
synchronization status line from file assp_sync.cfg for allowStatConnectionsFrom
 0 - synchronization not configured
 1 - out of sync - running master mode
 2 - in sync - running  mastermode
 3 - in sync - running slave mode
 4 - in sync - running master mode (wait to reach state 2)
"
    ::= {allowStatConnectionsFrom 6}

EnableHTTPCompression  OBJECT-TYPE
    SYNTAX      OCTET STRING
    MAX-ACCESS  read-write
    STATUS      current
    DESCRIPTION
"
Enable HTTP Compression for faster web administration interface loading. The perl module  is required to use this feature.
"
    REFERENCE "Enable HTTP Compression in GUI"
    DEFVAL { "1" }
    ::= {ServerSetup 770}

syncStatEnableHTTPCompression  OBJECT-TYPE
    SYNTAX      OCTET STRING
    MAX-ACCESS  read-only
    STATUS      current
    DESCRIPTION
"
synchronization status for EnableHTTPCompression
-1 - EnableHTTPCompression could not be synchronized
 0 - synchronization not configured
 1 - out of sync - running master mode
 2 - in sync - running  mastermode
 3 - in sync - running slave mode
 4 - in sync - running master mode (wait to reach state 2)
"
    ::= {EnableHTTPCompression 5}

syncStatStrEnableHTTPCompression  OBJECT-TYPE
    SYNTAX      OCTET STRING
    MAX-ACCESS  read-only
    STATUS      current
    DESCRIPTION
"
synchronization status line from file assp_sync.cfg for EnableHTTPCompression
 0 - synchronization not configured
 1 - out of sync - running master mode
 2 - in sync - running  mastermode
 3 - in sync - running slave mode
 4 - in sync - running master mode (wait to reach state 2)
"
    ::= {EnableHTTPCompression 6}

EnableFloatingMenu  OBJECT-TYPE
    SYNTAX      OCTET STRING
    MAX-ACCESS  read-write
    STATUS      current
    DESCRIPTION
"
Allow the menu panel on the web administration interface to float (floating Div code taken from ).
"
    REFERENCE "Enable Floating Menu Panel in GUI"
    DEFVAL { "" }
    ::= {ServerSetup 771}

syncStatEnableFloatingMenu  OBJECT-TYPE
    SYNTAX      OCTET STRING
    MAX-ACCESS  read-only
    STATUS      current
    DESCRIPTION
"
synchronization status for EnableFloatingMenu
-1 - EnableFloatingMenu could not be synchronized
 0 - synchronization not configured
 1 - out of sync - running master mode
 2 - in sync - running  mastermode
 3 - in sync - running slave mode
 4 - in sync - running master mode (wait to reach state 2)
"
    ::= {EnableFloatingMenu 5}

syncStatStrEnableFloatingMenu  OBJECT-TYPE
    SYNTAX      OCTET STRING
    MAX-ACCESS  read-only
    STATUS      current
    DESCRIPTION
"
synchronization status line from file assp_sync.cfg for EnableFloatingMenu
 0 - synchronization not configured
 1 - out of sync - running master mode
 2 - in sync - running  mastermode
 3 - in sync - running slave mode
 4 - in sync - running master mode (wait to reach state 2)
"
    ::= {EnableFloatingMenu 6}

hideAlphaIndex  OBJECT-TYPE
    SYNTAX      OCTET STRING
    MAX-ACCESS  read-write
    STATUS      current
    DESCRIPTION
"
Removes the index panel on the left side in the GUI, but the index is accessable by clicking on 'Sorted'.
"
    REFERENCE "Hide the Alpha Index Menu Panel in GUI"
    DEFVAL { "" }
    ::= {ServerSetup 772}

syncStathideAlphaIndex  OBJECT-TYPE
    SYNTAX      OCTET STRING
    MAX-ACCESS  read-only
    STATUS      current
    DESCRIPTION
"
synchronization status for hideAlphaIndex
-1 - hideAlphaIndex could not be synchronized
 0 - synchronization not configured
 1 - out of sync - running master mode
 2 - in sync - running  mastermode
 3 - in sync - running slave mode
 4 - in sync - running master mode (wait to reach state 2)
"
    ::= {hideAlphaIndex 5}

syncStatStrhideAlphaIndex  OBJECT-TYPE
    SYNTAX      OCTET STRING
    MAX-ACCESS  read-only
    STATUS      current
    DESCRIPTION
"
synchronization status line from file assp_sync.cfg for hideAlphaIndex
 0 - synchronization not configured
 1 - out of sync - running master mode
 2 - in sync - running  mastermode
 3 - in sync - running slave mode
 4 - in sync - running master mode (wait to reach state 2)
"
    ::= {hideAlphaIndex 6}

IndexSlideSpeed  OBJECT-TYPE
    SYNTAX      OCTET STRING
    MAX-ACCESS  read-write
    STATUS      current
    DESCRIPTION
"
Adjust the sliding speed of the Alpha Index Menu Panel in GUI to your needs.
"
    REFERENCE "Sliding Speed of the Alpha Index Menu Panel in GUI"
    DEFVAL { "10" }
    ::= {ServerSetup 773}

syncStatIndexSlideSpeed  OBJECT-TYPE
    SYNTAX      OCTET STRING
    MAX-ACCESS  read-only
    STATUS      current
    DESCRIPTION
"
synchronization status for IndexSlideSpeed
-1 - IndexSlideSpeed could not be synchronized
 0 - synchronization not configured
 1 - out of sync - running master mode
 2 - in sync - running  mastermode
 3 - in sync - running slave mode
 4 - in sync - running master mode (wait to reach state 2)
"
    ::= {IndexSlideSpeed 5}

syncStatStrIndexSlideSpeed  OBJECT-TYPE
    SYNTAX      OCTET STRING
    MAX-ACCESS  read-only
    STATUS      current
    DESCRIPTION
"
synchronization status line from file assp_sync.cfg for IndexSlideSpeed
 0 - synchronization not configured
 1 - out of sync - running master mode
 2 - in sync - running  mastermode
 3 - in sync - running slave mode
 4 - in sync - running master mode (wait to reach state 2)
"
    ::= {IndexSlideSpeed 6}

EnableInternalNamesInDesc  OBJECT-TYPE
    SYNTAX      OCTET STRING
    MAX-ACCESS  read-write
    STATUS      current
    DESCRIPTION
"
Show the internal names in the web interface. The internal names are used in the configuration file (assp.cfg), in the application code, and in the menu bar on the left side of the GUI.
"
    REFERENCE "Show Internal Names in the GUI"
    DEFVAL { "1" }
    ::= {ServerSetup 774}

syncStatEnableInternalNamesInDesc  OBJECT-TYPE
    SYNTAX      OCTET STRING
    MAX-ACCESS  read-only
    STATUS      current
    DESCRIPTION
"
synchronization status for EnableInternalNamesInDesc
-1 - EnableInternalNamesInDesc could not be synchronized
 0 - synchronization not configured
 1 - out of sync - running master mode
 2 - in sync - running  mastermode
 3 - in sync - running slave mode
 4 - in sync - running master mode (wait to reach state 2)
"
    ::= {EnableInternalNamesInDesc 5}

syncStatStrEnableInternalNamesInDesc  OBJECT-TYPE
    SYNTAX      OCTET STRING
    MAX-ACCESS  read-only
    STATUS      current
    DESCRIPTION
"
synchronization status line from file assp_sync.cfg for EnableInternalNamesInDesc
 0 - synchronization not configured
 1 - out of sync - running master mode
 2 - in sync - running  mastermode
 3 - in sync - running slave mode
 4 - in sync - running master mode (wait to reach state 2)
"
    ::= {EnableInternalNamesInDesc 6}

MaillogTailJump  OBJECT-TYPE
    SYNTAX      OCTET STRING
    MAX-ACCESS  read-write
    STATUS      current
    DESCRIPTION
"
Causes the browser window to jump to the bottom of the maillog instead of sitting at the top of the display.
"
    REFERENCE "Jump to the End of the Maillog"
    DEFVAL { "" }
    ::= {ServerSetup 775}

syncStatMaillogTailJump  OBJECT-TYPE
    SYNTAX      OCTET STRING
    MAX-ACCESS  read-only
    STATUS      current
    DESCRIPTION
"
synchronization status for MaillogTailJump
-1 - MaillogTailJump could not be synchronized
 0 - synchronization not configured
 1 - out of sync - running master mode
 2 - in sync - running  mastermode
 3 - in sync - running slave mode
 4 - in sync - running master mode (wait to reach state 2)
"
    ::= {MaillogTailJump 5}

syncStatStrMaillogTailJump  OBJECT-TYPE
    SYNTAX      OCTET STRING
    MAX-ACCESS  read-only
    STATUS      current
    DESCRIPTION
"
synchronization status line from file assp_sync.cfg for MaillogTailJump
 0 - synchronization not configured
 1 - out of sync - running master mode
 2 - in sync - running  mastermode
 3 - in sync - running slave mode
 4 - in sync - running master mode (wait to reach state 2)
"
    ::= {MaillogTailJump 6}

MaillogTailBytes  OBJECT-TYPE
    SYNTAX      OCTET STRING
    MAX-ACCESS  read-write
    STATUS      current
    DESCRIPTION
"
The number of bytes that will be shown when the end of the maillog is viewed. The default value is 10000.
"
    REFERENCE "Maillog Tail Bytes"
    DEFVAL { "10000" }
    ::= {ServerSetup 776}

syncStatMaillogTailBytes  OBJECT-TYPE
    SYNTAX      OCTET STRING
    MAX-ACCESS  read-only
    STATUS      current
    DESCRIPTION
"
synchronization status for MaillogTailBytes
-1 - MaillogTailBytes could not be synchronized
 0 - synchronization not configured
 1 - out of sync - running master mode
 2 - in sync - running  mastermode
 3 - in sync - running slave mode
 4 - in sync - running master mode (wait to reach state 2)
"
    ::= {MaillogTailBytes 5}

syncStatStrMaillogTailBytes  OBJECT-TYPE
    SYNTAX      OCTET STRING
    MAX-ACCESS  read-only
    STATUS      current
    DESCRIPTION
"
synchronization status line from file assp_sync.cfg for MaillogTailBytes
 0 - synchronization not configured
 1 - out of sync - running master mode
 2 - in sync - running  mastermode
 3 - in sync - running slave mode
 4 - in sync - running master mode (wait to reach state 2)
"
    ::= {MaillogTailBytes 6}

CleanCacheEvery  OBJECT-TYPE
    SYNTAX      OCTET STRING
    MAX-ACCESS  read-write
    STATUS      current
    DESCRIPTION
"
This period (in hours) determines how frequently ASSP does cache-housekeeping.
"
    REFERENCE "Cache Cleaning Interval <sup>s</sup>"
    DEFVAL { "6" }
    ::= {ServerSetup 778}

syncStatCleanCacheEvery  OBJECT-TYPE
    SYNTAX      OCTET STRING
    MAX-ACCESS  read-only
    STATUS      current
    DESCRIPTION
"
synchronization status for CleanCacheEvery
-1 - CleanCacheEvery could not be synchronized
 0 - synchronization not configured
 1 - out of sync - running master mode
 2 - in sync - running  mastermode
 3 - in sync - running slave mode
 4 - in sync - running master mode (wait to reach state 2)
"
    ::= {CleanCacheEvery 5}

syncStatStrCleanCacheEvery  OBJECT-TYPE
    SYNTAX      OCTET STRING
    MAX-ACCESS  read-only
    STATUS      current
    DESCRIPTION
"
synchronization status line from file assp_sync.cfg for CleanCacheEvery
 0 - synchronization not configured
 1 - out of sync - running master mode
 2 - in sync - running  mastermode
 3 - in sync - running slave mode
 4 - in sync - running master mode (wait to reach state 2)
"
    ::= {CleanCacheEvery 6}

SaveStatsEvery  OBJECT-TYPE
    SYNTAX      OCTET STRING
    MAX-ACCESS  read-write
    STATUS      current
    DESCRIPTION
"
This period (in minutes) determines how frequently ASSP statistics are written to a local file.
"
    REFERENCE "Statistics Save Interval <sup>s</sup>"
    DEFVAL { "30" }
    ::= {ServerSetup 779}

syncStatSaveStatsEvery  OBJECT-TYPE
    SYNTAX      OCTET STRING
    MAX-ACCESS  read-only
    STATUS      current
    DESCRIPTION
"
synchronization status for SaveStatsEvery
-1 - SaveStatsEvery could not be synchronized
 0 - synchronization not configured
 1 - out of sync - running master mode
 2 - in sync - running  mastermode
 3 - in sync - running slave mode
 4 - in sync - running master mode (wait to reach state 2)
"
    ::= {SaveStatsEvery 5}

syncStatStrSaveStatsEvery  OBJECT-TYPE
    SYNTAX      OCTET STRING
    MAX-ACCESS  read-only
    STATUS      current
    DESCRIPTION
"
synchronization status line from file assp_sync.cfg for SaveStatsEvery
 0 - synchronization not configured
 1 - out of sync - running master mode
 2 - in sync - running  mastermode
 3 - in sync - running slave mode
 4 - in sync - running master mode (wait to reach state 2)
"
    ::= {SaveStatsEvery 6}

totalizeSpamStats  OBJECT-TYPE
    SYNTAX      OCTET STRING
    MAX-ACCESS  read-write
    STATUS      current
    DESCRIPTION
"
ASSP will upload its statistics to be consolidated with the . This is a great marketing tool for the ASSP project &mdash; please do not disable it unless you have a good reason to do so. No private information is being disclosed by this upload.
"
    REFERENCE "Upload Consolidated Spam Statistics"
    DEFVAL { "1" }
    ::= {ServerSetup 780}

syncStattotalizeSpamStats  OBJECT-TYPE
    SYNTAX      OCTET STRING
    MAX-ACCESS  read-only
    STATUS      current
    DESCRIPTION
"
synchronization status for totalizeSpamStats
-1 - totalizeSpamStats could not be synchronized
 0 - synchronization not configured
 1 - out of sync - running master mode
 2 - in sync - running  mastermode
 3 - in sync - running slave mode
 4 - in sync - running master mode (wait to reach state 2)
"
    ::= {totalizeSpamStats 5}

syncStatStrtotalizeSpamStats  OBJECT-TYPE
    SYNTAX      OCTET STRING
    MAX-ACCESS  read-only
    STATUS      current
    DESCRIPTION
"
synchronization status line from file assp_sync.cfg for totalizeSpamStats
 0 - synchronization not configured
 1 - out of sync - running master mode
 2 - in sync - running  mastermode
 3 - in sync - running slave mode
 4 - in sync - running master mode (wait to reach state 2)
"
    ::= {totalizeSpamStats 6}

ReloadOptionFiles  OBJECT-TYPE
    SYNTAX      OCTET STRING
    MAX-ACCESS  read-write
    STATUS      current
    DESCRIPTION
"
If set not to zero, ASSP reloads configuration option files (file:.....) every this many seconds if they have changed. It is not recommended (and could make ASSP unavailable) to use rsync or any external tool to synchronise caches and list permanently. If you need to synchronise data between ASSP installations, you better use a database of your choice!
"
    REFERENCE "Reload Option Files Interval <sup>s</sup>"
    DEFVAL { "300" }
    ::= {ServerSetup 781}

syncStatReloadOptionFiles  OBJECT-TYPE
    SYNTAX      OCTET STRING
    MAX-ACCESS  read-only
    STATUS      current
    DESCRIPTION
"
synchronization status for ReloadOptionFiles
-1 - ReloadOptionFiles could not be synchronized
 0 - synchronization not configured
 1 - out of sync - running master mode
 2 - in sync - running  mastermode
 3 - in sync - running slave mode
 4 - in sync - running master mode (wait to reach state 2)
"
    ::= {ReloadOptionFiles 5}

syncStatStrReloadOptionFiles  OBJECT-TYPE
    SYNTAX      OCTET STRING
    MAX-ACCESS  read-only
    STATUS      current
    DESCRIPTION
"
synchronization status line from file assp_sync.cfg for ReloadOptionFiles
 0 - synchronization not configured
 1 - out of sync - running master mode
 2 - in sync - running  mastermode
 3 - in sync - running slave mode
 4 - in sync - running master mode (wait to reach state 2)
"
    ::= {ReloadOptionFiles 6}

OrderedTieHashTableSize  OBJECT-TYPE
    SYNTAX      OCTET STRING
    MAX-ACCESS  read-write
    STATUS      current
    DESCRIPTION
"
The number of entries allowed in the hash tables used by ASSP. This only belongs to Griplist if useDB4IntCache is not set. Larger numbers require more RAM but result in fewer disk hits. The default value is 10000. Adjust down to use less RAM.
"
    REFERENCE "Ordered-Tie Hash Table Size"
    DEFVAL { "10000" }
    ::= {ServerSetup 782}

syncStatOrderedTieHashTableSize  OBJECT-TYPE
    SYNTAX      OCTET STRING
    MAX-ACCESS  read-only
    STATUS      current
    DESCRIPTION
"
synchronization status for OrderedTieHashTableSize
-1 - OrderedTieHashTableSize could not be synchronized
 0 - synchronization not configured
 1 - out of sync - running master mode
 2 - in sync - running  mastermode
 3 - in sync - running slave mode
 4 - in sync - running master mode (wait to reach state 2)
"
    ::= {OrderedTieHashTableSize 5}

syncStatStrOrderedTieHashTableSize  OBJECT-TYPE
    SYNTAX      OCTET STRING
    MAX-ACCESS  read-only
    STATUS      current
    DESCRIPTION
"
synchronization status line from file assp_sync.cfg for OrderedTieHashTableSize
 0 - synchronization not configured
 1 - out of sync - running master mode
 2 - in sync - running  mastermode
 3 - in sync - running slave mode
 4 - in sync - running master mode (wait to reach state 2)
"
    ::= {OrderedTieHashTableSize 6}

OutgoingBufSizeNew  OBJECT-TYPE
    SYNTAX      OCTET STRING
    MAX-ACCESS  read-write
    STATUS      current
    DESCRIPTION
"
The default is 10240000 byte. Even more is better...
"
    REFERENCE "Size of TCP/IP Buffer"
    DEFVAL { "10240000" }
    ::= {ServerSetup 783}

syncStatOutgoingBufSizeNew  OBJECT-TYPE
    SYNTAX      OCTET STRING
    MAX-ACCESS  read-only
    STATUS      current
    DESCRIPTION
"
synchronization status for OutgoingBufSizeNew
-1 - OutgoingBufSizeNew could not be synchronized
 0 - synchronization not configured
 1 - out of sync - running master mode
 2 - in sync - running  mastermode
 3 - in sync - running slave mode
 4 - in sync - running master mode (wait to reach state 2)
"
    ::= {OutgoingBufSizeNew 5}

syncStatStrOutgoingBufSizeNew  OBJECT-TYPE
    SYNTAX      OCTET STRING
    MAX-ACCESS  read-only
    STATUS      current
    DESCRIPTION
"
synchronization status line from file assp_sync.cfg for OutgoingBufSizeNew
 0 - synchronization not configured
 1 - out of sync - running master mode
 2 - in sync - running  mastermode
 3 - in sync - running slave mode
 4 - in sync - running master mode (wait to reach state 2)
"
    ::= {OutgoingBufSizeNew 6}

useDB4IntCache  OBJECT-TYPE
    SYNTAX      OCTET STRING
    MAX-ACCESS  read-write
    STATUS      current
    DESCRIPTION
"
ASSP uses some internal caches that could grow to a large number of entries. Switch this on, if you want ASSP to use less memory and be a little slower. The perl module  version 0.34 or higher and BerkeleyDB version 4.5 or higher is required to use this feature.
"
    REFERENCE "Use BerkeleyDB for Internal Caches"
    DEFVAL { "" }
    ::= {ServerSetup 784}

syncStatuseDB4IntCache  OBJECT-TYPE
    SYNTAX      OCTET STRING
    MAX-ACCESS  read-only
    STATUS      current
    DESCRIPTION
"
synchronization status for useDB4IntCache
-1 - useDB4IntCache could not be synchronized
 0 - synchronization not configured
 1 - out of sync - running master mode
 2 - in sync - running  mastermode
 3 - in sync - running slave mode
 4 - in sync - running master mode (wait to reach state 2)
"
    ::= {useDB4IntCache 5}

syncStatStruseDB4IntCache  OBJECT-TYPE
    SYNTAX      OCTET STRING
    MAX-ACCESS  read-only
    STATUS      current
    DESCRIPTION
"
synchronization status line from file assp_sync.cfg for useDB4IntCache
 0 - synchronization not configured
 1 - out of sync - running master mode
 2 - in sync - running  mastermode
 3 - in sync - running slave mode
 4 - in sync - running master mode (wait to reach state 2)
"
    ::= {useDB4IntCache 6}

ALARMtimeout  OBJECT-TYPE
    SYNTAX      OCTET STRING
    MAX-ACCESS  read-write
    STATUS      current
    DESCRIPTION
"
Global Timeout for SPF checks. The default is 10 seconds.
  Thread Control - be carefull changing the following green options!</font>
"
    REFERENCE "Module Call Timeout"
    DEFVAL { "10" }
    ::= {ServerSetup 785}

syncStatALARMtimeout  OBJECT-TYPE
    SYNTAX      OCTET STRING
    MAX-ACCESS  read-only
    STATUS      current
    DESCRIPTION
"
synchronization status for ALARMtimeout
-1 - ALARMtimeout could not be synchronized
 0 - synchronization not configured
 1 - out of sync - running master mode
 2 - in sync - running  mastermode
 3 - in sync - running slave mode
 4 - in sync - running master mode (wait to reach state 2)
"
    ::= {ALARMtimeout 5}

syncStatStrALARMtimeout  OBJECT-TYPE
    SYNTAX      OCTET STRING
    MAX-ACCESS  read-only
    STATUS      current
    DESCRIPTION
"
synchronization status line from file assp_sync.cfg for ALARMtimeout
 0 - synchronization not configured
 1 - out of sync - running master mode
 2 - in sync - running  mastermode
 3 - in sync - running slave mode
 4 - in sync - running master mode (wait to reach state 2)
"
    ::= {ALARMtimeout 6}

NumComWorkers  OBJECT-TYPE
    SYNTAX      OCTET STRING
    MAX-ACCESS  read-write
    STATUS      current
    DESCRIPTION
"
Number of SMTP-Threads to be used! Typical and default is 5. 10 should be enought for 200.000 connections a day. 15 should be the absolute maximium. Values above 7 will mostly not increase performance. Configurable values are between 2 and 29. Restart ASSP if you changed this and you are using any database connection! An restart of assp is required if tis value was increased.
"
    REFERENCE "Number of SMTP-Threads"
    DEFVAL { "5" }
    ::= {ServerSetup 786}

ReservedOutboundWorkers  OBJECT-TYPE
    SYNTAX      OCTET STRING
    MAX-ACCESS  read-write
    STATUS      current
    DESCRIPTION
"
Number of SMTP-Threads to be resevered for relayed (outbound) connections on relayPort ! This number of Threads will be exclusive reserved for connections on relayPort . For example: NumComWorkers=7 and ReservedOutboundWorkers=2 - mails on listenPort , listenPort2 and listenPortSSL are using worker 1-5 and mails on relayPort using worker 7-1 ! If you are not using the relayPort, do not reserve any workers.
"
    REFERENCE "Reserved Number of Outbound-SMTP-Threads on relayPort"
    DEFVAL { "0" }
    ::= {ServerSetup 787}

myNameAlso  OBJECT-TYPE
    SYNTAX      OCTET STRING
    MAX-ACCESS  read-write
    STATUS      current
    DESCRIPTION
"
If myName was changed or you use shared folders (multiple ASSP) for the corpus files, define the old or other host names here - separate multiple entries by pipe, space or comma. ASSP will use this host names in addition to myName, to detect the received headerlines while the rebuildspamdb is running and in the mail analyzer.
"
    REFERENCE "Additional My-Name-Definitions"
    DEFVAL { "" }
    ::= {ServerSetup 788}

syncStatmyNameAlso  OBJECT-TYPE
    SYNTAX      OCTET STRING
    MAX-ACCESS  read-only
    STATUS      current
    DESCRIPTION
"
synchronization status for myNameAlso
-1 - myNameAlso could not be synchronized
 0 - synchronization not configured
 1 - out of sync - running master mode
 2 - in sync - running  mastermode
 3 - in sync - running slave mode
 4 - in sync - running master mode (wait to reach state 2)
"
    ::= {myNameAlso 5}

syncStatStrmyNameAlso  OBJECT-TYPE
    SYNTAX      OCTET STRING
    MAX-ACCESS  read-only
    STATUS      current
    DESCRIPTION
"
synchronization status line from file assp_sync.cfg for myNameAlso
 0 - synchronization not configured
 1 - out of sync - running master mode
 2 - in sync - running  mastermode
 3 - in sync - running slave mode
 4 - in sync - running master mode (wait to reach state 2)
"
    ::= {myNameAlso 6}

noModuleAutoUpdate  OBJECT-TYPE
    SYNTAX      OCTET STRING
    MAX-ACCESS  read-write
    STATUS      current
    DESCRIPTION
"
If set, ASSP will skip the automatic Perl module update.
"
    REFERENCE "No Automatic Perl Module update"
    DEFVAL { "" }
    ::= {ServerSetup 790}

syncStatnoModuleAutoUpdate  OBJECT-TYPE
    SYNTAX      OCTET STRING
    MAX-ACCESS  read-only
    STATUS      current
    DESCRIPTION
"
synchronization status for noModuleAutoUpdate
-1 - noModuleAutoUpdate could not be synchronized
 0 - synchronization not configured
 1 - out of sync - running master mode
 2 - in sync - running  mastermode
 3 - in sync - running slave mode
 4 - in sync - running master mode (wait to reach state 2)
"
    ::= {noModuleAutoUpdate 5}

syncStatStrnoModuleAutoUpdate  OBJECT-TYPE
    SYNTAX      OCTET STRING
    MAX-ACCESS  read-only
    STATUS      current
    DESCRIPTION
"
synchronization status line from file assp_sync.cfg for noModuleAutoUpdate
 0 - synchronization not configured
 1 - out of sync - running master mode
 2 - in sync - running  mastermode
 3 - in sync - running slave mode
 4 - in sync - running master mode (wait to reach state 2)
"
    ::= {noModuleAutoUpdate 6}

autoRestartDiedThreads  OBJECT-TYPE
    SYNTAX      OCTET STRING
    MAX-ACCESS  read-write
    STATUS      current
    DESCRIPTION
"
If defined, a (for any reason) died thread will be automaticly restarted!
"
    REFERENCE "automaticly restart died threads"
    DEFVAL { "1" }
    ::= {ServerSetup 792}

syncStatautoRestartDiedThreads  OBJECT-TYPE
    SYNTAX      OCTET STRING
    MAX-ACCESS  read-only
    STATUS      current
    DESCRIPTION
"
synchronization status for autoRestartDiedThreads
-1 - autoRestartDiedThreads could not be synchronized
 0 - synchronization not configured
 1 - out of sync - running master mode
 2 - in sync - running  mastermode
 3 - in sync - running slave mode
 4 - in sync - running master mode (wait to reach state 2)
"
    ::= {autoRestartDiedThreads 5}

syncStatStrautoRestartDiedThreads  OBJECT-TYPE
    SYNTAX      OCTET STRING
    MAX-ACCESS  read-only
    STATUS      current
    DESCRIPTION
"
synchronization status line from file assp_sync.cfg for autoRestartDiedThreads
 0 - synchronization not configured
 1 - out of sync - running master mode
 2 - in sync - running  mastermode
 3 - in sync - running slave mode
 4 - in sync - running master mode (wait to reach state 2)
"
    ::= {autoRestartDiedThreads 6}

MaxFinConWaitTime  OBJECT-TYPE
    SYNTAX      OCTET STRING
    MAX-ACCESS  read-write
    STATUS      current
    DESCRIPTION
"
The maximum time in seconds to wait for SMTP-Workers to finish connections, in case of a shutdown or restart of ASSP. Default is 45. Configurable values are 10 to 599.
"
    REFERENCE "Maximum time to wait for SMTP-Workers to finish connections"
    DEFVAL { "45" }
    ::= {ServerSetup 793}

syncStatMaxFinConWaitTime  OBJECT-TYPE
    SYNTAX      OCTET STRING
    MAX-ACCESS  read-only
    STATUS      current
    DESCRIPTION
"
synchronization status for MaxFinConWaitTime
-1 - MaxFinConWaitTime could not be synchronized
 0 - synchronization not configured
 1 - out of sync - running master mode
 2 - in sync - running  mastermode
 3 - in sync - running slave mode
 4 - in sync - running master mode (wait to reach state 2)
"
    ::= {MaxFinConWaitTime 5}

syncStatStrMaxFinConWaitTime  OBJECT-TYPE
    SYNTAX      OCTET STRING
    MAX-ACCESS  read-only
    STATUS      current
    DESCRIPTION
"
synchronization status line from file assp_sync.cfg for MaxFinConWaitTime
 0 - synchronization not configured
 1 - out of sync - running master mode
 2 - in sync - running  mastermode
 3 - in sync - running slave mode
 4 - in sync - running master mode (wait to reach state 2)
"
    ::= {MaxFinConWaitTime 6}

MonitorMainThread  OBJECT-TYPE
    SYNTAX      OCTET STRING
    MAX-ACCESS  read-write
    STATUS      current
    DESCRIPTION
"
If defined, the MainThread will be monitored for healthy by the MaintThread (Worker 10000)!
"
    REFERENCE "Monitor the MainThread"
    DEFVAL { "1" }
    ::= {ServerSetup 794}

syncStatMonitorMainThread  OBJECT-TYPE
    SYNTAX      OCTET STRING
    MAX-ACCESS  read-only
    STATUS      current
    DESCRIPTION
"
synchronization status for MonitorMainThread
-1 - MonitorMainThread could not be synchronized
 0 - synchronization not configured
 1 - out of sync - running master mode
 2 - in sync - running  mastermode
 3 - in sync - running slave mode
 4 - in sync - running master mode (wait to reach state 2)
"
    ::= {MonitorMainThread 5}

syncStatStrMonitorMainThread  OBJECT-TYPE
    SYNTAX      OCTET STRING
    MAX-ACCESS  read-only
    STATUS      current
    DESCRIPTION
"
synchronization status line from file assp_sync.cfg for MonitorMainThread
 0 - synchronization not configured
 1 - out of sync - running master mode
 2 - in sync - running  mastermode
 3 - in sync - running slave mode
 4 - in sync - running master mode (wait to reach state 2)
"
    ::= {MonitorMainThread 6}

ThreadCycleTime  OBJECT-TYPE
    SYNTAX      OCTET STRING
    MAX-ACCESS  read-write
    STATUS      current
    DESCRIPTION
"
Time in microseconds (for SMTP workers and MainThread) to give each other thread to run in high CPU-workload conditions. Default value is 3000, typical values are between 10 and 9000. You can set this to 0, if your OS honors system-yield-calls (0 is not recommended on Windows OS)! A higher value will reduce CPU usage but cause ASSP to run more slowly!
"
    REFERENCE "thread cycle time"
    DEFVAL { "3000" }
    ::= {ServerSetup 795}

syncStatThreadCycleTime  OBJECT-TYPE
    SYNTAX      OCTET STRING
    MAX-ACCESS  read-only
    STATUS      current
    DESCRIPTION
"
synchronization status for ThreadCycleTime
-1 - ThreadCycleTime could not be synchronized
 0 - synchronization not configured
 1 - out of sync - running master mode
 2 - in sync - running  mastermode
 3 - in sync - running slave mode
 4 - in sync - running master mode (wait to reach state 2)
"
    ::= {ThreadCycleTime 5}

syncStatStrThreadCycleTime  OBJECT-TYPE
    SYNTAX      OCTET STRING
    MAX-ACCESS  read-only
    STATUS      current
    DESCRIPTION
"
synchronization status line from file assp_sync.cfg for ThreadCycleTime
 0 - synchronization not configured
 1 - out of sync - running master mode
 2 - in sync - running  mastermode
 3 - in sync - running slave mode
 4 - in sync - running master mode (wait to reach state 2)
"
    ::= {ThreadCycleTime 6}

MaintThreadCycleTime  OBJECT-TYPE
    SYNTAX      OCTET STRING
    MAX-ACCESS  read-write
    STATUS      current
    DESCRIPTION
"
Time in microseconds (for MaintThread) to give each other thread to run in high CPU-workload conditions. Default value is 3000, typical values are between 10 and 9000. You can set this to 0, if your OS honors system-yield-calls (0 is not recommended on Windows OS)! A higher value will reduce CPU usage but cause ASSP to run more slowly!
"
    REFERENCE "MaintenanceThread cycle time"
    DEFVAL { "3000" }
    ::= {ServerSetup 796}

syncStatMaintThreadCycleTime  OBJECT-TYPE
    SYNTAX      OCTET STRING
    MAX-ACCESS  read-only
    STATUS      current
    DESCRIPTION
"
synchronization status for MaintThreadCycleTime
-1 - MaintThreadCycleTime could not be synchronized
 0 - synchronization not configured
 1 - out of sync - running master mode
 2 - in sync - running  mastermode
 3 - in sync - running slave mode
 4 - in sync - running master mode (wait to reach state 2)
"
    ::= {MaintThreadCycleTime 5}

syncStatStrMaintThreadCycleTime  OBJECT-TYPE
    SYNTAX      OCTET STRING
    MAX-ACCESS  read-only
    STATUS      current
    DESCRIPTION
"
synchronization status line from file assp_sync.cfg for MaintThreadCycleTime
 0 - synchronization not configured
 1 - out of sync - running master mode
 2 - in sync - running  mastermode
 3 - in sync - running slave mode
 4 - in sync - running master mode (wait to reach state 2)
"
    ::= {MaintThreadCycleTime 6}

RebuildThreadCycleTime  OBJECT-TYPE
    SYNTAX      OCTET STRING
    MAX-ACCESS  read-write
    STATUS      current
    DESCRIPTION
"
Time in microseconds (for RebuildSpamDBThread) to give each other thread to run in high CPU-workload conditions. Default value is 30, typical values are between 10 and 1000. You can set this to 0, if your OS honors system-yield-calls (0 is not recommended on Windows OS) and your system is fast enough! A higher value will reduce CPU usage but cause ASSP to run more slowly!
"
    REFERENCE "RebuildSpamDBThread cycle time"
    DEFVAL { "30" }
    ::= {ServerSetup 797}

syncStatRebuildThreadCycleTime  OBJECT-TYPE
    SYNTAX      OCTET STRING
    MAX-ACCESS  read-only
    STATUS      current
    DESCRIPTION
"
synchronization status for RebuildThreadCycleTime
-1 - RebuildThreadCycleTime could not be synchronized
 0 - synchronization not configured
 1 - out of sync - running master mode
 2 - in sync - running  mastermode
 3 - in sync - running slave mode
 4 - in sync - running master mode (wait to reach state 2)
"
    ::= {RebuildThreadCycleTime 5}

syncStatStrRebuildThreadCycleTime  OBJECT-TYPE
    SYNTAX      OCTET STRING
    MAX-ACCESS  read-only
    STATUS      current
    DESCRIPTION
"
synchronization status line from file assp_sync.cfg for RebuildThreadCycleTime
 0 - synchronization not configured
 1 - out of sync - running master mode
 2 - in sync - running  mastermode
 3 - in sync - running slave mode
 4 - in sync - running master mode (wait to reach state 2)
"
    ::= {RebuildThreadCycleTime 6}

IOEngine  OBJECT-TYPE
    SYNTAX      OCTET STRING
    MAX-ACCESS  read-write
    STATUS      current
    DESCRIPTION
"
Depending on your operating system and your Perl version it could be necessary to use the non default IOEngine 'IO::Select'. Try this if you see unexpected early closed connections in the log. You have to restart ASSP, if you have changed this value!
"
    REFERENCE "Use This IO Engine"
    DEFVAL { "0" }
    ::= {ServerSetup 798}

syncStatIOEngine  OBJECT-TYPE
    SYNTAX      OCTET STRING
    MAX-ACCESS  read-only
    STATUS      current
    DESCRIPTION
"
synchronization status for IOEngine
-1 - IOEngine could not be synchronized
 0 - synchronization not configured
 1 - out of sync - running master mode
 2 - in sync - running  mastermode
 3 - in sync - running slave mode
 4 - in sync - running master mode (wait to reach state 2)
"
    ::= {IOEngine 5}

syncStatStrIOEngine  OBJECT-TYPE
    SYNTAX      OCTET STRING
    MAX-ACCESS  read-only
    STATUS      current
    DESCRIPTION
"
synchronization status line from file assp_sync.cfg for IOEngine
 0 - synchronization not configured
 1 - out of sync - running master mode
 2 - in sync - running  mastermode
 3 - in sync - running slave mode
 4 - in sync - running master mode (wait to reach state 2)
"
    ::= {IOEngine 6}

MinPollTime  OBJECT-TYPE
    SYNTAX      OCTET STRING
    MAX-ACCESS  read-write
    STATUS      current
    DESCRIPTION
"
The time in milliseconds that ASSP will at least wait for IO::Poll/IO::Select events! A higher value will reduce CPU usage but cause ASSP to run more slowly! Default is 2.
"
    REFERENCE "Minimum Poll/Select Wait Time"
    DEFVAL { "2" }
    ::= {ServerSetup 799}

syncStatMinPollTime  OBJECT-TYPE
    SYNTAX      OCTET STRING
    MAX-ACCESS  read-only
    STATUS      current
    DESCRIPTION
"
synchronization status for MinPollTime
-1 - MinPollTime could not be synchronized
 0 - synchronization not configured
 1 - out of sync - running master mode
 2 - in sync - running  mastermode
 3 - in sync - running slave mode
 4 - in sync - running master mode (wait to reach state 2)
"
    ::= {MinPollTime 5}

syncStatStrMinPollTime  OBJECT-TYPE
    SYNTAX      OCTET STRING
    MAX-ACCESS  read-only
    STATUS      current
    DESCRIPTION
"
synchronization status line from file assp_sync.cfg for MinPollTime
 0 - synchronization not configured
 1 - out of sync - running master mode
 2 - in sync - running  mastermode
 3 - in sync - running slave mode
 4 - in sync - running master mode (wait to reach state 2)
"
    ::= {MinPollTime 6}

WorkerCPUPriority  OBJECT-TYPE
    SYNTAX      OCTET STRING
    MAX-ACCESS  read-write
    STATUS      current
    DESCRIPTION
"
Set the priority for the Workers in relation to all other processes/threads on the system. Than higher the value - than lower the priority. Default is 0 (system default is 0). Possible values are 0,1 and 2. This requires installed  module. It is recommended to run the Workers on lower priority, if ASSP has to process most of the time a large number of mails at one moment ( number of mails &gt; NumComWorkers ).
"
    REFERENCE "CPU priority for SMTP-Threads"
    DEFVAL { "0" }
    ::= {ServerSetup 800}

syncStatWorkerCPUPriority  OBJECT-TYPE
    SYNTAX      OCTET STRING
    MAX-ACCESS  read-only
    STATUS      current
    DESCRIPTION
"
synchronization status for WorkerCPUPriority
-1 - WorkerCPUPriority could not be synchronized
 0 - synchronization not configured
 1 - out of sync - running master mode
 2 - in sync - running  mastermode
 3 - in sync - running slave mode
 4 - in sync - running master mode (wait to reach state 2)
"
    ::= {WorkerCPUPriority 5}

syncStatStrWorkerCPUPriority  OBJECT-TYPE
    SYNTAX      OCTET STRING
    MAX-ACCESS  read-only
    STATUS      current
    DESCRIPTION
"
synchronization status line from file assp_sync.cfg for WorkerCPUPriority
 0 - synchronization not configured
 1 - out of sync - running master mode
 2 - in sync - running  mastermode
 3 - in sync - running slave mode
 4 - in sync - running master mode (wait to reach state 2)
"
    ::= {WorkerCPUPriority 6}

PreAllocMem  OBJECT-TYPE
    SYNTAX      OCTET STRING
    MAX-ACCESS  read-write
    STATUS      current
    DESCRIPTION
"
ASSP pre-allocates this number of bytes in mainstorage two times (in/out) for every mail to avoid memoryfracmentation (particularly in ASSP long run conditions). The memory will be allocated, if the DATA command is received from the server. Default is 100000 - this is enough for most of the mails. If ASSP receives the SIZE command from the server, the pre-allocation-memory will be calculated on that value. Question: Is it better to increase this value? Answer: Yes, it is - but be careful, this may cause ASSP running in out of memory errors!
"
    REFERENCE "pre allocate memory for every mail"
    DEFVAL { "100000" }
    ::= {ServerSetup 801}

syncStatPreAllocMem  OBJECT-TYPE
    SYNTAX      OCTET STRING
    MAX-ACCESS  read-only
    STATUS      current
    DESCRIPTION
"
synchronization status for PreAllocMem
-1 - PreAllocMem could not be synchronized
 0 - synchronization not configured
 1 - out of sync - running master mode
 2 - in sync - running  mastermode
 3 - in sync - running slave mode
 4 - in sync - running master mode (wait to reach state 2)
"
    ::= {PreAllocMem 5}

syncStatStrPreAllocMem  OBJECT-TYPE
    SYNTAX      OCTET STRING
    MAX-ACCESS  read-only
    STATUS      current
    DESCRIPTION
"
synchronization status line from file assp_sync.cfg for PreAllocMem
 0 - synchronization not configured
 1 - out of sync - running master mode
 2 - in sync - running  mastermode
 3 - in sync - running slave mode
 4 - in sync - running master mode (wait to reach state 2)
"
    ::= {PreAllocMem 6}

FreeupMemoryGarbage  OBJECT-TYPE
    SYNTAX      OCTET STRING
    MAX-ACCESS  read-write
    STATUS      current
    DESCRIPTION
"
If defined, all Threads will try to recover memory every five minutes!
"
    REFERENCE "Freeup Memory Garbage"
    DEFVAL { "1" }
    ::= {ServerSetup 802}

syncStatFreeupMemoryGarbage  OBJECT-TYPE
    SYNTAX      OCTET STRING
    MAX-ACCESS  read-only
    STATUS      current
    DESCRIPTION
"
synchronization status for FreeupMemoryGarbage
-1 - FreeupMemoryGarbage could not be synchronized
 0 - synchronization not configured
 1 - out of sync - running master mode
 2 - in sync - running  mastermode
 3 - in sync - running slave mode
 4 - in sync - running master mode (wait to reach state 2)
"
    ::= {FreeupMemoryGarbage 5}

syncStatStrFreeupMemoryGarbage  OBJECT-TYPE
    SYNTAX      OCTET STRING
    MAX-ACCESS  read-only
    STATUS      current
    DESCRIPTION
"
synchronization status line from file assp_sync.cfg for FreeupMemoryGarbage
 0 - synchronization not configured
 1 - out of sync - running master mode
 2 - in sync - running  mastermode
 3 - in sync - running slave mode
 4 - in sync - running master mode (wait to reach state 2)
"
    ::= {FreeupMemoryGarbage 6}

ConnectionTransferTimeOut  OBJECT-TYPE
    SYNTAX      OCTET STRING
    MAX-ACCESS  read-write
    STATUS      current
    DESCRIPTION
"
Global Timeout for MainThread to transfer a connection to any Worker. If no Worker is able to take the new SMTP-connection (for any reason), the new connection will be droped! The default is 30 seconds.
"
    REFERENCE "Connection Transfer Timeout"
    DEFVAL { "30" }
    ::= {ServerSetup 803}

syncStatConnectionTransferTimeOut  OBJECT-TYPE
    SYNTAX      OCTET STRING
    MAX-ACCESS  read-only
    STATUS      current
    DESCRIPTION
"
synchronization status for ConnectionTransferTimeOut
-1 - ConnectionTransferTimeOut could not be synchronized
 0 - synchronization not configured
 1 - out of sync - running master mode
 2 - in sync - running  mastermode
 3 - in sync - running slave mode
 4 - in sync - running master mode (wait to reach state 2)
"
    ::= {ConnectionTransferTimeOut 5}

syncStatStrConnectionTransferTimeOut  OBJECT-TYPE
    SYNTAX      OCTET STRING
    MAX-ACCESS  read-only
    STATUS      current
    DESCRIPTION
"
synchronization status line from file assp_sync.cfg for ConnectionTransferTimeOut
 0 - synchronization not configured
 1 - out of sync - running master mode
 2 - in sync - running  mastermode
 3 - in sync - running slave mode
 4 - in sync - running master mode (wait to reach state 2)
"
    ::= {ConnectionTransferTimeOut 6}

ShowPerformanceData  OBJECT-TYPE
    SYNTAX      OCTET STRING
    MAX-ACCESS  read-write
    STATUS      current
    DESCRIPTION
"
If defined, performance data will be shown in top of the SMTP connection screen!
  end of Thread Control</font>
"
    REFERENCE "Show Performance DATA in SMTP Connection screen"
    DEFVAL { "1" }
    ::= {ServerSetup 804}

syncStatShowPerformanceData  OBJECT-TYPE
    SYNTAX      OCTET STRING
    MAX-ACCESS  read-only
    STATUS      current
    DESCRIPTION
"
synchronization status for ShowPerformanceData
-1 - ShowPerformanceData could not be synchronized
 0 - synchronization not configured
 1 - out of sync - running master mode
 2 - in sync - running  mastermode
 3 - in sync - running slave mode
 4 - in sync - running master mode (wait to reach state 2)
"
    ::= {ShowPerformanceData 5}

syncStatStrShowPerformanceData  OBJECT-TYPE
    SYNTAX      OCTET STRING
    MAX-ACCESS  read-only
    STATUS      current
    DESCRIPTION
"
synchronization status line from file assp_sync.cfg for ShowPerformanceData
 0 - synchronization not configured
 1 - out of sync - running master mode
 2 - in sync - running  mastermode
 3 - in sync - running slave mode
 4 - in sync - running master mode (wait to reach state 2)
"
    ::= {ShowPerformanceData 6}

UseLocalTime  OBJECT-TYPE
    SYNTAX      OCTET STRING
    MAX-ACCESS  read-write
    STATUS      current
    DESCRIPTION
"
Use local time and timezone offset rather than UTC time in the mail headers.
  
"
    REFERENCE "Use Local Time"
    DEFVAL { "1" }
    ::= {ServerSetup 805}

syncStatUseLocalTime  OBJECT-TYPE
    SYNTAX      OCTET STRING
    MAX-ACCESS  read-only
    STATUS      current
    DESCRIPTION
"
synchronization status for UseLocalTime
-1 - UseLocalTime could not be synchronized
 0 - synchronization not configured
 1 - out of sync - running master mode
 2 - in sync - running  mastermode
 3 - in sync - running slave mode
 4 - in sync - running master mode (wait to reach state 2)
"
    ::= {UseLocalTime 5}

syncStatStrUseLocalTime  OBJECT-TYPE
    SYNTAX      OCTET STRING
    MAX-ACCESS  read-only
    STATUS      current
    DESCRIPTION
"
synchronization status line from file assp_sync.cfg for UseLocalTime
 0 - synchronization not configured
 1 - out of sync - running master mode
 2 - in sync - running  mastermode
 3 - in sync - running slave mode
 4 - in sync - running master mode (wait to reach state 2)
"
    ::= {UseLocalTime 6}

AutoUpdateASSP  OBJECT-TYPE
    SYNTAX      OCTET STRING
    MAX-ACCESS  read-write
    STATUS      current
    DESCRIPTION
"
No action will be done if 'no auto update' is selected. You'll get a hint in the GUI (top) and a log line will be written, if a new version is availabe at the download location.
  If 'download only' is selected and a new assp version is available, this new version will be downloaded to the directory C:/assp/download (assp.pl) and the syntax will be checked. The still running script will be saved version numbered to the download directory.
  If 'download and install' is selected, in addition the still running script will be replaced by the new version.
  Configure ( AutoRestartAfterCodeChange ), if you want the new version to become the active running script.
  If this value is changed to 'download and install', the autoupdate procedure will be scheduled immediatly.
  If set, ASSP (on windows systems with ActivePerl installations) will search for updated Perl modules in all registered PPM respositories &nbsp;&nbsp;
  The installation of some modules could require manual configuration and the installation fails or an upgrade is not recommended. In this case put the case sensitive module names (one per line) in the followog file. &nbsp;&nbsp;
  If this value is set to 'download and install', ASSP will try an autoupdate of the new available modules. It is possible, that some modules could not be installed, because the XS module parts are still in use. In this case follow the instruction - click the 'new available perl modules' button above. To disable the automatic Perl module update - set 'noModuleAutoUpdate' below.
  Click this button to see the log file for the updated modules&nbsp;&nbsp;
  The perl module  is required to use this feature.
"
    REFERENCE "Auto Update the Running Script (assp.pl)"
    DEFVAL { "0" }
    ::= {ServerSetup 881}

syncStatAutoUpdateASSP  OBJECT-TYPE
    SYNTAX      OCTET STRING
    MAX-ACCESS  read-only
    STATUS      current
    DESCRIPTION
"
synchronization status for AutoUpdateASSP
-1 - AutoUpdateASSP could not be synchronized
 0 - synchronization not configured
 1 - out of sync - running master mode
 2 - in sync - running  mastermode
 3 - in sync - running slave mode
 4 - in sync - running master mode (wait to reach state 2)
"
    ::= {AutoUpdateASSP 5}

syncStatStrAutoUpdateASSP  OBJECT-TYPE
    SYNTAX      OCTET STRING
    MAX-ACCESS  read-only
    STATUS      current
    DESCRIPTION
"
synchronization status line from file assp_sync.cfg for AutoUpdateASSP
 0 - synchronization not configured
 1 - out of sync - running master mode
 2 - in sync - running  mastermode
 3 - in sync - running slave mode
 4 - in sync - running master mode (wait to reach state 2)
"
    ::= {AutoUpdateASSP 6}

httpRequireCookies  OBJECT-TYPE
    SYNTAX      OCTET STRING
    MAX-ACCESS  read-write
    STATUS      current
    DESCRIPTION
"
Cookie based http session ID's are used by assp to handle different requests from the same IP (eg behind NAT). Switch this off, if you are unable to use cookies in your browser. If switched off, a security hole is opened for connection that are using NAT - it could be possible that a second workstation (behind NAT) is able to login to the GUI, without user credentials if the same OS and browser version is used.
"
    REFERENCE "HTTP and HTTPS require enabled browser cookies"
    DEFVAL { "1" }
    ::= {ServerSetup 900}

syncStathttpRequireCookies  OBJECT-TYPE
    SYNTAX      OCTET STRING
    MAX-ACCESS  read-only
    STATUS      current
    DESCRIPTION
"
synchronization status for httpRequireCookies
-1 - httpRequireCookies could not be synchronized
 0 - synchronization not configured
 1 - out of sync - running master mode
 2 - in sync - running  mastermode
 3 - in sync - running slave mode
 4 - in sync - running master mode (wait to reach state 2)
"
    ::= {httpRequireCookies 5}

syncStatStrhttpRequireCookies  OBJECT-TYPE
    SYNTAX      OCTET STRING
    MAX-ACCESS  read-only
    STATUS      current
    DESCRIPTION
"
synchronization status line from file assp_sync.cfg for httpRequireCookies
 0 - synchronization not configured
 1 - out of sync - running master mode
 2 - in sync - running  mastermode
 3 - in sync - running slave mode
 4 - in sync - running master mode (wait to reach state 2)
"
    ::= {httpRequireCookies 6}

ThreadStackSize  OBJECT-TYPE
    SYNTAX      OCTET STRING
    MAX-ACCESS  read-write
    STATUS      current
    DESCRIPTION
"
The stack size in MB that is used by every thread. Default is 0, which means to use the default system stack size. 16 MB is the default system stack size on windows platforms. This system value may differ on different platforms. To get the default stack size on linux use the shell command 'ulimit -a'. Try to increase this value, if you get 'out of memory' errors while running assp. Changing this value requires an assp restart to take effect.
"
    REFERENCE "Stack Size use by every Thread"
    DEFVAL { "0" }
    ::= {ServerSetup 903}

syncStatThreadStackSize  OBJECT-TYPE
    SYNTAX      OCTET STRING
    MAX-ACCESS  read-only
    STATUS      current
    DESCRIPTION
"
synchronization status for ThreadStackSize
-1 - ThreadStackSize could not be synchronized
 0 - synchronization not configured
 1 - out of sync - running master mode
 2 - in sync - running  mastermode
 3 - in sync - running slave mode
 4 - in sync - running master mode (wait to reach state 2)
"
    ::= {ThreadStackSize 5}

syncStatStrThreadStackSize  OBJECT-TYPE
    SYNTAX      OCTET STRING
    MAX-ACCESS  read-only
    STATUS      current
    DESCRIPTION
"
synchronization status line from file assp_sync.cfg for ThreadStackSize
 0 - synchronization not configured
 1 - out of sync - running master mode
 2 - in sync - running  mastermode
 3 - in sync - running slave mode
 4 - in sync - running master mode (wait to reach state 2)
"
    ::= {ThreadStackSize 6}

webStatHealthyResp  OBJECT-TYPE
    SYNTAX      OCTET STRING
    MAX-ACCESS  read-write
    STATUS      current
    DESCRIPTION
"
This option must be set and it must be different to webStatNotHealthyResp. This literal will be given back in stat requests, if ASSP is working healty.
"
    REFERENCE "Status Response Literal for a Healty State of ASSP"
    DEFVAL { "healthy" }
    ::= {ServerSetup 926}

webStatNotHealthyResp  OBJECT-TYPE
    SYNTAX      OCTET STRING
    MAX-ACCESS  read-write
    STATUS      current
    DESCRIPTION
"
This option must be set and it must be different to webStatHealthyResp. This literal will be given back in stat requests, if ASSP is working not healty.
"
    REFERENCE "Status Response Literal for a Not Healty State of ASSP"
    DEFVAL { "not healthy" }
    ::= {ServerSetup 927}

RememberGUIPos  OBJECT-TYPE
    SYNTAX      OCTET STRING
    MAX-ACCESS  read-write
    STATUS      current
    DESCRIPTION
"
If selected, the GUI will remember the last topic of the main menu, that had the focus, was changed, that were jumped to or that were clicked on.
"
    REFERENCE "Remember the last GUI position"
    DEFVAL { "1" }
    ::= {ServerSetup 934}

syncStatRememberGUIPos  OBJECT-TYPE
    SYNTAX      OCTET STRING
    MAX-ACCESS  read-only
    STATUS      current
    DESCRIPTION
"
synchronization status for RememberGUIPos
-1 - RememberGUIPos could not be synchronized
 0 - synchronization not configured
 1 - out of sync - running master mode
 2 - in sync - running  mastermode
 3 - in sync - running slave mode
 4 - in sync - running master mode (wait to reach state 2)
"
    ::= {RememberGUIPos 5}

syncStatStrRememberGUIPos  OBJECT-TYPE
    SYNTAX      OCTET STRING
    MAX-ACCESS  read-only
    STATUS      current
    DESCRIPTION
"
synchronization status line from file assp_sync.cfg for RememberGUIPos
 0 - synchronization not configured
 1 - out of sync - running master mode
 2 - in sync - running  mastermode
 3 - in sync - running slave mode
 4 - in sync - running master mode (wait to reach state 2)
"
    ::= {RememberGUIPos 6}

ConfigChangeSchedule  OBJECT-TYPE
    SYNTAX      OCTET STRING
    MAX-ACCESS  read-write
    STATUS      current
    DESCRIPTION
"
Use this option to schedule configuration changes. You must use the file option like 'file:files/configchangeschedule.txt' to define schedules - an empty value disables this feature.
 Define one schedule per line - comments are not allowed in a schedule definition line!
 The line has to start with the schedule string ( see ReStartSchedule ) followed by the variable (or hidden variable ) name to change, followed by ':=', followed by the value to change the variable to - like:
 8 0 * * * myNameAlso:=otherhost1.mydomain.tld
 0 6 * * *|0 10 * * * myNameAlso:=otherhost2.mydomain.tld
 0 1 * * * debug:=1
 0 2 * * * debug:=
 The schedule string can contain multiple schedule definitions separated by pipe'|'. You will get errors if:
 - the schedule definiton is wrong
 - the variable name is wrong (does not exists)
 - the syntax of the value is wrong
 Notice - assp will only check the syntax at definition time - the logical correctness of the value will be checked at the scheduled time! So, assp will (for example) not check any dependencies at definition time - if a dependency is wrong, the change request at the scheduled time will fail!
 Notice - all configuration changes are done with 'root' permission! For this reason, this configuration parameter is only visable to root and it is stored encrypted!
 For advanced users ONLY:
 Using the following extension, requires a deep internal knowledge of the assp code!
 It is also possible to schedule a call to an internal assp subroutine. The name of the subroutine has to begin with a '&amp;', the parameters that should passed to the subroutine must be in '()' - like:
 0 6 * * * &amp;subname(var1,var2,..,...)
 0 7 * * * &amp;subname()
 Notice: the subroutine will be called in the MainThread and syntax check will be done at run time - possible errors are shown in the log!
"
    REFERENCE "Schedule Configuration Changes*"
    DEFVAL { "" }
    ::= {ServerSetup 968}

syncStatConfigChangeSchedule  OBJECT-TYPE
    SYNTAX      OCTET STRING
    MAX-ACCESS  read-only
    STATUS      current
    DESCRIPTION
"
synchronization status for ConfigChangeSchedule
-1 - ConfigChangeSchedule could not be synchronized
 0 - synchronization not configured
 1 - out of sync - running master mode
 2 - in sync - running  mastermode
 3 - in sync - running slave mode
 4 - in sync - running master mode (wait to reach state 2)
"
    ::= {ConfigChangeSchedule 5}

syncStatStrConfigChangeSchedule  OBJECT-TYPE
    SYNTAX      OCTET STRING
    MAX-ACCESS  read-only
    STATUS      current
    DESCRIPTION
"
synchronization status line from file assp_sync.cfg for ConfigChangeSchedule
 0 - synchronization not configured
 1 - out of sync - running master mode
 2 - in sync - running  mastermode
 3 - in sync - running slave mode
 4 - in sync - running master mode (wait to reach state 2)
"
    ::= {ConfigChangeSchedule 6}

EnableHighPerformance  OBJECT-TYPE
    SYNTAX      OCTET STRING
    MAX-ACCESS  read-write
    STATUS      current
    DESCRIPTION
"
If set, the SMTP-Worker-Threads will get new pending connections much faster - using less wait states. The speed to interrupt the workers by the MainThread is increased. Using this feature will increase the CPU usage of the system!
"
    REFERENCE "Enable Higher Performance"
    DEFVAL { "0" }
    ::= {ServerSetup 970}

syncStatEnableHighPerformance  OBJECT-TYPE
    SYNTAX      OCTET STRING
    MAX-ACCESS  read-only
    STATUS      current
    DESCRIPTION
"
synchronization status for EnableHighPerformance
-1 - EnableHighPerformance could not be synchronized
 0 - synchronization not configured
 1 - out of sync - running master mode
 2 - in sync - running  mastermode
 3 - in sync - running slave mode
 4 - in sync - running master mode (wait to reach state 2)
"
    ::= {EnableHighPerformance 5}

syncStatStrEnableHighPerformance  OBJECT-TYPE
    SYNTAX      OCTET STRING
    MAX-ACCESS  read-only
    STATUS      current
    DESCRIPTION
"
synchronization status line from file assp_sync.cfg for EnableHighPerformance
 0 - synchronization not configured
 1 - out of sync - running master mode
 2 - in sync - running  mastermode
 3 - in sync - running slave mode
 4 - in sync - running master mode (wait to reach state 2)
"
    ::= {EnableHighPerformance 6}

host2IPminTTL  OBJECT-TYPE
    SYNTAX      OCTET STRING
    MAX-ACCESS  read-write
    STATUS      current
    DESCRIPTION
"
Minimum TTL used for config reload options, if hostnames are defined for any IP in regular expressions.
"
    REFERENCE "Minimum TTL used for config reload"
    DEFVAL { "300" }
    ::= {ServerSetup 981}

syncStathost2IPminTTL  OBJECT-TYPE
    SYNTAX      OCTET STRING
    MAX-ACCESS  read-only
    STATUS      current
    DESCRIPTION
"
synchronization status for host2IPminTTL
-1 - host2IPminTTL could not be synchronized
 0 - synchronization not configured
 1 - out of sync - running master mode
 2 - in sync - running  mastermode
 3 - in sync - running slave mode
 4 - in sync - running master mode (wait to reach state 2)
"
    ::= {host2IPminTTL 5}

syncStatStrhost2IPminTTL  OBJECT-TYPE
    SYNTAX      OCTET STRING
    MAX-ACCESS  read-only
    STATUS      current
    DESCRIPTION
"
synchronization status line from file assp_sync.cfg for host2IPminTTL
 0 - synchronization not configured
 1 - out of sync - running master mode
 2 - in sync - running  mastermode
 3 - in sync - running slave mode
 4 - in sync - running master mode (wait to reach state 2)
"
    ::= {host2IPminTTL 6}

HideIPandHelo  OBJECT-TYPE
    SYNTAX      OCTET STRING
    MAX-ACCESS  read-write
    STATUS      current
    DESCRIPTION
"
Replace any of these information ( ip=127.0.0.1 helo=anyhost.local ) in our received header for outgoing mails. use the syntax ip=127.0.0.1 and/or helo=anyhost.local .
"
    REFERENCE "Hide IP and/or Helo"
    DEFVAL { "" }
    ::= {ServerSetup 983}

syncStatHideIPandHelo  OBJECT-TYPE
    SYNTAX      OCTET STRING
    MAX-ACCESS  read-only
    STATUS      current
    DESCRIPTION
"
synchronization status for HideIPandHelo
-1 - HideIPandHelo could not be synchronized
 0 - synchronization not configured
 1 - out of sync - running master mode
 2 - in sync - running  mastermode
 3 - in sync - running slave mode
 4 - in sync - running master mode (wait to reach state 2)
"
    ::= {HideIPandHelo 5}

syncStatStrHideIPandHelo  OBJECT-TYPE
    SYNTAX      OCTET STRING
    MAX-ACCESS  read-only
    STATUS      current
    DESCRIPTION
"
synchronization status line from file assp_sync.cfg for HideIPandHelo
 0 - synchronization not configured
 1 - out of sync - running master mode
 2 - in sync - running  mastermode
 3 - in sync - running slave mode
 4 - in sync - running master mode (wait to reach state 2)
"
    ::= {HideIPandHelo 6}

asspCpuAffinity  OBJECT-TYPE
    SYNTAX      OCTET STRING
    MAX-ACCESS  read-write
    STATUS      current
    DESCRIPTION
"
Set the Cpu Affinity for all threads . Default is -1 (for use all CPU's). Possible values are comma or space separated CPU numbers starting with zero (0) or -1 for all CPU's. This requires installed  module. This feature will possibly not work on MacOS and OpenBSD and on any OS, if the system contains more than 32 CPU's.
"
    REFERENCE "Cpu Affinity for assp"
    DEFVAL { "-1" }
    ::= {ServerSetup 988}

MemoryUsageLimit  OBJECT-TYPE
    SYNTAX      OCTET STRING
    MAX-ACCESS  read-write
    STATUS      current
    DESCRIPTION
"
The memory limit in megabyte the assp process could use at maximum on your system. Set this to empty or zero to disable the feature. The check is done using the schedule defined in MemoryUsageCheckSchedule . If the assp process uses more memory than the limit at a scheduled time and assp is able to restart it self - a restart will be done within 15 seconds. The user running assp must have read access to /proc on nix systems or must have read access to the WMI provider on windows systems!
"
    REFERENCE "Memory Limit in MB that ASSP could use"
    DEFVAL { "" }
    ::= {ServerSetup 995}

MemoryUsageCheckSchedule  OBJECT-TYPE
    SYNTAX      OCTET STRING
    MAX-ACCESS  read-write
    STATUS      current
    DESCRIPTION
"
The schedule(s) that is used to check the current memory usage of the assp process compared to the MemoryUsageLimit. Default value is (0-59/10 * * * *), which means every 10 minutes. This requires an installed  module in PERL.
"
    REFERENCE "Schedule(s) to check the ASSP process memory usage <sup>s</sup>"
    DEFVAL { "0-59/10 * * * *" }
    ::= {ServerSetup 996}

syncStatMemoryUsageCheckSchedule  OBJECT-TYPE
    SYNTAX      OCTET STRING
    MAX-ACCESS  read-only
    STATUS      current
    DESCRIPTION
"
synchronization status for MemoryUsageCheckSchedule
-1 - MemoryUsageCheckSchedule could not be synchronized
 0 - synchronization not configured
 1 - out of sync - running master mode
 2 - in sync - running  mastermode
 3 - in sync - running slave mode
 4 - in sync - running master mode (wait to reach state 2)
"
    ::= {MemoryUsageCheckSchedule 5}

syncStatStrMemoryUsageCheckSchedule  OBJECT-TYPE
    SYNTAX      OCTET STRING
    MAX-ACCESS  read-only
    STATUS      current
    DESCRIPTION
"
synchronization status line from file assp_sync.cfg for MemoryUsageCheckSchedule
 0 - synchronization not configured
 1 - out of sync - running master mode
 2 - in sync - running  mastermode
 3 - in sync - running slave mode
 4 - in sync - running master mode (wait to reach state 2)
"
    ::= {MemoryUsageCheckSchedule 6}

enableGraphStats  OBJECT-TYPE
    SYNTAX      OCTET STRING
    MAX-ACCESS  read-write
    STATUS      current
    DESCRIPTION
"
ASSP will collect statistical data in files located in the '/logs' folder (scoreGraphStats-YYYY-MM.txt , statGraphStats-YYYY-MM.txt). If data are collected and the module lib/ASSP_SVG.pm is installed and the files images/stat.gplot, images/svg_style.css, images/svg_defs.svg and images/svg.js are installed and your browser supports SVG, assp will show graphical statistic data, if you click on a line in the 'Info and Stats' view.
 It is recommended to set 'SaveStatsEvery' to a value of 5 or 10 minutes, if this option is enabled!
 Keep in mind that assp will NOT delete any of the '*GraphStats...txt'-files. If you don't need some of that files anymore, remove them manualy!
"
    REFERENCE "Enable Graphical Statistics Collection"
    DEFVAL { "0" }
    ::= {ServerSetup 1000}

syncStatenableGraphStats  OBJECT-TYPE
    SYNTAX      OCTET STRING
    MAX-ACCESS  read-only
    STATUS      current
    DESCRIPTION
"
synchronization status for enableGraphStats
-1 - enableGraphStats could not be synchronized
 0 - synchronization not configured
 1 - out of sync - running master mode
 2 - in sync - running  mastermode
 3 - in sync - running slave mode
 4 - in sync - running master mode (wait to reach state 2)
"
    ::= {enableGraphStats 5}

syncStatStrenableGraphStats  OBJECT-TYPE
    SYNTAX      OCTET STRING
    MAX-ACCESS  read-only
    STATUS      current
    DESCRIPTION
"
synchronization status line from file assp_sync.cfg for enableGraphStats
 0 - synchronization not configured
 1 - out of sync - running master mode
 2 - in sync - running  mastermode
 3 - in sync - running slave mode
 4 - in sync - running master mode (wait to reach state 2)
"
    ::= {enableGraphStats 6}

myGreeting  OBJECT-TYPE
    SYNTAX      OCTET STRING
    MAX-ACCESS  read-write
    STATUS      current
    DESCRIPTION
"
Send this SMTP greeting (eg. 220 MYNAME is ready - using ASSP VERSION) instead of your MTA's SMTP greeting to the client. If not defined (default), the MTA's greeting will be sent to the client. The literal MYNAME will be replaced with myName and the literal VERSION will be replaced by the full version string of assp. If the starting '220 ' is not defined, assp will add it to the greeting.
"
    REFERENCE "Override the Server SMTP Greeting"
    DEFVAL { "" }
    ::= {ServerSetup 1026}

syncStatmyGreeting  OBJECT-TYPE
    SYNTAX      OCTET STRING
    MAX-ACCESS  read-only
    STATUS      current
    DESCRIPTION
"
synchronization status for myGreeting
-1 - myGreeting could not be synchronized
 0 - synchronization not configured
 1 - out of sync - running master mode
 2 - in sync - running  mastermode
 3 - in sync - running slave mode
 4 - in sync - running master mode (wait to reach state 2)
"
    ::= {myGreeting 5}

syncStatStrmyGreeting  OBJECT-TYPE
    SYNTAX      OCTET STRING
    MAX-ACCESS  read-only
    STATUS      current
    DESCRIPTION
"
synchronization status line from file assp_sync.cfg for myGreeting
 0 - synchronization not configured
 1 - out of sync - running master mode
 2 - in sync - running  mastermode
 3 - in sync - running slave mode
 4 - in sync - running master mode (wait to reach state 2)
"
    ::= {myGreeting 6}

normalizeUnicode  OBJECT-TYPE
    SYNTAX      OCTET STRING
    MAX-ACCESS  read-write
    STATUS      current
    DESCRIPTION
"
If set (which is the default and recommended), all regular expressions and both, the Bayesian and the HMM engine, are normalizing all characters in there setup and the checked content, according to unicode .
 In addition some extended (assp unique) unicode normalization is done for the unicode blocks 'Enclosed Alphanumerics', 'Enclosed Alphanumeric Supplement' , 'Enclosed CJK Letters And Months' and 'Enclosed Ideographic Supplement' - like: &#9312; &#9313; &#9331; &#9332; &#9352; &#9451; &#9461; &#9424; &#9398; &#127280; &#12809; &#12853; &#13003; &#127559;. Those characters are decomposed by compatibility, then recomposed by canonical equivalence (eg. to LATIN or CJK).
 If this value is changed, it is recommended to run a rebuildspamdb.
 This feature requires a Perl version 5.012000 (5.12.0) or higher.
 NOTICE: the rebuildspamdb task will take up to double the time, if this feature is enabled and non-LATIN mails are processed!
"
    REFERENCE "Normalize Unicode to NFKC"
    DEFVAL { "1" }
    ::= {ServerSetup 1042}

syncStatnormalizeUnicode  OBJECT-TYPE
    SYNTAX      OCTET STRING
    MAX-ACCESS  read-only
    STATUS      current
    DESCRIPTION
"
synchronization status for normalizeUnicode
-1 - normalizeUnicode could not be synchronized
 0 - synchronization not configured
 1 - out of sync - running master mode
 2 - in sync - running  mastermode
 3 - in sync - running slave mode
 4 - in sync - running master mode (wait to reach state 2)
"
    ::= {normalizeUnicode 5}

syncStatStrnormalizeUnicode  OBJECT-TYPE
    SYNTAX      OCTET STRING
    MAX-ACCESS  read-only
    STATUS      current
    DESCRIPTION
"
synchronization status line from file assp_sync.cfg for normalizeUnicode
 0 - synchronization not configured
 1 - out of sync - running master mode
 2 - in sync - running  mastermode
 3 - in sync - running slave mode
 4 - in sync - running master mode (wait to reach state 2)
"
    ::= {normalizeUnicode 6}

RebuildSpamdb  OBJECT IDENTIFIER ::= {asspConfig 33}
RebuildSchedule  OBJECT-TYPE
    SYNTAX      OCTET STRING
    MAX-ACCESS  read-write
    STATUS      current
    DESCRIPTION
"
If not set to 'noschedule' (noschedule is default) , ASSP uses scheduled times to run the RebuildSpamdb! The syntax is the same like in ! To disable the Scheduler write 'noschedule'! Never write quotes in to this field!
This requires an installed  module in PERL.
It is possible to define more than one scheduled time per day to keep the Bayesian and HMM databes up to date, but this is not required - use 'newReportedInterval' instead.
If a file C:/assp/rebuilddebug.txt exists, the rebuild task will write the debug output to this file.
Time and Date specification

Entry is the specification of the scheduled time in crontab format,
which contains five mandatory time and date fields.
Entry can be either a plain string, which contains
a whitespace separated time and date specification.

The time and date fields are (taken mostly from 'Vixie' cron):

<table BORDER CELLSPACING=0 CELLPADDING=4 WIDTH='50%' >
<tr><td>field</td><td>values</td></tr>
<tr><td>minute</td><td>0-59</td></tr>
<tr><td>hour</td><td>0-23</td></tr>
<tr><td>day of month</td><td>1-31</td></tr>
<tr><td>month</td><td>1-12 (or as names)</td></tr>
<tr><td>day of week</td><td>0-7 (0 or 7 is Sunday, or as names )</td></tr>
<tr><td>seconds</td><td>0-59 (optional) not supported inside ASSP !!!</td></tr>
</table>

 A field may be an asterisk (*), which always stands for
 'first-last'.

 Ranges of numbers are  allowed.  Ranges are two numbers
 separated  with  a  hyphen.   The  specified  range  is
 inclusive.   For example, 8-11  for an  'hours' entry
 specifies execution at hours 8, 9, 10 and 11.

 Lists  are allowed.   A list  is a  set of  numbers (or
 ranges)  separated by  commas.   Examples: '1,2,5,9',
 '0-4,8-12'.

 Step  values can  be used  in conjunction  with ranges.
 Following a range with '/<number>' specifies skips of
 the  numbers value  through the  range.   For example,
 '0-23/2' can  be used in  the hours field  to specify
 command execution every  other hour (the alternative in
 the V7 standard is '0,2,4,6,8,10,12,14,16,18,20,22').
 Steps are  also permitted after an asterisk,  so if you
 want to say 'every two hours', just use '*/2'.

 Names can also  be used for the 'month'  and 'day of
 week'  fields.  Use  the  first three  letters of  the
 particular day or month (case doesn't matter).

 Note:
       The day of a command's execution can be specified
       by two fields  -- day of month, and  day of week.
       If both fields are restricted (ie, aren't *), the
       command will be run when either field matches the
       current  time.  For  example, '30  4 1,15  * 5'
       would cause a command to be run at 4:30 am on the
       1st and 15th of each month, plus every Friday

Examples:

<table BORDER CELLSPACING=0 CELLPADDING=4 WIDTH='80%' >
<tr><td>8 0 * * *</td><td>==></td><td>8 minutes after midnight, every day</td></tr>
<tr><td>5 11 * * Sat,Sun</td><td>==></td><td>at 11:05 on each Saturday and Sunday</td></tr>
<tr><td>0-59/5 * * * *</td><td>==></td><td>every five minutes</td></tr>
<tr><td>42 12 3 Feb Sat</td><td>==></td><td>at 12:42 on 3rd of February and on each Saturday in February</td></tr>
<tr><td>32 11 * * * 0-30/2</td><td>==></td><td>11:32:00, 11:32:02, ... 11:32:30 every day</td></tr>
</table>

In addition, ranges or lists of names are allowed.
If you want to define multiple entries separate them by '|'
"
    REFERENCE "Schedule Cron time for RebuildSpamdb"
    DEFVAL { "noschedule" }
    ::= {RebuildSpamdb 807}

useDB4Rebuild  OBJECT-TYPE
    SYNTAX      OCTET STRING
    MAX-ACCESS  read-write
    STATUS      current
    DESCRIPTION
"
The RebuildSpamDB thread uses some internal caches that could grow to a large number of entries. Switch this on, if you want this thread to use less memory and be a little slower.
   Adjust RebuildThreadCycleTime to a lower value (between 0 and 30) to speed up the RebuildSpamDB thread.
   The perl module  version 0.34 or higher and BerkeleyDB version 4.5 or higher is required to use this feature. DB_File (Berkeley V1) will be used if BerkeleyDB is not available. If both BerkeleyDB and DB_File are not available, the rebuild thread will use the internal 'orderedtie' which is up to 1000 times slower than BerkeleyDB.
"
    REFERENCE "Use BerkeleyDB/DB_File or orderedtie for the RebuildSpamDB Internal Caches"
    DEFVAL { "" }
    ::= {RebuildSpamdb 808}

syncStatuseDB4Rebuild  OBJECT-TYPE
    SYNTAX      OCTET STRING
    MAX-ACCESS  read-only
    STATUS      current
    DESCRIPTION
"
synchronization status for useDB4Rebuild
-1 - useDB4Rebuild could not be synchronized
 0 - synchronization not configured
 1 - out of sync - running master mode
 2 - in sync - running  mastermode
 3 - in sync - running slave mode
 4 - in sync - running master mode (wait to reach state 2)
"
    ::= {useDB4Rebuild 5}

syncStatStruseDB4Rebuild  OBJECT-TYPE
    SYNTAX      OCTET STRING
    MAX-ACCESS  read-only
    STATUS      current
    DESCRIPTION
"
synchronization status line from file assp_sync.cfg for useDB4Rebuild
 0 - synchronization not configured
 1 - out of sync - running master mode
 2 - in sync - running  mastermode
 3 - in sync - running slave mode
 4 - in sync - running master mode (wait to reach state 2)
"
    ::= {useDB4Rebuild 6}

ReplaceOldSpamdb  OBJECT-TYPE
    SYNTAX      OCTET STRING
    MAX-ACCESS  read-write
    STATUS      current
    DESCRIPTION
"
If selected, the new created records for Spamdb and Spamdb.helo will replace the old (belongs not to HMM, which is replaced every time). If not seleted, the new records will be added to Spamdb and Spamdb.helo . Default is on.
"
    REFERENCE "Replace the old Records in Spamdb and Spamdb.helo"
    DEFVAL { "1" }
    ::= {RebuildSpamdb 809}

doMove2Num  OBJECT-TYPE
    SYNTAX      OCTET STRING
    MAX-ACCESS  read-write
    STATUS      current
    DESCRIPTION
"
Renames files to numbers before the rebuild is started. If this is done, some other features like 'MailLogTail' and 'Block-Report' will be unable to find the files!
"
    REFERENCE "Do move2num Before Rebuild"
    DEFVAL { "" }
    ::= {RebuildSpamdb 810}

syncStatdoMove2Num  OBJECT-TYPE
    SYNTAX      OCTET STRING
    MAX-ACCESS  read-only
    STATUS      current
    DESCRIPTION
"
synchronization status for doMove2Num
-1 - doMove2Num could not be synchronized
 0 - synchronization not configured
 1 - out of sync - running master mode
 2 - in sync - running  mastermode
 3 - in sync - running slave mode
 4 - in sync - running master mode (wait to reach state 2)
"
    ::= {doMove2Num 5}

syncStatStrdoMove2Num  OBJECT-TYPE
    SYNTAX      OCTET STRING
    MAX-ACCESS  read-only
    STATUS      current
    DESCRIPTION
"
synchronization status line from file assp_sync.cfg for doMove2Num
 0 - synchronization not configured
 1 - out of sync - running master mode
 2 - in sync - running  mastermode
 3 - in sync - running slave mode
 4 - in sync - running master mode (wait to reach state 2)
"
    ::= {doMove2Num 6}

RebuildNotify  OBJECT-TYPE
    SYNTAX      OCTET STRING
    MAX-ACCESS  read-write
    STATUS      current
    DESCRIPTION
"
Email address(es) to which you want ASSP to send a notification email after the rebuild task is finished. The file rebuildrun.txt is included in this notification. Separate multiple entries by '|'.
"
    REFERENCE "Notification Email To"
    DEFVAL { "" }
    ::= {RebuildSpamdb 811}

syncStatRebuildNotify  OBJECT-TYPE
    SYNTAX      OCTET STRING
    MAX-ACCESS  read-only
    STATUS      current
    DESCRIPTION
"
synchronization status for RebuildNotify
-1 - RebuildNotify could not be synchronized
 0 - synchronization not configured
 1 - out of sync - running master mode
 2 - in sync - running  mastermode
 3 - in sync - running slave mode
 4 - in sync - running master mode (wait to reach state 2)
"
    ::= {RebuildNotify 5}

syncStatStrRebuildNotify  OBJECT-TYPE
    SYNTAX      OCTET STRING
    MAX-ACCESS  read-only
    STATUS      current
    DESCRIPTION
"
synchronization status line from file assp_sync.cfg for RebuildNotify
 0 - synchronization not configured
 1 - out of sync - running master mode
 2 - in sync - running  mastermode
 3 - in sync - running slave mode
 4 - in sync - running master mode (wait to reach state 2)
"
    ::= {RebuildNotify 6}

RunRebuildNow  OBJECT-TYPE
    SYNTAX      OCTET STRING
    MAX-ACCESS  read-write
    STATUS      current
    DESCRIPTION
"
If selected, RebuildSpamdb will be started immediately.&nbsp;
  
  <div class='menuLevel1'>normfile - shows current:
  Corpus-Norm , Corrected-SpamFiles , Corrected-NotSpamFiles , Spamlog-Files , NotSpamlog-Files , SpamWords/File , Hamwords/File , Spamwords , Hamwords</div>
  
"
    REFERENCE "Run RebuildSpamdb now"
    DEFVAL { "" }
    ::= {RebuildSpamdb 812}

MaxKeepDeleted  OBJECT-TYPE
    SYNTAX      OCTET STRING
    MAX-ACCESS  read-write
    STATUS      current
    DESCRIPTION
"
The maximum number in days deleted files in the bayesian collection folders ( spamlog , notspamlog ) will be kept. This is necessary when EmailBlockReport is used to handle the file and the file is meanwhile deleted. The list of files that are maked for deletion is stored in trashlist.db .
"
    REFERENCE "Max Days of Keep Deleted"
    DEFVAL { "0" }
    ::= {RebuildSpamdb 865}

syncStatMaxKeepDeleted  OBJECT-TYPE
    SYNTAX      OCTET STRING
    MAX-ACCESS  read-only
    STATUS      current
    DESCRIPTION
"
synchronization status for MaxKeepDeleted
-1 - MaxKeepDeleted could not be synchronized
 0 - synchronization not configured
 1 - out of sync - running master mode
 2 - in sync - running  mastermode
 3 - in sync - running slave mode
 4 - in sync - running master mode (wait to reach state 2)
"
    ::= {MaxKeepDeleted 5}

syncStatStrMaxKeepDeleted  OBJECT-TYPE
    SYNTAX      OCTET STRING
    MAX-ACCESS  read-only
    STATUS      current
    DESCRIPTION
"
synchronization status line from file assp_sync.cfg for MaxKeepDeleted
 0 - synchronization not configured
 1 - out of sync - running master mode
 2 - in sync - running  mastermode
 3 - in sync - running slave mode
 4 - in sync - running master mode (wait to reach state 2)
"
    ::= {MaxKeepDeleted 6}

autoCorrectCorpus  OBJECT-TYPE
    SYNTAX      OCTET STRING
    MAX-ACCESS  read-write
    STATUS      current
    DESCRIPTION
"
(Syntax: a.a[a]-b.b[b]-cccc-dd or empty - default is '0.6-1.4-4000-14') If the corpus norm (the weight between spamwords/hamwords) is less than 'a' (0.6 - too much ham) or greater than 'b' (1.4 - too much spam), assp will delete the excess (oldest) files from the corresponding folder ( spamlog , notspamlog ). ASSP will keep a minimum of 'c' (4000) files in the folder and will never delete files that are younger than 'd' (14) days. This cleanup will run at the end of the rebuildspamdb task. So the corrected file corpus will take effect at the next rebuildspamdb!
  If this value is defined, assp will use the middle value of 'a' and 'b' ((a+b)/2) as target corpusnorm and will try to reach this value, using (as many as possible) but only such a count of files in the folders spamlog and notspamlog as required!
"
    REFERENCE "Automatic Corpus Correction"
    DEFVAL { "0.6-1.4-4000-14" }
    ::= {RebuildSpamdb 898}

syncStatautoCorrectCorpus  OBJECT-TYPE
    SYNTAX      OCTET STRING
    MAX-ACCESS  read-only
    STATUS      current
    DESCRIPTION
"
synchronization status for autoCorrectCorpus
-1 - autoCorrectCorpus could not be synchronized
 0 - synchronization not configured
 1 - out of sync - running master mode
 2 - in sync - running  mastermode
 3 - in sync - running slave mode
 4 - in sync - running master mode (wait to reach state 2)
"
    ::= {autoCorrectCorpus 5}

syncStatStrautoCorrectCorpus  OBJECT-TYPE
    SYNTAX      OCTET STRING
    MAX-ACCESS  read-only
    STATUS      current
    DESCRIPTION
"
synchronization status line from file assp_sync.cfg for autoCorrectCorpus
 0 - synchronization not configured
 1 - out of sync - running master mode
 2 - in sync - running  mastermode
 3 - in sync - running slave mode
 4 - in sync - running master mode (wait to reach state 2)
"
    ::= {autoCorrectCorpus 6}

RebuildFileTimeLimit  OBJECT-TYPE
    SYNTAX      OCTET STRING
    MAX-ACCESS  read-write
    STATUS      current
    DESCRIPTION
"
(Syntax: a[.aa] b[.bb] - default is '1 5')
   Define one, or two space or comma separated values.
   If the first value is not zero and the processing time of a single corpus file exceeds the first value in seconds, this will be shown in the rebuild log.
   If the second value is not zero and the processing time of a single corpus file exceeds the second value in seconds, the file will be moved to the folder '$base/rebuild_error' to prevent future runtime penalties.
"
    REFERENCE "File Processing time Limit"
    DEFVAL { "1 5" }
    ::= {RebuildSpamdb 962}

syncStatRebuildFileTimeLimit  OBJECT-TYPE
    SYNTAX      OCTET STRING
    MAX-ACCESS  read-only
    STATUS      current
    DESCRIPTION
"
synchronization status for RebuildFileTimeLimit
-1 - RebuildFileTimeLimit could not be synchronized
 0 - synchronization not configured
 1 - out of sync - running master mode
 2 - in sync - running  mastermode
 3 - in sync - running slave mode
 4 - in sync - running master mode (wait to reach state 2)
"
    ::= {RebuildFileTimeLimit 5}

syncStatStrRebuildFileTimeLimit  OBJECT-TYPE
    SYNTAX      OCTET STRING
    MAX-ACCESS  read-only
    STATUS      current
    DESCRIPTION
"
synchronization status line from file assp_sync.cfg for RebuildFileTimeLimit
 0 - synchronization not configured
 1 - out of sync - running master mode
 2 - in sync - running  mastermode
 3 - in sync - running slave mode
 4 - in sync - running master mode (wait to reach state 2)
"
    ::= {RebuildFileTimeLimit 6}

RebuildTestMode  OBJECT-TYPE
    SYNTAX      OCTET STRING
    MAX-ACCESS  read-write
    STATUS      current
    DESCRIPTION
"
If selected, all rebuildspamdb tasks will not populate the spamdb and hmmdb - and no data will be sent to the griplist-Server.
"
    REFERENCE "Run the Rebuild in Test Mode"
    DEFVAL { "" }
    ::= {RebuildSpamdb 972}

syncStatRebuildTestMode  OBJECT-TYPE
    SYNTAX      OCTET STRING
    MAX-ACCESS  read-only
    STATUS      current
    DESCRIPTION
"
synchronization status for RebuildTestMode
-1 - RebuildTestMode could not be synchronized
 0 - synchronization not configured
 1 - out of sync - running master mode
 2 - in sync - running  mastermode
 3 - in sync - running slave mode
 4 - in sync - running master mode (wait to reach state 2)
"
    ::= {RebuildTestMode 5}

syncStatStrRebuildTestMode  OBJECT-TYPE
    SYNTAX      OCTET STRING
    MAX-ACCESS  read-only
    STATUS      current
    DESCRIPTION
"
synchronization status line from file assp_sync.cfg for RebuildTestMode
 0 - synchronization not configured
 1 - out of sync - running master mode
 2 - in sync - running  mastermode
 3 - in sync - running slave mode
 4 - in sync - running master mode (wait to reach state 2)
"
    ::= {RebuildTestMode 6}

forceRebuildDowngrade  OBJECT-TYPE
    SYNTAX      OCTET STRING
    MAX-ACCESS  read-write
    STATUS      current
    DESCRIPTION
"
Keep rebuildspamdb.pm compatible to assp.pl in case of an assp.pl version downgrade.
"
    REFERENCE "Keep rebuildspamdb.pm compatible to assp.pl"
    DEFVAL { "1" }
    ::= {RebuildSpamdb 984}

syncStatforceRebuildDowngrade  OBJECT-TYPE
    SYNTAX      OCTET STRING
    MAX-ACCESS  read-only
    STATUS      current
    DESCRIPTION
"
synchronization status for forceRebuildDowngrade
-1 - forceRebuildDowngrade could not be synchronized
 0 - synchronization not configured
 1 - out of sync - running master mode
 2 - in sync - running  mastermode
 3 - in sync - running slave mode
 4 - in sync - running master mode (wait to reach state 2)
"
    ::= {forceRebuildDowngrade 5}

syncStatStrforceRebuildDowngrade  OBJECT-TYPE
    SYNTAX      OCTET STRING
    MAX-ACCESS  read-only
    STATUS      current
    DESCRIPTION
"
synchronization status line from file assp_sync.cfg for forceRebuildDowngrade
 0 - synchronization not configured
 1 - out of sync - running master mode
 2 - in sync - running  mastermode
 3 - in sync - running slave mode
 4 - in sync - running master mode (wait to reach state 2)
"
    ::= {forceRebuildDowngrade 6}

newReportedInterval  OBJECT-TYPE
    SYNTAX      OCTET STRING
    MAX-ACCESS  read-write
    STATUS      current
    DESCRIPTION
"
File count and interval definition (count minutes) for processing new reported mails (correctedspam , correctednotspam) - process if at least 'first value' mails are reported but every 'second value' minutes. defaults to '10 5'
 Set the first value to zero to disable this feature.
 If enabled, new reported mails or files moved in to the corpus via GUI are used, to immediatly update the Spamdb and HMMdb with the new information.
 This will keep the databases continuously uptodate and the RebuildSchedule interval could be increased, if there are enough files in the corpus and your corpus norm is fine.
 If you need to copy/move several files from outside assp in to the corpus and you want assp to process them immediatly, copy/move the files in to the subfolder 'error/.../newManualyAdded'.
"
    REFERENCE "Interval for processing new Reported Mails"
    DEFVAL { "10 5" }
    ::= {RebuildSpamdb 987}

syncStatnewReportedInterval  OBJECT-TYPE
    SYNTAX      OCTET STRING
    MAX-ACCESS  read-only
    STATUS      current
    DESCRIPTION
"
synchronization status for newReportedInterval
-1 - newReportedInterval could not be synchronized
 0 - synchronization not configured
 1 - out of sync - running master mode
 2 - in sync - running  mastermode
 3 - in sync - running slave mode
 4 - in sync - running master mode (wait to reach state 2)
"
    ::= {newReportedInterval 5}

syncStatStrnewReportedInterval  OBJECT-TYPE
    SYNTAX      OCTET STRING
    MAX-ACCESS  read-only
    STATUS      current
    DESCRIPTION
"
synchronization status line from file assp_sync.cfg for newReportedInterval
 0 - synchronization not configured
 1 - out of sync - running master mode
 2 - in sync - running  mastermode
 3 - in sync - running slave mode
 4 - in sync - running master mode (wait to reach state 2)
"
    ::= {newReportedInterval 6}

CharConversionsTNEF  OBJECT IDENTIFIER ::= {asspConfig 34}
inChrSetConv  OBJECT-TYPE
    SYNTAX      OCTET STRING
    MAX-ACCESS  read-write
    STATUS      current
    DESCRIPTION
"
If defined, characterset conversion for inbound mails will be done. For example: if your emailserver does not understand UTF-8, ASSP will convert the mail parts to the characterset of your choice. The rules specified here are used to convert text parts of inbound mails from one to an other characterset.Example:UTF-8=>ISO-8859-1|ISO-8859-15=>ISO-8859-1
 This requires an installed  module in PERL.
 This conversions are done for all (inbound,CC,report ..) mails except relayed mails. The converted mail will be not available on disk except DEBUG.
"
    REFERENCE "inbound charset conversion table*"
    DEFVAL { "" }
    ::= {CharConversionsTNEF 813}

syncStatinChrSetConv  OBJECT-TYPE
    SYNTAX      OCTET STRING
    MAX-ACCESS  read-only
    STATUS      current
    DESCRIPTION
"
synchronization status for inChrSetConv
-1 - inChrSetConv could not be synchronized
 0 - synchronization not configured
 1 - out of sync - running master mode
 2 - in sync - running  mastermode
 3 - in sync - running slave mode
 4 - in sync - running master mode (wait to reach state 2)
"
    ::= {inChrSetConv 5}

syncStatStrinChrSetConv  OBJECT-TYPE
    SYNTAX      OCTET STRING
    MAX-ACCESS  read-only
    STATUS      current
    DESCRIPTION
"
synchronization status line from file assp_sync.cfg for inChrSetConv
 0 - synchronization not configured
 1 - out of sync - running master mode
 2 - in sync - running  mastermode
 3 - in sync - running slave mode
 4 - in sync - running master mode (wait to reach state 2)
"
    ::= {inChrSetConv 6}

outChrSetConv  OBJECT-TYPE
    SYNTAX      OCTET STRING
    MAX-ACCESS  read-write
    STATUS      current
    DESCRIPTION
"
If defined, characterset conversion for outbound mails will be done. For example: if your emailserver is unable to send mails in UTF-8, ASSP will convert the mail parts to UTF-8. The rules specified here are used to convert text parts of outbound mails from one to an other characterset.Example:ISO-8859-1=>UTF-8|ISO-8859-2=>UTF-8|windows-1250=>UTF-8
 This requires an installed  module in PERL.
 This conversions are done only for relayed mails!
"
    REFERENCE "outbound charset conversion table*"
    DEFVAL { "" }
    ::= {CharConversionsTNEF 814}

syncStatoutChrSetConv  OBJECT-TYPE
    SYNTAX      OCTET STRING
    MAX-ACCESS  read-only
    STATUS      current
    DESCRIPTION
"
synchronization status for outChrSetConv
-1 - outChrSetConv could not be synchronized
 0 - synchronization not configured
 1 - out of sync - running master mode
 2 - in sync - running  mastermode
 3 - in sync - running slave mode
 4 - in sync - running master mode (wait to reach state 2)
"
    ::= {outChrSetConv 5}

syncStatStroutChrSetConv  OBJECT-TYPE
    SYNTAX      OCTET STRING
    MAX-ACCESS  read-only
    STATUS      current
    DESCRIPTION
"
synchronization status line from file assp_sync.cfg for outChrSetConv
 0 - synchronization not configured
 1 - out of sync - running master mode
 2 - in sync - running  mastermode
 3 - in sync - running slave mode
 4 - in sync - running master mode (wait to reach state 2)
"
    ::= {outChrSetConv 6}

doInFixTNEF  OBJECT-TYPE
    SYNTAX      OCTET STRING
    MAX-ACCESS  read-write
    STATUS      current
    DESCRIPTION
"
convert inbound MS-TNEF attachments like winmail.dat to MIME parts/attachments. If a TNEF-file is attached by other than Exchange (like application/octet-stream) no conversion will be done. 
 In addition to  this requires both installed  and  module in PERL.
"
    REFERENCE "convert inbound MS-TNEF attachments to MIME"
    DEFVAL { "" }
    ::= {CharConversionsTNEF 815}

syncStatdoInFixTNEF  OBJECT-TYPE
    SYNTAX      OCTET STRING
    MAX-ACCESS  read-only
    STATUS      current
    DESCRIPTION
"
synchronization status for doInFixTNEF
-1 - doInFixTNEF could not be synchronized
 0 - synchronization not configured
 1 - out of sync - running master mode
 2 - in sync - running  mastermode
 3 - in sync - running slave mode
 4 - in sync - running master mode (wait to reach state 2)
"
    ::= {doInFixTNEF 5}

syncStatStrdoInFixTNEF  OBJECT-TYPE
    SYNTAX      OCTET STRING
    MAX-ACCESS  read-only
    STATUS      current
    DESCRIPTION
"
synchronization status line from file assp_sync.cfg for doInFixTNEF
 0 - synchronization not configured
 1 - out of sync - running master mode
 2 - in sync - running  mastermode
 3 - in sync - running slave mode
 4 - in sync - running master mode (wait to reach state 2)
"
    ::= {doInFixTNEF 6}

keepInTNEF  OBJECT-TYPE
    SYNTAX      OCTET STRING
    MAX-ACCESS  read-write
    STATUS      current
    DESCRIPTION
"
keep inbound MS-TNEF attachments like winmail.dat in MIME parts. If unchecked and the conversion is successfull, the original attachment will be removed from mail!
"
    REFERENCE "keep the MS-TNEF part in inbound mail"
    DEFVAL { "1" }
    ::= {CharConversionsTNEF 816}

syncStatkeepInTNEF  OBJECT-TYPE
    SYNTAX      OCTET STRING
    MAX-ACCESS  read-only
    STATUS      current
    DESCRIPTION
"
synchronization status for keepInTNEF
-1 - keepInTNEF could not be synchronized
 0 - synchronization not configured
 1 - out of sync - running master mode
 2 - in sync - running  mastermode
 3 - in sync - running slave mode
 4 - in sync - running master mode (wait to reach state 2)
"
    ::= {keepInTNEF 5}

syncStatStrkeepInTNEF  OBJECT-TYPE
    SYNTAX      OCTET STRING
    MAX-ACCESS  read-only
    STATUS      current
    DESCRIPTION
"
synchronization status line from file assp_sync.cfg for keepInTNEF
 0 - synchronization not configured
 1 - out of sync - running master mode
 2 - in sync - running  mastermode
 3 - in sync - running slave mode
 4 - in sync - running master mode (wait to reach state 2)
"
    ::= {keepInTNEF 6}

doOutFixTNEF  OBJECT-TYPE
    SYNTAX      OCTET STRING
    MAX-ACCESS  read-write
    STATUS      current
    DESCRIPTION
"
convert outbound MS-TNEF attachments like winmail.dat to MIME parts/attachments. If a TNEF-file is attached by other than Exchange (like application/octet-stream) no conversion will be done.
 In addition to  this requires both installed  and  module in PERL.
"
    REFERENCE "convert outbound MS-TNEF attachments to MIME"
    DEFVAL { "" }
    ::= {CharConversionsTNEF 817}

syncStatdoOutFixTNEF  OBJECT-TYPE
    SYNTAX      OCTET STRING
    MAX-ACCESS  read-only
    STATUS      current
    DESCRIPTION
"
synchronization status for doOutFixTNEF
-1 - doOutFixTNEF could not be synchronized
 0 - synchronization not configured
 1 - out of sync - running master mode
 2 - in sync - running  mastermode
 3 - in sync - running slave mode
 4 - in sync - running master mode (wait to reach state 2)
"
    ::= {doOutFixTNEF 5}

syncStatStrdoOutFixTNEF  OBJECT-TYPE
    SYNTAX      OCTET STRING
    MAX-ACCESS  read-only
    STATUS      current
    DESCRIPTION
"
synchronization status line from file assp_sync.cfg for doOutFixTNEF
 0 - synchronization not configured
 1 - out of sync - running master mode
 2 - in sync - running  mastermode
 3 - in sync - running slave mode
 4 - in sync - running master mode (wait to reach state 2)
"
    ::= {doOutFixTNEF 6}

keepOutTNEF  OBJECT-TYPE
    SYNTAX      OCTET STRING
    MAX-ACCESS  read-write
    STATUS      current
    DESCRIPTION
"
keep outbound MS-TNEF attachments like winmail.dat in MIME parts. If unchecked and the conversion is successfull, the original attachment will be removed from mail!
"
    REFERENCE "keep the MS-TNEF part in outbound mail"
    DEFVAL { "1" }
    ::= {CharConversionsTNEF 818}

syncStatkeepOutTNEF  OBJECT-TYPE
    SYNTAX      OCTET STRING
    MAX-ACCESS  read-only
    STATUS      current
    DESCRIPTION
"
synchronization status for keepOutTNEF
-1 - keepOutTNEF could not be synchronized
 0 - synchronization not configured
 1 - out of sync - running master mode
 2 - in sync - running  mastermode
 3 - in sync - running slave mode
 4 - in sync - running master mode (wait to reach state 2)
"
    ::= {keepOutTNEF 5}

syncStatStrkeepOutTNEF  OBJECT-TYPE
    SYNTAX      OCTET STRING
    MAX-ACCESS  read-only
    STATUS      current
    DESCRIPTION
"
synchronization status line from file assp_sync.cfg for keepOutTNEF
 0 - synchronization not configured
 1 - out of sync - running master mode
 2 - in sync - running  mastermode
 3 - in sync - running slave mode
 4 - in sync - running master mode (wait to reach state 2)
"
    ::= {keepOutTNEF 6}

doDKIMConv  OBJECT-TYPE
    SYNTAX      OCTET STRING
    MAX-ACCESS  read-write
    STATUS      current
    DESCRIPTION
"
DKIM messages could normally not modified. If checked, conversions will be done on DKIM messages - you have to disable the DKIM check on your emailserver (MTA)!
"
    REFERENCE "convert DKIM mails"
    DEFVAL { "0" }
    ::= {CharConversionsTNEF 819}

syncStatdoDKIMConv  OBJECT-TYPE
    SYNTAX      OCTET STRING
    MAX-ACCESS  read-only
    STATUS      current
    DESCRIPTION
"
synchronization status for doDKIMConv
-1 - doDKIMConv could not be synchronized
 0 - synchronization not configured
 1 - out of sync - running master mode
 2 - in sync - running  mastermode
 3 - in sync - running slave mode
 4 - in sync - running master mode (wait to reach state 2)
"
    ::= {doDKIMConv 5}

syncStatStrdoDKIMConv  OBJECT-TYPE
    SYNTAX      OCTET STRING
    MAX-ACCESS  read-only
    STATUS      current
    DESCRIPTION
"
synchronization status line from file assp_sync.cfg for doDKIMConv
 0 - synchronization not configured
 1 - out of sync - running master mode
 2 - in sync - running  mastermode
 3 - in sync - running slave mode
 4 - in sync - running master mode (wait to reach state 2)
"
    ::= {doDKIMConv 6}

TNEFDEBUG  OBJECT-TYPE
    SYNTAX      OCTET STRING
    MAX-ACCESS  read-write
    STATUS      current
    DESCRIPTION
"
prints TNEF conversion debug info to screen.
  
"
    REFERENCE "TNEFDEBUG (only in dev)"
    DEFVAL { "" }
    ::= {CharConversionsTNEF 820}

syncStatTNEFDEBUG  OBJECT-TYPE
    SYNTAX      OCTET STRING
    MAX-ACCESS  read-only
    STATUS      current
    DESCRIPTION
"
synchronization status for TNEFDEBUG
-1 - TNEFDEBUG could not be synchronized
 0 - synchronization not configured
 1 - out of sync - running master mode
 2 - in sync - running  mastermode
 3 - in sync - running slave mode
 4 - in sync - running master mode (wait to reach state 2)
"
    ::= {TNEFDEBUG 5}

syncStatStrTNEFDEBUG  OBJECT-TYPE
    SYNTAX      OCTET STRING
    MAX-ACCESS  read-only
    STATUS      current
    DESCRIPTION
"
synchronization status line from file assp_sync.cfg for TNEFDEBUG
 0 - synchronization not configured
 1 - out of sync - running master mode
 2 - in sync - running  mastermode
 3 - in sync - running slave mode
 4 - in sync - running master mode (wait to reach state 2)
"
    ::= {TNEFDEBUG 6}

convertNP  OBJECT-TYPE
    SYNTAX      OCTET STRING
    MAX-ACCESS  read-write
    STATUS      current
    DESCRIPTION
"
Set this to on, if noprocessing mails should be converted, which is normally not the case.
"
    REFERENCE "convert NoProcessing mails"
    DEFVAL { "" }
    ::= {CharConversionsTNEF 884}

syncStatconvertNP  OBJECT-TYPE
    SYNTAX      OCTET STRING
    MAX-ACCESS  read-only
    STATUS      current
    DESCRIPTION
"
synchronization status for convertNP
-1 - convertNP could not be synchronized
 0 - synchronization not configured
 1 - out of sync - running master mode
 2 - in sync - running  mastermode
 3 - in sync - running slave mode
 4 - in sync - running master mode (wait to reach state 2)
"
    ::= {convertNP 5}

syncStatStrconvertNP  OBJECT-TYPE
    SYNTAX      OCTET STRING
    MAX-ACCESS  read-only
    STATUS      current
    DESCRIPTION
"
synchronization status line from file assp_sync.cfg for convertNP
 0 - synchronization not configured
 1 - out of sync - running master mode
 2 - in sync - running  mastermode
 3 - in sync - running slave mode
 4 - in sync - running master mode (wait to reach state 2)
"
    ::= {convertNP 6}

SSLProxyandTLSsupport  OBJECT IDENTIFIER ::= {asspConfig 35}
DoTLS  OBJECT-TYPE
    SYNTAX      OCTET STRING
    MAX-ACCESS  read-write
    STATUS      current
    DESCRIPTION
"
If set to 'drop TLS', any STARTTLS request will be removed from the protocol stack and no connection will ever go in to any TLS mode!
  If set to 'TLS to Proxy' and both peers (client and server) supports TLS, both connection will be moved in to a transparent Proxy mode. All data will be encrypted and unreadable to ASSP.
  If set to 'do TLS', ASSP will be the 'man in the middle'. ASSP will try to move both connections in to TLS. All data will be readable to ASSP - so all checks could be done. If any of the peers does not support TLS, ASSP will fake this (250-STARTTLS) to the other peer. So it could be possible, that the connection to the client is going in to TLS mode, even if TLS is not supported by the server. If a client does not request TLS (STARTTLS) even it has got the (250-STARTTLS), ASSP tries to start a TLS session to server, if he has sent (250-STARTTLS)! This behavior belongs to incoming and outgoing messages. This option requires the installed perl module !
  For 'do TLS' a server-certificate-file ' SSLCertFile ' and a server-key-file ' SSLKeyFile ' must exist and must be valid!
  If you do not have valid certificates, you may generate both files online with  or you may use OpenSSL to generate ! If you have installed OpenSSL (must be in PATH) and installed and enabled IO::Socket::SSL and ASSP is unable to find valid certificates - ASSP will try to create them at startup!
  
"
    REFERENCE "How to Handle STARTTLS Requests"
    DEFVAL { "0" }
    ::= {SSLProxyandTLSsupport 821}

syncStatDoTLS  OBJECT-TYPE
    SYNTAX      OCTET STRING
    MAX-ACCESS  read-only
    STATUS      current
    DESCRIPTION
"
synchronization status for DoTLS
-1 - DoTLS could not be synchronized
 0 - synchronization not configured
 1 - out of sync - running master mode
 2 - in sync - running  mastermode
 3 - in sync - running slave mode
 4 - in sync - running master mode (wait to reach state 2)
"
    ::= {DoTLS 5}

syncStatStrDoTLS  OBJECT-TYPE
    SYNTAX      OCTET STRING
    MAX-ACCESS  read-only
    STATUS      current
    DESCRIPTION
"
synchronization status line from file assp_sync.cfg for DoTLS
 0 - synchronization not configured
 1 - out of sync - running master mode
 2 - in sync - running  mastermode
 3 - in sync - running slave mode
 4 - in sync - running master mode (wait to reach state 2)
"
    ::= {DoTLS 6}

NoTLSlistenPorts  OBJECT-TYPE
    SYNTAX      OCTET STRING
    MAX-ACCESS  read-write
    STATUS      current
    DESCRIPTION
"
This disables TLS/SSL on the defined listenPorts, if DoTLS is set to 'do TLS'. All other SMTP listeners will support TLS/SSL, if DoTLS is set to 'do TLS'. This option works for listenPort , listenPort2 and relayPort . The listener definition here has to be the same like in the port definitions. Separate multiple entries by '|'.Examples: 25, 127.0.0.1:25, 127.0.0.1:25|127.0.0.2:25 
"
    REFERENCE "Disable SSL support on listenPorts"
    DEFVAL { "" }
    ::= {SSLProxyandTLSsupport 822}

syncStatNoTLSlistenPorts  OBJECT-TYPE
    SYNTAX      OCTET STRING
    MAX-ACCESS  read-only
    STATUS      current
    DESCRIPTION
"
synchronization status for NoTLSlistenPorts
-1 - NoTLSlistenPorts could not be synchronized
 0 - synchronization not configured
 1 - out of sync - running master mode
 2 - in sync - running  mastermode
 3 - in sync - running slave mode
 4 - in sync - running master mode (wait to reach state 2)
"
    ::= {NoTLSlistenPorts 5}

syncStatStrNoTLSlistenPorts  OBJECT-TYPE
    SYNTAX      OCTET STRING
    MAX-ACCESS  read-only
    STATUS      current
    DESCRIPTION
"
synchronization status line from file assp_sync.cfg for NoTLSlistenPorts
 0 - synchronization not configured
 1 - out of sync - running master mode
 2 - in sync - running  mastermode
 3 - in sync - running slave mode
 4 - in sync - running master mode (wait to reach state 2)
"
    ::= {NoTLSlistenPorts 6}

SSLCertFile  OBJECT-TYPE
    SYNTAX      OCTET STRING
    MAX-ACCESS  read-write
    STATUS      current
    DESCRIPTION
"
Full path to the file containing the server's SSL certificate or certificate-chain, for example : /usr/local/etc/ssl/certs/assp-cert.pem or c:/assp/certs/server-cert.pem. A general cert.pem file is already provided in 'assp/certs/server-cert.pem'.
"
    REFERENCE "SSL Certificate File (PEM format)"
    DEFVAL { "C:/assp/certs/server-cert.pem" }
    ::= {SSLProxyandTLSsupport 823}

syncStatSSLCertFile  OBJECT-TYPE
    SYNTAX      OCTET STRING
    MAX-ACCESS  read-only
    STATUS      current
    DESCRIPTION
"
synchronization status for SSLCertFile
-1 - SSLCertFile could not be synchronized
 0 - synchronization not configured
 1 - out of sync - running master mode
 2 - in sync - running  mastermode
 3 - in sync - running slave mode
 4 - in sync - running master mode (wait to reach state 2)
"
    ::= {SSLCertFile 5}

syncStatStrSSLCertFile  OBJECT-TYPE
    SYNTAX      OCTET STRING
    MAX-ACCESS  read-only
    STATUS      current
    DESCRIPTION
"
synchronization status line from file assp_sync.cfg for SSLCertFile
 0 - synchronization not configured
 1 - out of sync - running master mode
 2 - in sync - running  mastermode
 3 - in sync - running slave mode
 4 - in sync - running master mode (wait to reach state 2)
"
    ::= {SSLCertFile 6}

SSLKeyFile  OBJECT-TYPE
    SYNTAX      OCTET STRING
    MAX-ACCESS  read-write
    STATUS      current
    DESCRIPTION
"
Full path to the file containing the server's SSL private key, for example: /usr/local/etc/ssl/certs/assp-key.pem or c:/assp/certs/server-key.pem. A general key.pem file is already provided in 'assp/certs/server-key.pem'
"
    REFERENCE "SSL Key File (PEM format)"
    DEFVAL { "C:/assp/certs/server-key.pem" }
    ::= {SSLProxyandTLSsupport 824}

syncStatSSLKeyFile  OBJECT-TYPE
    SYNTAX      OCTET STRING
    MAX-ACCESS  read-only
    STATUS      current
    DESCRIPTION
"
synchronization status for SSLKeyFile
-1 - SSLKeyFile could not be synchronized
 0 - synchronization not configured
 1 - out of sync - running master mode
 2 - in sync - running  mastermode
 3 - in sync - running slave mode
 4 - in sync - running master mode (wait to reach state 2)
"
    ::= {SSLKeyFile 5}

syncStatStrSSLKeyFile  OBJECT-TYPE
    SYNTAX      OCTET STRING
    MAX-ACCESS  read-only
    STATUS      current
    DESCRIPTION
"
synchronization status line from file assp_sync.cfg for SSLKeyFile
 0 - synchronization not configured
 1 - out of sync - running master mode
 2 - in sync - running  mastermode
 3 - in sync - running slave mode
 4 - in sync - running master mode (wait to reach state 2)
"
    ::= {SSLKeyFile 6}

noTLSIP  OBJECT-TYPE
    SYNTAX      OCTET STRING
    MAX-ACCESS  read-write
    STATUS      current
    DESCRIPTION
"
Enter IP's that you want to exclude from starting SSL/TLS, separated by pipes (|). For example, put all IP's here, that making trouble to switch to TLS every time, what will prevent ASSP from getting mails from this hosts.
"
    REFERENCE "Exclude these IP's from TLS*"
    DEFVAL { "" }
    ::= {SSLProxyandTLSsupport 825}

syncStatnoTLSIP  OBJECT-TYPE
    SYNTAX      OCTET STRING
    MAX-ACCESS  read-only
    STATUS      current
    DESCRIPTION
"
synchronization status for noTLSIP
-1 - noTLSIP could not be synchronized
 0 - synchronization not configured
 1 - out of sync - running master mode
 2 - in sync - running  mastermode
 3 - in sync - running slave mode
 4 - in sync - running master mode (wait to reach state 2)
"
    ::= {noTLSIP 5}

syncStatStrnoTLSIP  OBJECT-TYPE
    SYNTAX      OCTET STRING
    MAX-ACCESS  read-only
    STATUS      current
    DESCRIPTION
"
synchronization status line from file assp_sync.cfg for noTLSIP
 0 - synchronization not configured
 1 - out of sync - running master mode
 2 - in sync - running  mastermode
 3 - in sync - running slave mode
 4 - in sync - running master mode (wait to reach state 2)
"
    ::= {noTLSIP 6}

sendEHLO  OBJECT-TYPE
    SYNTAX      OCTET STRING
    MAX-ACCESS  read-write
    STATUS      current
    DESCRIPTION
"
If selected, ASSP sends an EHLO even if the client has sent only a HELO. This is useful to force the usage of TLS to the server or to statisfy XCLIENT/XFORWARD helo offers, because EHLO is needed before STARTTLS or XCLIENT/XFORWARD could be used.
"
    REFERENCE "Send EHLO"
    DEFVAL { "" }
    ::= {SSLProxyandTLSsupport 826}

syncStatsendEHLO  OBJECT-TYPE
    SYNTAX      OCTET STRING
    MAX-ACCESS  read-only
    STATUS      current
    DESCRIPTION
"
synchronization status for sendEHLO
-1 - sendEHLO could not be synchronized
 0 - synchronization not configured
 1 - out of sync - running master mode
 2 - in sync - running  mastermode
 3 - in sync - running slave mode
 4 - in sync - running master mode (wait to reach state 2)
"
    ::= {sendEHLO 5}

syncStatStrsendEHLO  OBJECT-TYPE
    SYNTAX      OCTET STRING
    MAX-ACCESS  read-only
    STATUS      current
    DESCRIPTION
"
synchronization status line from file assp_sync.cfg for sendEHLO
 0 - synchronization not configured
 1 - out of sync - running master mode
 2 - in sync - running  mastermode
 3 - in sync - running slave mode
 4 - in sync - running master mode (wait to reach state 2)
"
    ::= {sendEHLO 6}

SSLRetryOnError  OBJECT-TYPE
    SYNTAX      OCTET STRING
    MAX-ACCESS  read-write
    STATUS      current
    DESCRIPTION
"
If selected, ASSP retries one time to establish a SSL connection with one second delay, if the peer was not ready after STARTTLS because of a 'SSL want a read/write first' error.
"
    REFERENCE "Retry SSL on 'SSL want a read first' error"
    DEFVAL { "" }
    ::= {SSLProxyandTLSsupport 827}

syncStatSSLRetryOnError  OBJECT-TYPE
    SYNTAX      OCTET STRING
    MAX-ACCESS  read-only
    STATUS      current
    DESCRIPTION
"
synchronization status for SSLRetryOnError
-1 - SSLRetryOnError could not be synchronized
 0 - synchronization not configured
 1 - out of sync - running master mode
 2 - in sync - running  mastermode
 3 - in sync - running slave mode
 4 - in sync - running master mode (wait to reach state 2)
"
    ::= {SSLRetryOnError 5}

syncStatStrSSLRetryOnError  OBJECT-TYPE
    SYNTAX      OCTET STRING
    MAX-ACCESS  read-only
    STATUS      current
    DESCRIPTION
"
synchronization status line from file assp_sync.cfg for SSLRetryOnError
 0 - synchronization not configured
 1 - out of sync - running master mode
 2 - in sync - running  mastermode
 3 - in sync - running slave mode
 4 - in sync - running master mode (wait to reach state 2)
"
    ::= {SSLRetryOnError 6}

SSLtimeout  OBJECT-TYPE
    SYNTAX      OCTET STRING
    MAX-ACCESS  read-write
    STATUS      current
    DESCRIPTION
"
SSL/TLS negotiation will timeout after this many seconds. default is : 5 seconds.
"
    REFERENCE "SSL Timeout (0-999)"
    DEFVAL { "5" }
    ::= {SSLProxyandTLSsupport 828}

syncStatSSLtimeout  OBJECT-TYPE
    SYNTAX      OCTET STRING
    MAX-ACCESS  read-only
    STATUS      current
    DESCRIPTION
"
synchronization status for SSLtimeout
-1 - SSLtimeout could not be synchronized
 0 - synchronization not configured
 1 - out of sync - running master mode
 2 - in sync - running  mastermode
 3 - in sync - running slave mode
 4 - in sync - running master mode (wait to reach state 2)
"
    ::= {SSLtimeout 5}

syncStatStrSSLtimeout  OBJECT-TYPE
    SYNTAX      OCTET STRING
    MAX-ACCESS  read-only
    STATUS      current
    DESCRIPTION
"
synchronization status line from file assp_sync.cfg for SSLtimeout
 0 - synchronization not configured
 1 - out of sync - running master mode
 2 - in sync - running  mastermode
 3 - in sync - running slave mode
 4 - in sync - running master mode (wait to reach state 2)
"
    ::= {SSLtimeout 6}

SSLDEBUG  OBJECT-TYPE
    SYNTAX      OCTET STRING
    MAX-ACCESS  read-write
    STATUS      current
    DESCRIPTION
"
Set the debug-level for SSL/TLS. Than higher the level, than more information are written to STDOUT!
"
    REFERENCE "Debug Level for SSL/TLS"
    DEFVAL { "0" }
    ::= {SSLProxyandTLSsupport 829}

syncStatSSLDEBUG  OBJECT-TYPE
    SYNTAX      OCTET STRING
    MAX-ACCESS  read-only
    STATUS      current
    DESCRIPTION
"
synchronization status for SSLDEBUG
-1 - SSLDEBUG could not be synchronized
 0 - synchronization not configured
 1 - out of sync - running master mode
 2 - in sync - running  mastermode
 3 - in sync - running slave mode
 4 - in sync - running master mode (wait to reach state 2)
"
    ::= {SSLDEBUG 5}

syncStatStrSSLDEBUG  OBJECT-TYPE
    SYNTAX      OCTET STRING
    MAX-ACCESS  read-only
    STATUS      current
    DESCRIPTION
"
synchronization status line from file assp_sync.cfg for SSLDEBUG
 0 - synchronization not configured
 1 - out of sync - running master mode
 2 - in sync - running  mastermode
 3 - in sync - running slave mode
 4 - in sync - running master mode (wait to reach state 2)
"
    ::= {SSLDEBUG 6}

ProxyConf  OBJECT-TYPE
    SYNTAX      OCTET STRING
    MAX-ACCESS  read-write
    STATUS      current
    DESCRIPTION
"
Define transparent Port Proxy here. ASSP will forward incoming packets to a specific destination.
   For example: if you want incoming connections on port 465 (SMTP-SSL) to be forwarded to your emailserver.
   Example:0.0.0.0:465=>192.168.1.25:465<=12.1.1.3,34.5.6.7,67.23.2.1|
   10.1.1.1:1477=>192.168.1.23:25<=120.5.1.3,134.5.19.7,67.123.221.11
 The syntax is: localIP:localPORT=>forwardIP:forwardPORT<=allowfromIP1,allowfromIP2,...|next Proxy configuration|....
 You have to configure the IP-address and IP-port for both - local and forward  values. AllowfromIP are comma separated values of IP-addresses from where connections are allowed. If there is no allow value defined, all connections will be allowed!
  
"
    REFERENCE "Transparent TCP Proxy Table*"
    DEFVAL { "" }
    ::= {SSLProxyandTLSsupport 830}

syncStatProxyConf  OBJECT-TYPE
    SYNTAX      OCTET STRING
    MAX-ACCESS  read-only
    STATUS      current
    DESCRIPTION
"
synchronization status for ProxyConf
-1 - ProxyConf could not be synchronized
 0 - synchronization not configured
 1 - out of sync - running master mode
 2 - in sync - running  mastermode
 3 - in sync - running slave mode
 4 - in sync - running master mode (wait to reach state 2)
"
    ::= {ProxyConf 5}

syncStatStrProxyConf  OBJECT-TYPE
    SYNTAX      OCTET STRING
    MAX-ACCESS  read-only
    STATUS      current
    DESCRIPTION
"
synchronization status line from file assp_sync.cfg for ProxyConf
 0 - synchronization not configured
 1 - out of sync - running master mode
 2 - in sync - running  mastermode
 3 - in sync - running slave mode
 4 - in sync - running master mode (wait to reach state 2)
"
    ::= {ProxyConf 6}

TLStoProxyListenPorts  OBJECT-TYPE
    SYNTAX      OCTET STRING
    MAX-ACCESS  read-write
    STATUS      current
    DESCRIPTION
"
If a STARTTLS command is received on a port that is defined here, the connection will be moved in to the transparent proxy mode every time - independant from the setting of DoTLS . This option works for listenPort , listenPort2 and relayPort . The listener definition here has to be the same like in the port definitions. Separate multiple entries by '|'.Examples: 25, 127.0.0.1:25, 127.0.0.1:25|127.0.0.2:25 
"
    REFERENCE "Force TLS to Proxy on this Ports"
    DEFVAL { "" }
    ::= {SSLProxyandTLSsupport 902}

syncStatTLStoProxyListenPorts  OBJECT-TYPE
    SYNTAX      OCTET STRING
    MAX-ACCESS  read-only
    STATUS      current
    DESCRIPTION
"
synchronization status for TLStoProxyListenPorts
-1 - TLStoProxyListenPorts could not be synchronized
 0 - synchronization not configured
 1 - out of sync - running master mode
 2 - in sync - running  mastermode
 3 - in sync - running slave mode
 4 - in sync - running master mode (wait to reach state 2)
"
    ::= {TLStoProxyListenPorts 5}

syncStatStrTLStoProxyListenPorts  OBJECT-TYPE
    SYNTAX      OCTET STRING
    MAX-ACCESS  read-only
    STATUS      current
    DESCRIPTION
"
synchronization status line from file assp_sync.cfg for TLStoProxyListenPorts
 0 - synchronization not configured
 1 - out of sync - running master mode
 2 - in sync - running  mastermode
 3 - in sync - running slave mode
 4 - in sync - running master mode (wait to reach state 2)
"
    ::= {TLStoProxyListenPorts 6}

SSLCaFile  OBJECT-TYPE
    SYNTAX      OCTET STRING
    MAX-ACCESS  read-write
    STATUS      current
    DESCRIPTION
"
Optional parameter to enable chained certificate validation at the client side. Full path to the file containing the server's SSL certificate authority. If you provide the ca-certificate or certificate-chain together with the certificate file in the SSLCertFile parameter, leave this field blank. For example : /usr/local/etc/ssl/certs/assp-ca.crt or c:/assp/certs/server-ca.crt. A general ca.crt file is already provided in 'C:/assp/certs/server-ca.crt'. The default value is empty and leave it empty as long as you don't know, how this parameter works.
"
    REFERENCE "SSL Certificate Authority File"
    DEFVAL { "" }
    ::= {SSLProxyandTLSsupport 953}

syncStatSSLCaFile  OBJECT-TYPE
    SYNTAX      OCTET STRING
    MAX-ACCESS  read-only
    STATUS      current
    DESCRIPTION
"
synchronization status for SSLCaFile
-1 - SSLCaFile could not be synchronized
 0 - synchronization not configured
 1 - out of sync - running master mode
 2 - in sync - running  mastermode
 3 - in sync - running slave mode
 4 - in sync - running master mode (wait to reach state 2)
"
    ::= {SSLCaFile 5}

syncStatStrSSLCaFile  OBJECT-TYPE
    SYNTAX      OCTET STRING
    MAX-ACCESS  read-only
    STATUS      current
    DESCRIPTION
"
synchronization status line from file assp_sync.cfg for SSLCaFile
 0 - synchronization not configured
 1 - out of sync - running master mode
 2 - in sync - running  mastermode
 3 - in sync - running slave mode
 4 - in sync - running master mode (wait to reach state 2)
"
    ::= {SSLCaFile 6}

SSLPKPassword  OBJECT-TYPE
    SYNTAX      OCTET STRING
    MAX-ACCESS  read-write
    STATUS      current
    DESCRIPTION
"
Optional parameter. If your private key ' SSLKeyFile ' is password protected, assp will need this password to decrypt the server's SSL private key file.
"
    REFERENCE "SSL Private Key Password"
    DEFVAL { "" }
    ::= {SSLProxyandTLSsupport 954}

syncStatSSLPKPassword  OBJECT-TYPE
    SYNTAX      OCTET STRING
    MAX-ACCESS  read-only
    STATUS      current
    DESCRIPTION
"
synchronization status for SSLPKPassword
-1 - SSLPKPassword could not be synchronized
 0 - synchronization not configured
 1 - out of sync - running master mode
 2 - in sync - running  mastermode
 3 - in sync - running slave mode
 4 - in sync - running master mode (wait to reach state 2)
"
    ::= {SSLPKPassword 5}

syncStatStrSSLPKPassword  OBJECT-TYPE
    SYNTAX      OCTET STRING
    MAX-ACCESS  read-only
    STATUS      current
    DESCRIPTION
"
synchronization status line from file assp_sync.cfg for SSLPKPassword
 0 - synchronization not configured
 1 - out of sync - running master mode
 2 - in sync - running  mastermode
 3 - in sync - running slave mode
 4 - in sync - running master mode (wait to reach state 2)
"
    ::= {SSLPKPassword 6}

SSLversion  OBJECT-TYPE
    SYNTAX      OCTET STRING
    MAX-ACCESS  read-write
    STATUS      current
    DESCRIPTION
"
Sets the version of the SSL protocol used to transmit data. The default is SSLv2/3,
  which auto-negotiates between SSLv2 and SSLv3. You may specify 'SSLv2', 'SSLv3', or 'TLSv1' (case-insensitive) combined with ':' and negated with '!' (example: 'SSLv2/3:!SSLv2') if you do not want this behavior.
"
    REFERENCE "SSL version used for transmission"
    DEFVAL { "SSLv2/3" }
    ::= {SSLProxyandTLSsupport 966}

syncStatSSLversion  OBJECT-TYPE
    SYNTAX      OCTET STRING
    MAX-ACCESS  read-only
    STATUS      current
    DESCRIPTION
"
synchronization status for SSLversion
-1 - SSLversion could not be synchronized
 0 - synchronization not configured
 1 - out of sync - running master mode
 2 - in sync - running  mastermode
 3 - in sync - running slave mode
 4 - in sync - running master mode (wait to reach state 2)
"
    ::= {SSLversion 5}

syncStatStrSSLversion  OBJECT-TYPE
    SYNTAX      OCTET STRING
    MAX-ACCESS  read-only
    STATUS      current
    DESCRIPTION
"
synchronization status line from file assp_sync.cfg for SSLversion
 0 - synchronization not configured
 1 - out of sync - running master mode
 2 - in sync - running  mastermode
 3 - in sync - running slave mode
 4 - in sync - running master mode (wait to reach state 2)
"
    ::= {SSLversion 6}

SSLcipherlist  OBJECT-TYPE
    SYNTAX      OCTET STRING
    MAX-ACCESS  read-write
    STATUS      current
    DESCRIPTION
"
If this option is set, the cipher list for the connection will be set to the given value, e.g. something like 'ALL:!LOW:!EXP:!ADH'. Look into the OpenSSL documentation () for more details. Setting this value causes the 'SSL_honor_cipher_order' flag to be switched on (BEAST vulnerable)
 If this option is not used (default) the openssl builtin default is used which is suitable for most cases.
"
    REFERENCE "SSL key cipher list"
    DEFVAL { "" }
    ::= {SSLProxyandTLSsupport 967}

syncStatSSLcipherlist  OBJECT-TYPE
    SYNTAX      OCTET STRING
    MAX-ACCESS  read-only
    STATUS      current
    DESCRIPTION
"
synchronization status for SSLcipherlist
-1 - SSLcipherlist could not be synchronized
 0 - synchronization not configured
 1 - out of sync - running master mode
 2 - in sync - running  mastermode
 3 - in sync - running slave mode
 4 - in sync - running master mode (wait to reach state 2)
"
    ::= {SSLcipherlist 5}

syncStatStrSSLcipherlist  OBJECT-TYPE
    SYNTAX      OCTET STRING
    MAX-ACCESS  read-only
    STATUS      current
    DESCRIPTION
"
synchronization status line from file assp_sync.cfg for SSLcipherlist
 0 - synchronization not configured
 1 - out of sync - running master mode
 2 - in sync - running  mastermode
 3 - in sync - running slave mode
 4 - in sync - running master mode (wait to reach state 2)
"
    ::= {SSLcipherlist 6}

banFailedSSLIP  OBJECT-TYPE
    SYNTAX      OCTET STRING
    MAX-ACCESS  read-write
    STATUS      current
    DESCRIPTION
"
If set (recommended is 'both'), an IP that fails to connect via SSL/TLS will be banned for 12 hour from using SSL/TLS.
  Privat IP's and IP addresses listed in 'acceptAllMail' will get one more try to correct the mistake.
  This is done per default ('both'), to prevent possible DoS attacks via SSL/TLS.
  Those IP's are stored in the SSLfailed cache. This cache is cleaned up at startup.
  disable - disables this feature, which is highly NOT recommended
  privat only - only privat IP's and IP's in acceptAllMail will be banned (they have two tries)
  public only - only public IP's will be banned
  both - privat and public IP's will be banned
  
"
    REFERENCE "Ban Failed SSL IP"
    DEFVAL { "3" }
    ::= {SSLProxyandTLSsupport 1010}

syncStatbanFailedSSLIP  OBJECT-TYPE
    SYNTAX      OCTET STRING
    MAX-ACCESS  read-only
    STATUS      current
    DESCRIPTION
"
synchronization status for banFailedSSLIP
-1 - banFailedSSLIP could not be synchronized
 0 - synchronization not configured
 1 - out of sync - running master mode
 2 - in sync - running  mastermode
 3 - in sync - running slave mode
 4 - in sync - running master mode (wait to reach state 2)
"
    ::= {banFailedSSLIP 5}

syncStatStrbanFailedSSLIP  OBJECT-TYPE
    SYNTAX      OCTET STRING
    MAX-ACCESS  read-only
    STATUS      current
    DESCRIPTION
"
synchronization status line from file assp_sync.cfg for banFailedSSLIP
 0 - synchronization not configured
 1 - out of sync - running master mode
 2 - in sync - running  mastermode
 3 - in sync - running slave mode
 4 - in sync - running master mode (wait to reach state 2)
"
    ::= {banFailedSSLIP 6}

webSSLRequireCientCert  OBJECT-TYPE
    SYNTAX      OCTET STRING
    MAX-ACCESS  read-write
    STATUS      current
    DESCRIPTION
"
If enabled and enableWebAdminSSL is set to ON, each browser session is forced to provide a valid SSL client certificate. If no certificate is provided by the client, the connection will fail! To extend the verification of the certificate, use SSLWEBCertVerifyCB . Per default are used 'SSL_VERIFY_PEER | SSL_VERIFY_FAIL_IF_NO_PEER_CERT | SSL_VERIFY_CLIENT_ONCE'
  To create a PKCS12 from the PEM formated cert- and key file you can use openssl, like : 
  openssl pkcs12 -export -clcerts -in client.pem -inkey client.key -out client.p12
  The file client.p12 could now be imported in to your browser.
  !!! Install a valid certificate in to your browser BEFORE you enable this option - otherwise the GUI will get inaccessable !!!
  NOTICE: This option will not work if you use any self signed certificate!
"
    REFERENCE "Client requires valid SSL Certificate for GUI Requests"
    DEFVAL { "" }
    ::= {SSLProxyandTLSsupport 1015}

syncStatwebSSLRequireCientCert  OBJECT-TYPE
    SYNTAX      OCTET STRING
    MAX-ACCESS  read-only
    STATUS      current
    DESCRIPTION
"
synchronization status for webSSLRequireCientCert
-1 - webSSLRequireCientCert could not be synchronized
 0 - synchronization not configured
 1 - out of sync - running master mode
 2 - in sync - running  mastermode
 3 - in sync - running slave mode
 4 - in sync - running master mode (wait to reach state 2)
"
    ::= {webSSLRequireCientCert 5}

syncStatStrwebSSLRequireCientCert  OBJECT-TYPE
    SYNTAX      OCTET STRING
    MAX-ACCESS  read-only
    STATUS      current
    DESCRIPTION
"
synchronization status line from file assp_sync.cfg for webSSLRequireCientCert
 0 - synchronization not configured
 1 - out of sync - running master mode
 2 - in sync - running  mastermode
 3 - in sync - running slave mode
 4 - in sync - running master mode (wait to reach state 2)
"
    ::= {webSSLRequireCientCert 6}

SSLWEBCertVerifyCB  OBJECT-TYPE
    SYNTAX      OCTET STRING
    MAX-ACCESS  read-write
    STATUS      current
    DESCRIPTION
"
If used, assp will call the defined subroutine as SSL->SSL_verify_callback in an eval closure submitting the original ARRAY of parameters (see the IO::Socket::SSL documentation).
  The subroutine has to return 1 on certificate verification success - otherwise 0.
  You can use/modify the module lib/CorrectASSPcfg.pm to implement your code. For example
  sub checkWebSSLCert {
  &nbsp;&nbsp;&nbsp;&nbsp;my ($OpenSSLSays,$CertStackPtr,$DN,$OpenSSLError, $Cert)=@_;
  &nbsp;&nbsp;&nbsp;&nbsp;my $subject = Net::SSLeay::X509_NAME_oneline(Net::SSLeay::X509_get_subject_name($Cert));
  &nbsp;&nbsp;&nbsp;&nbsp;my $chain = Net::SSLeay::PEM_get_string_X509($Cert);
  &nbsp;&nbsp;&nbsp;&nbsp;...any code...;
  &nbsp;&nbsp;&nbsp;&nbsp;my $success = eval{verify($Cert);};
  &nbsp;&nbsp;&nbsp;&nbsp;return $OpenSSLSays if $@;
  &nbsp;&nbsp;&nbsp;&nbsp;my $user = eval{get_owner($Cert);};
  &nbsp;&nbsp;&nbsp;&nbsp;return $OpenSSLSays if $@;
  &nbsp;&nbsp;&nbsp;&nbsp;my $pass = get_pass($user);};
  &nbsp;&nbsp;&nbsp;&nbsp;@main::ExtWebAuth = ($user,$pass)
  &nbsp;&nbsp;&nbsp;&nbsp;return $success;
  }
  Now, if you set this parameter to 'CorrectASSPcfg::checkWebSSLCert' - assp will call
  CorrectASSPcfg::checkWebSSLCert->(@_);
  The variable '@main::ExtWebAuth' could be used to authenticate the user to the GUI related to the used certificate. The username must be provided as first element of the array. The password could be provided as second element of the array - this is not recommended and it is not required! If the used certificate is valid and a known adminusername (root is provided) is stored as first element in '@main::ExtWebAuth', the user will be automaticaly logged on to the GUI.
  NOTICE: This option will not work if you use any self signed certificate!
"
    REFERENCE "CallBack to Verify Client Certificates for GUI Connections"
    DEFVAL { "" }
    ::= {SSLProxyandTLSsupport 1016}

syncStatSSLWEBCertVerifyCB  OBJECT-TYPE
    SYNTAX      OCTET STRING
    MAX-ACCESS  read-only
    STATUS      current
    DESCRIPTION
"
synchronization status for SSLWEBCertVerifyCB
-1 - SSLWEBCertVerifyCB could not be synchronized
 0 - synchronization not configured
 1 - out of sync - running master mode
 2 - in sync - running  mastermode
 3 - in sync - running slave mode
 4 - in sync - running master mode (wait to reach state 2)
"
    ::= {SSLWEBCertVerifyCB 5}

syncStatStrSSLWEBCertVerifyCB  OBJECT-TYPE
    SYNTAX      OCTET STRING
    MAX-ACCESS  read-only
    STATUS      current
    DESCRIPTION
"
synchronization status line from file assp_sync.cfg for SSLWEBCertVerifyCB
 0 - synchronization not configured
 1 - out of sync - running master mode
 2 - in sync - running  mastermode
 3 - in sync - running slave mode
 4 - in sync - running master mode (wait to reach state 2)
"
    ::= {SSLWEBCertVerifyCB 6}

SSLWEBConfigure  OBJECT-TYPE
    SYNTAX      OCTET STRING
    MAX-ACCESS  read-write
    STATUS      current
    DESCRIPTION
"
If used, assp will call the defined subroutine in an eval closure submitting a reference to the assp predefined SSL-Socket-Configuration-HASH.
  The HASH could be modified in place to your needs - please read the documentation of IO::Socket::SSL, Net::SSLeay and OpenSSL. Return values are ignored.
  You can use/modify the module lib/CorrectASSPcfg.pm to implement your code. For example
  sub configWebSSL {
  &nbsp;&nbsp;&nbsp;&nbsp;my \$parms = shift;
  &nbsp;&nbsp;&nbsp;&nbsp;$parms->{timeout} = 10;
  &nbsp;&nbsp;&nbsp;&nbsp;$parms->{'SSL_check_crl'} = 1;
  &nbsp;&nbsp;&nbsp;&nbsp;$parms->{'SSL_crl_file'} = '/assp/certs/crl/crllist.pem';
  &nbsp;&nbsp;&nbsp;&nbsp;return;
  }
  Now, if you set this parameter to 'CorrectASSPcfg::configWebSSL' - assp will call
  CorrectASSPcfg::configWebSSL->(\%sslparms);
  NOTICE: This option will not work if you use any self signed certificate!
"
    REFERENCE "Call to Configure SSL-Listener-Parameters for GUI Connections"
    DEFVAL { "" }
    ::= {SSLProxyandTLSsupport 1017}

syncStatSSLWEBConfigure  OBJECT-TYPE
    SYNTAX      OCTET STRING
    MAX-ACCESS  read-only
    STATUS      current
    DESCRIPTION
"
synchronization status for SSLWEBConfigure
-1 - SSLWEBConfigure could not be synchronized
 0 - synchronization not configured
 1 - out of sync - running master mode
 2 - in sync - running  mastermode
 3 - in sync - running slave mode
 4 - in sync - running master mode (wait to reach state 2)
"
    ::= {SSLWEBConfigure 5}

syncStatStrSSLWEBConfigure  OBJECT-TYPE
    SYNTAX      OCTET STRING
    MAX-ACCESS  read-only
    STATUS      current
    DESCRIPTION
"
synchronization status line from file assp_sync.cfg for SSLWEBConfigure
 0 - synchronization not configured
 1 - out of sync - running master mode
 2 - in sync - running  mastermode
 3 - in sync - running slave mode
 4 - in sync - running master mode (wait to reach state 2)
"
    ::= {SSLWEBConfigure 6}

statSSLRequireClientCert  OBJECT-TYPE
    SYNTAX      OCTET STRING
    MAX-ACCESS  read-write
    STATUS      current
    DESCRIPTION
"
If enabled and enableWebStatSSL is set to ON, each session is forced to provide a valid SSL client certificate. If no certificate is provided by the client, the connection will fail! To extend the verification of the certificate, use SSLSTATCertVerifyCB . Per default are used 'SSL_VERIFY_PEER | SSL_VERIFY_FAIL_IF_NO_PEER_CERT | SSL_VERIFY_CLIENT_ONCE'
  NOTICE: This option will not work if you use any self signed certificate!
"
    REFERENCE "Client requires valid SSL Certificate for STAT Requests"
    DEFVAL { "" }
    ::= {SSLProxyandTLSsupport 1018}

syncStatstatSSLRequireClientCert  OBJECT-TYPE
    SYNTAX      OCTET STRING
    MAX-ACCESS  read-only
    STATUS      current
    DESCRIPTION
"
synchronization status for statSSLRequireClientCert
-1 - statSSLRequireClientCert could not be synchronized
 0 - synchronization not configured
 1 - out of sync - running master mode
 2 - in sync - running  mastermode
 3 - in sync - running slave mode
 4 - in sync - running master mode (wait to reach state 2)
"
    ::= {statSSLRequireClientCert 5}

syncStatStrstatSSLRequireClientCert  OBJECT-TYPE
    SYNTAX      OCTET STRING
    MAX-ACCESS  read-only
    STATUS      current
    DESCRIPTION
"
synchronization status line from file assp_sync.cfg for statSSLRequireClientCert
 0 - synchronization not configured
 1 - out of sync - running master mode
 2 - in sync - running  mastermode
 3 - in sync - running slave mode
 4 - in sync - running master mode (wait to reach state 2)
"
    ::= {statSSLRequireClientCert 6}

SSLSTATCertVerifyCB  OBJECT-TYPE
    SYNTAX      OCTET STRING
    MAX-ACCESS  read-write
    STATUS      current
    DESCRIPTION
"
Please read the description of SSLWEBCertVerifyCB .
  NOTICE: This option will not work if you use any self signed certificate!
"
    REFERENCE "CallBack to Verify Client Certificates for STAT Connections"
    DEFVAL { "" }
    ::= {SSLProxyandTLSsupport 1019}

syncStatSSLSTATCertVerifyCB  OBJECT-TYPE
    SYNTAX      OCTET STRING
    MAX-ACCESS  read-only
    STATUS      current
    DESCRIPTION
"
synchronization status for SSLSTATCertVerifyCB
-1 - SSLSTATCertVerifyCB could not be synchronized
 0 - synchronization not configured
 1 - out of sync - running master mode
 2 - in sync - running  mastermode
 3 - in sync - running slave mode
 4 - in sync - running master mode (wait to reach state 2)
"
    ::= {SSLSTATCertVerifyCB 5}

syncStatStrSSLSTATCertVerifyCB  OBJECT-TYPE
    SYNTAX      OCTET STRING
    MAX-ACCESS  read-only
    STATUS      current
    DESCRIPTION
"
synchronization status line from file assp_sync.cfg for SSLSTATCertVerifyCB
 0 - synchronization not configured
 1 - out of sync - running master mode
 2 - in sync - running  mastermode
 3 - in sync - running slave mode
 4 - in sync - running master mode (wait to reach state 2)
"
    ::= {SSLSTATCertVerifyCB 6}

SSLSTATConfigure  OBJECT-TYPE
    SYNTAX      OCTET STRING
    MAX-ACCESS  read-write
    STATUS      current
    DESCRIPTION
"
If used, assp will call the defined subroutine in an eval closure submitting a reference to the assp predefined SSL-Socket-Configuration-HASH.
   Please follow the description for SSLWEBConfigure .
   NOTICE: This option will not work if you use any self signed certificate!
"
    REFERENCE "Call to Configure SSL-Listener-Parameters for STAT Connections"
    DEFVAL { "" }
    ::= {SSLProxyandTLSsupport 1020}

syncStatSSLSTATConfigure  OBJECT-TYPE
    SYNTAX      OCTET STRING
    MAX-ACCESS  read-only
    STATUS      current
    DESCRIPTION
"
synchronization status for SSLSTATConfigure
-1 - SSLSTATConfigure could not be synchronized
 0 - synchronization not configured
 1 - out of sync - running master mode
 2 - in sync - running  mastermode
 3 - in sync - running slave mode
 4 - in sync - running master mode (wait to reach state 2)
"
    ::= {SSLSTATConfigure 5}

syncStatStrSSLSTATConfigure  OBJECT-TYPE
    SYNTAX      OCTET STRING
    MAX-ACCESS  read-only
    STATUS      current
    DESCRIPTION
"
synchronization status line from file assp_sync.cfg for SSLSTATConfigure
 0 - synchronization not configured
 1 - out of sync - running master mode
 2 - in sync - running  mastermode
 3 - in sync - running slave mode
 4 - in sync - running master mode (wait to reach state 2)
"
    ::= {SSLSTATConfigure 6}

smtpSSLRequireClientCert  OBJECT-TYPE
    SYNTAX      OCTET STRING
    MAX-ACCESS  read-write
    STATUS      current
    DESCRIPTION
"
If enabled, each client or server requesting a connection at the listenPortSSL requires a valid SSL client certificate. If no certificate is provided by the client, the connection will fail! To extend the verification of the certificate, use SSLSMTPCertVerifyCB . Per default are used 'SSL_VERIFY_PEER | SSL_VERIFY_FAIL_IF_NO_PEER_CERT | SSL_VERIFY_CLIENT_ONCE'
  NOTICE: This option will not work if you use any self signed certificate!
"
    REFERENCE "Client requires valid SSL Certificate for SMTP SSL Connections"
    DEFVAL { "" }
    ::= {SSLProxyandTLSsupport 1021}

syncStatsmtpSSLRequireClientCert  OBJECT-TYPE
    SYNTAX      OCTET STRING
    MAX-ACCESS  read-only
    STATUS      current
    DESCRIPTION
"
synchronization status for smtpSSLRequireClientCert
-1 - smtpSSLRequireClientCert could not be synchronized
 0 - synchronization not configured
 1 - out of sync - running master mode
 2 - in sync - running  mastermode
 3 - in sync - running slave mode
 4 - in sync - running master mode (wait to reach state 2)
"
    ::= {smtpSSLRequireClientCert 5}

syncStatStrsmtpSSLRequireClientCert  OBJECT-TYPE
    SYNTAX      OCTET STRING
    MAX-ACCESS  read-only
    STATUS      current
    DESCRIPTION
"
synchronization status line from file assp_sync.cfg for smtpSSLRequireClientCert
 0 - synchronization not configured
 1 - out of sync - running master mode
 2 - in sync - running  mastermode
 3 - in sync - running slave mode
 4 - in sync - running master mode (wait to reach state 2)
"
    ::= {smtpSSLRequireClientCert 6}

SSLSMTPCertVerifyCB  OBJECT-TYPE
    SYNTAX      OCTET STRING
    MAX-ACCESS  read-write
    STATUS      current
    DESCRIPTION
"
Please read the description of SSLWEBCertVerifyCB .
  NOTICE: This option will not work if you use any self signed certificate!
"
    REFERENCE "CallBack to Verify Client Certificates for SMTP Connections"
    DEFVAL { "" }
    ::= {SSLProxyandTLSsupport 1022}

syncStatSSLSMTPCertVerifyCB  OBJECT-TYPE
    SYNTAX      OCTET STRING
    MAX-ACCESS  read-only
    STATUS      current
    DESCRIPTION
"
synchronization status for SSLSMTPCertVerifyCB
-1 - SSLSMTPCertVerifyCB could not be synchronized
 0 - synchronization not configured
 1 - out of sync - running master mode
 2 - in sync - running  mastermode
 3 - in sync - running slave mode
 4 - in sync - running master mode (wait to reach state 2)
"
    ::= {SSLSMTPCertVerifyCB 5}

syncStatStrSSLSMTPCertVerifyCB  OBJECT-TYPE
    SYNTAX      OCTET STRING
    MAX-ACCESS  read-only
    STATUS      current
    DESCRIPTION
"
synchronization status line from file assp_sync.cfg for SSLSMTPCertVerifyCB
 0 - synchronization not configured
 1 - out of sync - running master mode
 2 - in sync - running  mastermode
 3 - in sync - running slave mode
 4 - in sync - running master mode (wait to reach state 2)
"
    ::= {SSLSMTPCertVerifyCB 6}

SSLSMTPConfigure  OBJECT-TYPE
    SYNTAX      OCTET STRING
    MAX-ACCESS  read-write
    STATUS      current
    DESCRIPTION
"
If used, assp will call the defined subroutine in an eval closure submitting a reference to the assp predefined SSL-Socket-Configuration-HASH.
   Please follow the description for SSLWEBConfigure .
   NOTICE: This option will not work if you use any self signed certificate!
"
    REFERENCE "Call to Configure SSL-Listener-Parameters for SMTP Connections"
    DEFVAL { "" }
    ::= {SSLProxyandTLSsupport 1023}

syncStatSSLSMTPConfigure  OBJECT-TYPE
    SYNTAX      OCTET STRING
    MAX-ACCESS  read-only
    STATUS      current
    DESCRIPTION
"
synchronization status for SSLSMTPConfigure
-1 - SSLSMTPConfigure could not be synchronized
 0 - synchronization not configured
 1 - out of sync - running master mode
 2 - in sync - running  mastermode
 3 - in sync - running slave mode
 4 - in sync - running master mode (wait to reach state 2)
"
    ::= {SSLSMTPConfigure 5}

syncStatStrSSLSMTPConfigure  OBJECT-TYPE
    SYNTAX      OCTET STRING
    MAX-ACCESS  read-only
    STATUS      current
    DESCRIPTION
"
synchronization status line from file assp_sync.cfg for SSLSMTPConfigure
 0 - synchronization not configured
 1 - out of sync - running master mode
 2 - in sync - running  mastermode
 3 - in sync - running slave mode
 4 - in sync - running master mode (wait to reach state 2)
"
    ::= {SSLSMTPConfigure 6}

noBanFailedSSLIP  OBJECT-TYPE
    SYNTAX      OCTET STRING
    MAX-ACCESS  read-write
    STATUS      current
    DESCRIPTION
"
Enter IP's that you want to exclude from being added to the SSLfailed-Cache, separated by pipes (|).
"
    REFERENCE "Exclude these IP's from SSLfailed Cache*"
    DEFVAL { "" }
    ::= {SSLProxyandTLSsupport 1028}

syncStatnoBanFailedSSLIP  OBJECT-TYPE
    SYNTAX      OCTET STRING
    MAX-ACCESS  read-only
    STATUS      current
    DESCRIPTION
"
synchronization status for noBanFailedSSLIP
-1 - noBanFailedSSLIP could not be synchronized
 0 - synchronization not configured
 1 - out of sync - running master mode
 2 - in sync - running  mastermode
 3 - in sync - running slave mode
 4 - in sync - running master mode (wait to reach state 2)
"
    ::= {noBanFailedSSLIP 5}

syncStatStrnoBanFailedSSLIP  OBJECT-TYPE
    SYNTAX      OCTET STRING
    MAX-ACCESS  read-only
    STATUS      current
    DESCRIPTION
"
synchronization status line from file assp_sync.cfg for noBanFailedSSLIP
 0 - synchronization not configured
 1 - out of sync - running master mode
 2 - in sync - running  mastermode
 3 - in sync - running slave mode
 4 - in sync - running master mode (wait to reach state 2)
"
    ::= {noBanFailedSSLIP 6}

GlobalPenaltyBox  OBJECT IDENTIFIER ::= {asspConfig 36}
globalClientName  OBJECT-TYPE
    SYNTAX      OCTET STRING
    MAX-ACCESS  read-write
    STATUS      current
    DESCRIPTION
"
The Name of this global-client for registation on the global-server. This entry has to be the full qualified DNS-Name of the IP-address over which ASSP is doing HTTP-requests! If you are using a HTTP-Proxy, this should be the public IP-address of the last Proxy in chain! This DNS-Name has to be resolveable worldwide and the resolved IP-address has to match the ASSP-HTTP-connection-IP-address. It is not possible to use an IP-address in this field! Dynamic DNS-Names like 'yourdomain.dyndns.org' are supported!
 To become a member of the exclusive global-penalty-box-users, you will need a subscription and you will have to pay a yearly maintenance fee. To get registered and/or to get more information, please send an email with your personal/company details and the globalClientName to 'assp.globalpb@thockar.com'.
 The name of this client has to be known by the global server before it could be registered from here. Please wait until you've got an information, that your client name is known by the global server.
 In addition to  this requires an installed  module in PERL.
"
    REFERENCE "client registration name"
    DEFVAL { "" }
    ::= {GlobalPenaltyBox 831}

globalClientPass  OBJECT-TYPE
    SYNTAX      OCTET STRING
    MAX-ACCESS  read-write
    STATUS      current
    DESCRIPTION
"
If the global client is registered on the global-server, you will see a number of '*' in this field. This field is readonly.
"
    REFERENCE "client registration password"
    DEFVAL { "" }
    ::= {GlobalPenaltyBox 832}

globalClientLicDate  OBJECT-TYPE
    SYNTAX      OCTET STRING
    MAX-ACCESS  read-write
    STATUS      current
    DESCRIPTION
"
The date of license/subscription expiration for this global client. If this date is exceeded, no upload and download of global PB will be done! This field is readonly.
"
    REFERENCE "client subscription expiration date"
    DEFVAL { "" }
    ::= {GlobalPenaltyBox 833}

DoGlobalBlack  OBJECT-TYPE
    SYNTAX      OCTET STRING
    MAX-ACCESS  read-write
    STATUS      current
    DESCRIPTION
"
Enables the merge of the Black-Penalty-Box-Entries, if the client is registered on the global-PB-server. Upload and download of the black penalty entries are done independant from this setting as long as any of GPBDownloadLists or GPBautoLibUpdate is activated.
"
    REFERENCE "Enable the Global-Black-Penalty"
    DEFVAL { "" }
    ::= {GlobalPenaltyBox 834}

globalValencePB  OBJECT-TYPE
    SYNTAX      OCTET STRING
    MAX-ACCESS  read-write
    STATUS      current
    DESCRIPTION
"
This penalty-value will be given to downloaded Black-Penalty-Box-Entries. As long as entries have the 'GLOBALPB' state, they will never become extreme-Black. It is recommended to set this value above PenaltyLimit!
"
    REFERENCE "Value for Global-Black-PB Entries +"
    DEFVAL { "20" }
    ::= {GlobalPenaltyBox 835}

globalBlackExpiration  OBJECT-TYPE
    SYNTAX      OCTET STRING
    MAX-ACCESS  read-write
    STATUS      current
    DESCRIPTION
"
Global-Black-Penalties will expire after this number of hours.
"
    REFERENCE "Expiration for Global-PB-Black Records"
    DEFVAL { "48" }
    ::= {GlobalPenaltyBox 836}

DoGlobalWhite  OBJECT-TYPE
    SYNTAX      OCTET STRING
    MAX-ACCESS  read-write
    STATUS      current
    DESCRIPTION
"
Enables the merge of the White-Penalty-Box-Entries, if the client is registered on the global-PB-server. Upload and download of the white penalty entries are done independant from this setting as long as any of GPBDownloadLists or GPBautoLibUpdate is activated.
"
    REFERENCE "Enable the Global-White-Penalty"
    DEFVAL { "" }
    ::= {GlobalPenaltyBox 837}

globalWhiteExpiration  OBJECT-TYPE
    SYNTAX      OCTET STRING
    MAX-ACCESS  read-write
    STATUS      current
    DESCRIPTION
"
Global-White-Penalties will expire after this number of days.
"
    REFERENCE "Expiration for Global-PB-White Records(days)"
    DEFVAL { "7" }
    ::= {GlobalPenaltyBox 838}

GPBDownloadLists  OBJECT-TYPE
    SYNTAX      OCTET STRING
    MAX-ACCESS  read-write
    STATUS      current
    DESCRIPTION
"
Select, if assp should download updates for lists and regular expressions from the global penaltybox server. Downloads will be done to the 'download' folder. If install is selected, the downloaded lines will merged in to the defined files (file:...). If you want to disable a specific line in any of your files, do not delete the line, instead commed it out - putting an '#' or ';' in front of the line. If any list is not configured using the 'file:...' option, only the download will be done, even if install is selected. To disable a line that was added by the GPB-server to your file - simply commend the line out (# or ;). If you remove such a line, it could be possibly added again by the next GPB check. To change a line that was added by the GPB-server to your file - disable the line and customize a copied line to your needs.
"
    REFERENCE "Download List and Regex Updates from GPB-Server"
    DEFVAL { "2" }
    ::= {GlobalPenaltyBox 937}

GPBautoLibUpdate  OBJECT-TYPE
    SYNTAX      OCTET STRING
    MAX-ACCESS  read-write
    STATUS      current
    DESCRIPTION
"
Select, if assp should download updates for Plugins or Library-Files (../lib) from the global penaltybox server. Downloads will be done to the 'download' folder. If install is selected, the downloaded Plugins and/or modules will be installed in to there original location, if an older version of the file still exists. If an older version is not found, only the download will be done. To activate updated Plugins or modules a restart of assp is required. This feature will not force an automatic restart of assp!.

"
    REFERENCE "Download Plugin and Library Updates from GPB-Server"
    DEFVAL { "2" }
    ::= {GlobalPenaltyBox 938}

BlockReporting  OBJECT IDENTIFIER ::= {asspConfig 37}
ExtraBlockReportLog  OBJECT-TYPE
    SYNTAX      OCTET STRING
    MAX-ACCESS  read-write
    STATUS      current
    DESCRIPTION
"
Maillogs could grow to a very large size. Enable this feature to log only loglines with blocking information to an extra file. These files will be named as 'b' + logfile . Using this option will speed up Block Reporting. Before you switch on this option, you should run 'grep'[linux/MacOS] or 'find'[Windows] to create the 'b' - file from the maillogs.
 linux/MacOS - grep '\[spam found\]' *maillog.txt &gt; bmaillog.txt
 Windows - find '[spam found]' *maillog.txt &gt; bmaillog.txt
"
    REFERENCE "Enable extra Logging for BlockReports"
    DEFVAL { "1" }
    ::= {BlockReporting 839}

syncStatExtraBlockReportLog  OBJECT-TYPE
    SYNTAX      OCTET STRING
    MAX-ACCESS  read-only
    STATUS      current
    DESCRIPTION
"
synchronization status for ExtraBlockReportLog
-1 - ExtraBlockReportLog could not be synchronized
 0 - synchronization not configured
 1 - out of sync - running master mode
 2 - in sync - running  mastermode
 3 - in sync - running slave mode
 4 - in sync - running master mode (wait to reach state 2)
"
    ::= {ExtraBlockReportLog 5}

syncStatStrExtraBlockReportLog  OBJECT-TYPE
    SYNTAX      OCTET STRING
    MAX-ACCESS  read-only
    STATUS      current
    DESCRIPTION
"
synchronization status line from file assp_sync.cfg for ExtraBlockReportLog
 0 - synchronization not configured
 1 - out of sync - running master mode
 2 - in sync - running  mastermode
 3 - in sync - running slave mode
 4 - in sync - running master mode (wait to reach state 2)
"
    ::= {ExtraBlockReportLog 6}

EmailBlockReport  OBJECT-TYPE
    SYNTAX      OCTET STRING
    MAX-ACCESS  read-write
    STATUS      current
    DESCRIPTION
"
Any mail sent by local/authenticated users to this username will be interpreted as a request to get a report about blocked emails. Do not put the full address here, just the user part. For example: asspblock
 Leading digits/numbers in the mail subject will be interpreted as 'report request for the last number of days'. If the number of days is not specified in the mail subject, a default of 5 days will be used to build the report. 
 All characters behind the 'number of days' will be interpreted as a regular expression to overwrite the BlockReportFilter - leading and trailing white spaces will be ignored.
 Users defined in EmailBlockTo, EmailAdmins and EmailAdminReportsTo are 'Admins' and can request a report for multiple users. They have to use a special syntax with '=>' in the body of the report request. The syntax is: 
 QueryAddress=>ReportRecipient=>ReportDays  -  there are many possible combinations of this three parameters. For example:
 user@domain and user@domain=>user@domain - will send a report for this user to this user
 *@domain (better use) *@domain=>* - will send a report for every blocked user in this domain to this user
 user@domain=>recipient@any-domain - will send a report for user@domain to recipient@any-domain
 *@domain=>recipient@any-domain - will send a report for every blocked user in this domain to recipient@any-domain
 It is possible to define a group ( Groups ) in the first parameter like:
 [user@domain]=>recipient@any-domain
 The group name must be a lower case email address of a local domain without any wildcard. This will create a combined block report for all email addresses defined in this group - useful, if someone has multiple email addresses and want's to get a single report.
 If the group name is equal to a real existing email address of a user, and this user requests a block report using this email address (MAIL FROM:), a combined block report for the group will be generated.
 A third parameter is possible to set, which defines the number of days for which the report should be created. The default (if empty or not defined) is one day. This value is used to calculate the 'next run date'. For example:
 *@domain=>recipient@any-domain=>2 - creates a report for two days.
 *@domain=>*=>14 - creates a report for 14 days.
 user@domain=>=>3 or user@domain=>*=>3 - creates a report for three days. The second parameter is here empty or *.
 To overwrite the defined BlockReportFilter, you can define a fourth parameter, which contains the regular expression to use.
 *@domain=>*=>14=>virus|newsletter - creates a report for 14 days and skips all lines that contains the words 'virus' or 'newsletter'.
 If an admin emails a block report request and specifies a filter in the subject of the email and a fourth parameter in the body, both regular expressions will be merged in to a single regex for each line.
 If you or a user want the default BlockReportFilter to become part of the overwrite regex, the literal '$BRF' should be inluded in the regex like:
 *@domain=>*=>14=>virus|$BRF|newsletter - or even in the subject of the email
 In this case the literal '$BRF' will be replaced by the BlockReportFilter.
 Only Admins are able to request blockreports for non local email addresses. For example:
 user@non_local_domain=>recipient@any-domain=>4
 *@non_local_domain=>recipient@any-domain=>4
 This will result in an extended blockreport for the non local address(es). Replace 'non_local_domain' with the domain name you want to query for.
 It is possible to change the complete design of the BlockReports to your needs,  using a html-css file. An default css-file 'blockreport.css' is in the image folder.
 There you can also find a default icon file 'blockreporticon.gif' and a default header-image-file 'blockreport.gif' - which is the same like 'logo.gif'.  There is no need to install that fles. If assp can not find this files in its
 image folder, it will use default hardcoded css and icon. If the file 'blockreport.gif' is not found 'logo.gif' will be used.
 To change any contents, use the Blockreport::modify module in the lib folder. You'll need some Perl skills to do that.
  
  
  
"
    REFERENCE "Request Block Report"
    DEFVAL { "asspblock" }
    ::= {BlockReporting 840}

syncStatEmailBlockReport  OBJECT-TYPE
    SYNTAX      OCTET STRING
    MAX-ACCESS  read-only
    STATUS      current
    DESCRIPTION
"
synchronization status for EmailBlockReport
-1 - EmailBlockReport could not be synchronized
 0 - synchronization not configured
 1 - out of sync - running master mode
 2 - in sync - running  mastermode
 3 - in sync - running slave mode
 4 - in sync - running master mode (wait to reach state 2)
"
    ::= {EmailBlockReport 5}

syncStatStrEmailBlockReport  OBJECT-TYPE
    SYNTAX      OCTET STRING
    MAX-ACCESS  read-only
    STATUS      current
    DESCRIPTION
"
synchronization status line from file assp_sync.cfg for EmailBlockReport
 0 - synchronization not configured
 1 - out of sync - running master mode
 2 - in sync - running  mastermode
 3 - in sync - running slave mode
 4 - in sync - running master mode (wait to reach state 2)
"
    ::= {EmailBlockReport 6}

EmailBlockReportDomain  OBJECT-TYPE
    SYNTAX      OCTET STRING
    MAX-ACCESS  read-write
    STATUS      current
    DESCRIPTION
"
Set this to the domain to which the users can send a request to receive blocked messages. For example: @assp.local. Notice the leading required '@'!
"
    REFERENCE "Request Blocked Email Domain"
    DEFVAL { "@assp.local" }
    ::= {BlockReporting 841}

syncStatEmailBlockReportDomain  OBJECT-TYPE
    SYNTAX      OCTET STRING
    MAX-ACCESS  read-only
    STATUS      current
    DESCRIPTION
"
synchronization status for EmailBlockReportDomain
-1 - EmailBlockReportDomain could not be synchronized
 0 - synchronization not configured
 1 - out of sync - running master mode
 2 - in sync - running  mastermode
 3 - in sync - running slave mode
 4 - in sync - running master mode (wait to reach state 2)
"
    ::= {EmailBlockReportDomain 5}

syncStatStrEmailBlockReportDomain  OBJECT-TYPE
    SYNTAX      OCTET STRING
    MAX-ACCESS  read-only
    STATUS      current
    DESCRIPTION
"
synchronization status line from file assp_sync.cfg for EmailBlockReportDomain
 0 - synchronization not configured
 1 - out of sync - running master mode
 2 - in sync - running  mastermode
 3 - in sync - running slave mode
 4 - in sync - running master mode (wait to reach state 2)
"
    ::= {EmailBlockReportDomain 6}

EmailBlockReply  OBJECT-TYPE
    SYNTAX      OCTET STRING
    MAX-ACCESS  read-write
    STATUS      current
    DESCRIPTION
"

"
    REFERENCE "Reply to Block-Report Request"
    DEFVAL { "1" }
    ::= {BlockReporting 842}

syncStatEmailBlockReply  OBJECT-TYPE
    SYNTAX      OCTET STRING
    MAX-ACCESS  read-only
    STATUS      current
    DESCRIPTION
"
synchronization status for EmailBlockReply
-1 - EmailBlockReply could not be synchronized
 0 - synchronization not configured
 1 - out of sync - running master mode
 2 - in sync - running  mastermode
 3 - in sync - running slave mode
 4 - in sync - running master mode (wait to reach state 2)
"
    ::= {EmailBlockReply 5}

syncStatStrEmailBlockReply  OBJECT-TYPE
    SYNTAX      OCTET STRING
    MAX-ACCESS  read-only
    STATUS      current
    DESCRIPTION
"
synchronization status line from file assp_sync.cfg for EmailBlockReply
 0 - synchronization not configured
 1 - out of sync - running master mode
 2 - in sync - running  mastermode
 3 - in sync - running slave mode
 4 - in sync - running master mode (wait to reach state 2)
"
    ::= {EmailBlockReply 6}

QueueUserBlockReports  OBJECT-TYPE
    SYNTAX      OCTET STRING
    MAX-ACCESS  read-write
    STATUS      current
    DESCRIPTION
"
How to process block report requests for users ( not EmailBlockTo, EmailAdmins, EmailAdminReportsTo ).
  'run instantly' - the request will be processed instantly (not stored).
  'store and run scheduled' - (deprecated) the request will be stored/queued, runs permanently scheduled at BlockReportSchedule until it will be removed from queue - a '+' in the subject is not needed
  To add a request to queue, the user has to send an email to EmailBlockReport. Leading digits/numbers in the mail subject will be interpreted as 'report request for the last number of days'. If the number of days is not specified in the mail subject, a default of 5 days will be used to build the report.
  If 'run instantly' is selected, but a user wants to schedule a permanent request, a leading '+' before the digits in subject is required.
  To remove a request from queue the user has to send an email to EmailBlockReport with a leading '-' in the subject.
  
"
    REFERENCE "Queue User Block Report Requests"
    DEFVAL { "0" }
    ::= {BlockReporting 843}

syncStatQueueUserBlockReports  OBJECT-TYPE
    SYNTAX      OCTET STRING
    MAX-ACCESS  read-only
    STATUS      current
    DESCRIPTION
"
synchronization status for QueueUserBlockReports
-1 - QueueUserBlockReports could not be synchronized
 0 - synchronization not configured
 1 - out of sync - running master mode
 2 - in sync - running  mastermode
 3 - in sync - running slave mode
 4 - in sync - running master mode (wait to reach state 2)
"
    ::= {QueueUserBlockReports 5}

syncStatStrQueueUserBlockReports  OBJECT-TYPE
    SYNTAX      OCTET STRING
    MAX-ACCESS  read-only
    STATUS      current
    DESCRIPTION
"
synchronization status line from file assp_sync.cfg for QueueUserBlockReports
 0 - synchronization not configured
 1 - out of sync - running master mode
 2 - in sync - running  mastermode
 3 - in sync - running slave mode
 4 - in sync - running master mode (wait to reach state 2)
"
    ::= {QueueUserBlockReports 6}

QueueSchedule  OBJECT-TYPE
    SYNTAX      OCTET STRING
    MAX-ACCESS  read-write
    STATUS      current
    DESCRIPTION
"
Runtime hour for reports in QueueUserBlockReports. Set a number between 0 and 23. 0 means midnight and is default
"
    REFERENCE "Runtime for Queued Requests <sup>s</sup>"
    DEFVAL { "0" }
    ::= {BlockReporting 844}

syncStatQueueSchedule  OBJECT-TYPE
    SYNTAX      OCTET STRING
    MAX-ACCESS  read-only
    STATUS      current
    DESCRIPTION
"
synchronization status for QueueSchedule
-1 - QueueSchedule could not be synchronized
 0 - synchronization not configured
 1 - out of sync - running master mode
 2 - in sync - running  mastermode
 3 - in sync - running slave mode
 4 - in sync - running master mode (wait to reach state 2)
"
    ::= {QueueSchedule 5}

syncStatStrQueueSchedule  OBJECT-TYPE
    SYNTAX      OCTET STRING
    MAX-ACCESS  read-only
    STATUS      current
    DESCRIPTION
"
synchronization status line from file assp_sync.cfg for QueueSchedule
 0 - synchronization not configured
 1 - out of sync - running master mode
 2 - in sync - running  mastermode
 3 - in sync - running slave mode
 4 - in sync - running master mode (wait to reach state 2)
"
    ::= {QueueSchedule 6}

BlockRepForwHost  OBJECT-TYPE
    SYNTAX      OCTET STRING
    MAX-ACCESS  read-write
    STATUS      current
    DESCRIPTION
"
If you are using more than one ASSP (backup MX), define the IP-address and relayPort (x.x.x.x:ppp - for SSL use SSL:x.x.x.x:ppp) of the other ASSP here (separate multiple entries by '|'). The Blockreportrequest will be forwarded to this ASSP and the user will get a blockreport from every ASSP. The forwarded request has the same sender and recipient like the original request. So EmailBlockReport and EmailBlockReportDomain have to be configured identically on all ASSP!!!! Resend requests are automatic forwarded to the right (or next) host, if ASSP finds the hostname in the subject of the request. If you have more than two ASSP, the logical sending structure must be a star. If ASSP(A) (the sun) is in the middle and you have also ASSP(B), ASSP(C) and ASSP(D) (satelites), ASSP(A) should know C,B and D, and B,C and D should only know A.
  If a forward host is unreachable, the forward request will be queued for a maximum of 24 hours and the user will be informed sending the 'reports/blockreportforwarderror.txt' file.
  The perl module  is required to use this feature (for SSL - Net::SMTP::SSL is required).
"
    REFERENCE "Forward The Blockreportrequest to other ASSP"
    DEFVAL { "" }
    ::= {BlockReporting 845}

EmailBlockTo  OBJECT-TYPE
    SYNTAX      OCTET STRING
    MAX-ACCESS  read-write
    STATUS      current
    DESCRIPTION
"
Email sent from ASSP acknowledging your submissions will be sent to this address. For example: admin@domain.com
"
    REFERENCE "Send Copy of Block-Reports TO"
    DEFVAL { "" }
    ::= {BlockReporting 846}

syncStatEmailBlockTo  OBJECT-TYPE
    SYNTAX      OCTET STRING
    MAX-ACCESS  read-only
    STATUS      current
    DESCRIPTION
"
synchronization status for EmailBlockTo
-1 - EmailBlockTo could not be synchronized
 0 - synchronization not configured
 1 - out of sync - running master mode
 2 - in sync - running  mastermode
 3 - in sync - running slave mode
 4 - in sync - running master mode (wait to reach state 2)
"
    ::= {EmailBlockTo 5}

syncStatStrEmailBlockTo  OBJECT-TYPE
    SYNTAX      OCTET STRING
    MAX-ACCESS  read-only
    STATUS      current
    DESCRIPTION
"
synchronization status line from file assp_sync.cfg for EmailBlockTo
 0 - synchronization not configured
 1 - out of sync - running master mode
 2 - in sync - running  mastermode
 3 - in sync - running slave mode
 4 - in sync - running master mode (wait to reach state 2)
"
    ::= {EmailBlockTo 6}

BlockReportFile  OBJECT-TYPE
    SYNTAX      OCTET STRING
    MAX-ACCESS  read-write
    STATUS      current
    DESCRIPTION
"
A file with BlockReport requests. ASSP will generate a block report for every line in this file (file:files/blockreportlist.txt - file: is required if defined!) every day at midnight for the last day. The perl modules  and  are required to use this feature. A report will be only created, if there is at least one blocked email found! The syntax is: 
 QueryAddress=>ReportRecipient=>ReportDays  -  there are many possible combinations of this three parameters. For example:
 user@domain and user@domain=>user@domain - will send a report for this user to this user
 *@domain (better use) *@domain=>* - will send a report for every blocked user in this domain to this user
 *@* - creates a report for all local users in all local domains
 user@domain=>recipient@any-domain - will send a report for user@domain to recipient@any-domain
 *@domain=>recipient@any-domain - will send a report for every blocked user in this domain to recipient@any-domain
 It is possible to define a group ( Groups ) in the first parameter like:
 [user@domain]=>recipient@any-domain
 The group name must be a lower case email address of a local domain without any wildcard. This will create a combined block report for all email addresses defined in this group - useful, if someone has multiple email addresses and want's to get a single report.
 An third parameter is possible to set, which defines the number of days for which the report should be created. The default (if empty or not defined) is one day. This value is used to calculate the 'next run date'. For example:
 *@domain=>recipient@any-domain=>2 - creates a report for two days.
 *@domain=>*=>14 - creates a report for 14 days.
 user@domain=>=>3 or user@domain=>*=>3 - creates a report for three days. The second parameter is here empty or *!
 To overwrite the defined BlockReportFilter, you can define a fourth parameter, which contains the regular expression to use.
 *@domain=>*=>14=>virus|newsletter - creates a report for 14 days and skippes all lines that contains the words 'virus' or 'newsletter'.
 An fifth parameter could be used to schedule (cron) a BlockReport. If this paramter is used, the line will be ignored at BlockReportSchedule. For the syntax of the cron entry, please read RebuildSchedule . Multiple schedules in one line could be separated by pipe (|).
 *@domain=>it_dep@domain=>7=>virus|newsletter=>0 0 * * 0 - creates a report every Sunday at 00:00 for the last seven days
 *@domain=>it_dep@domain=>2=>virus|newsletter=>0 0 * * 2,4,6|0 12 * * 1 - creates a report every Tuesday,Thursday,Saturday at 00:00 and at every Monday at 12:00 for the last two days
 Only Admins are able to request blockreports for non local email addresses. For example:
 user@non_local_domain=>recipient@any-domain=>4
 *@non_local_domain=>recipient@any-domain=>4
 This will result in an extended blockreport for the non local address(es). Replace 'non_local_domain' with the domain name you want to query for.
"
    REFERENCE "File for Blockreportrequest"
    DEFVAL { "" }
    ::= {BlockReporting 847}

syncStatBlockReportFile  OBJECT-TYPE
    SYNTAX      OCTET STRING
    MAX-ACCESS  read-only
    STATUS      current
    DESCRIPTION
"
synchronization status for BlockReportFile
-1 - BlockReportFile could not be synchronized
 0 - synchronization not configured
 1 - out of sync - running master mode
 2 - in sync - running  mastermode
 3 - in sync - running slave mode
 4 - in sync - running master mode (wait to reach state 2)
"
    ::= {BlockReportFile 5}

syncStatStrBlockReportFile  OBJECT-TYPE
    SYNTAX      OCTET STRING
    MAX-ACCESS  read-only
    STATUS      current
    DESCRIPTION
"
synchronization status line from file assp_sync.cfg for BlockReportFile
 0 - synchronization not configured
 1 - out of sync - running master mode
 2 - in sync - running  mastermode
 3 - in sync - running slave mode
 4 - in sync - running master mode (wait to reach state 2)
"
    ::= {BlockReportFile 6}

BlockReportSchedule  OBJECT-TYPE
    SYNTAX      OCTET STRING
    MAX-ACCESS  read-write
    STATUS      current
    DESCRIPTION
"
Runtime hour for reports in BlockReportFile. Set a number between 0 and 23. 0 means midnight and is default.
"
    REFERENCE "Runtime BlockReportFile <sup>s</sup>"
    DEFVAL { "0" }
    ::= {BlockReporting 848}

syncStatBlockReportSchedule  OBJECT-TYPE
    SYNTAX      OCTET STRING
    MAX-ACCESS  read-only
    STATUS      current
    DESCRIPTION
"
synchronization status for BlockReportSchedule
-1 - BlockReportSchedule could not be synchronized
 0 - synchronization not configured
 1 - out of sync - running master mode
 2 - in sync - running  mastermode
 3 - in sync - running slave mode
 4 - in sync - running master mode (wait to reach state 2)
"
    ::= {BlockReportSchedule 5}

syncStatStrBlockReportSchedule  OBJECT-TYPE
    SYNTAX      OCTET STRING
    MAX-ACCESS  read-only
    STATUS      current
    DESCRIPTION
"
synchronization status line from file assp_sync.cfg for BlockReportSchedule
 0 - synchronization not configured
 1 - out of sync - running master mode
 2 - in sync - running  mastermode
 3 - in sync - running slave mode
 4 - in sync - running master mode (wait to reach state 2)
"
    ::= {BlockReportSchedule 6}

BlockReportNow  OBJECT-TYPE
    SYNTAX      OCTET STRING
    MAX-ACCESS  read-write
    STATUS      current
    DESCRIPTION
"
If selected, ASSP will generate a block report from BlockReportFile now. &nbsp;
"
    REFERENCE "Generate a BlockReport from BlockReportFile Now"
    DEFVAL { "" }
    ::= {BlockReporting 849}

BlockMaxSearchTime  OBJECT-TYPE
    SYNTAX      OCTET STRING
    MAX-ACCESS  read-write
    STATUS      current
    DESCRIPTION
"
The maximum time in seconds, the Blockreport feature spends on searching in one log file. If this value is reached, the next log file will be processed. Default is 0. A value of 0 disables this feature and all needed log files will be fully processed.
"
    REFERENCE "Max Search time per log File"
    DEFVAL { "0" }
    ::= {BlockReporting 850}

syncStatBlockMaxSearchTime  OBJECT-TYPE
    SYNTAX      OCTET STRING
    MAX-ACCESS  read-only
    STATUS      current
    DESCRIPTION
"
synchronization status for BlockMaxSearchTime
-1 - BlockMaxSearchTime could not be synchronized
 0 - synchronization not configured
 1 - out of sync - running master mode
 2 - in sync - running  mastermode
 3 - in sync - running slave mode
 4 - in sync - running master mode (wait to reach state 2)
"
    ::= {BlockMaxSearchTime 5}

syncStatStrBlockMaxSearchTime  OBJECT-TYPE
    SYNTAX      OCTET STRING
    MAX-ACCESS  read-only
    STATUS      current
    DESCRIPTION
"
synchronization status line from file assp_sync.cfg for BlockMaxSearchTime
 0 - synchronization not configured
 1 - out of sync - running master mode
 2 - in sync - running  mastermode
 3 - in sync - running slave mode
 4 - in sync - running master mode (wait to reach state 2)
"
    ::= {BlockMaxSearchTime 6}

BlockReportFormat  OBJECT-TYPE
    SYNTAX      OCTET STRING
    MAX-ACCESS  read-write
    STATUS      current
    DESCRIPTION
"
Block reports will be sent as multipart/alternative MIME messages. They normally contains two parts, a plain text part and a html part. Select 'text only' or 'html only' if you want to skip any of this parts.
  To make it possible to detect a resent email, ASSP will add a header line 'X-Assp-Resend-Blocked: myName' to each email!
"
    REFERENCE "The format of the Report Email"
    DEFVAL { "0" }
    ::= {BlockReporting 851}

syncStatBlockReportFormat  OBJECT-TYPE
    SYNTAX      OCTET STRING
    MAX-ACCESS  read-only
    STATUS      current
    DESCRIPTION
"
synchronization status for BlockReportFormat
-1 - BlockReportFormat could not be synchronized
 0 - synchronization not configured
 1 - out of sync - running master mode
 2 - in sync - running  mastermode
 3 - in sync - running slave mode
 4 - in sync - running master mode (wait to reach state 2)
"
    ::= {BlockReportFormat 5}

syncStatStrBlockReportFormat  OBJECT-TYPE
    SYNTAX      OCTET STRING
    MAX-ACCESS  read-only
    STATUS      current
    DESCRIPTION
"
synchronization status line from file assp_sync.cfg for BlockReportFormat
 0 - synchronization not configured
 1 - out of sync - running master mode
 2 - in sync - running  mastermode
 3 - in sync - running slave mode
 4 - in sync - running master mode (wait to reach state 2)
"
    ::= {BlockReportFormat 6}

BlockReportFilter  OBJECT-TYPE
    SYNTAX      OCTET STRING
    MAX-ACCESS  read-write
    STATUS      current
    DESCRIPTION
"
Put anything here to identify messages which should not be reported in any Block Report. For example:  Virus|BlackDomain.
 For individual filter settings, it is possible to overwrite this value in the BlockReportFile for every single line and in every request per email using the subject line ( read EmailBlockReport ).
"
    REFERENCE "Regular Expression to Skip Log Records*"
    DEFVAL { "Virus|BlackDomain" }
    ::= {BlockReporting 852}

syncStatBlockReportFilter  OBJECT-TYPE
    SYNTAX      OCTET STRING
    MAX-ACCESS  read-only
    STATUS      current
    DESCRIPTION
"
synchronization status for BlockReportFilter
-1 - BlockReportFilter could not be synchronized
 0 - synchronization not configured
 1 - out of sync - running master mode
 2 - in sync - running  mastermode
 3 - in sync - running slave mode
 4 - in sync - running master mode (wait to reach state 2)
"
    ::= {BlockReportFilter 5}

syncStatStrBlockReportFilter  OBJECT-TYPE
    SYNTAX      OCTET STRING
    MAX-ACCESS  read-only
    STATUS      current
    DESCRIPTION
"
synchronization status line from file assp_sync.cfg for BlockReportFilter
 0 - synchronization not configured
 1 - out of sync - running master mode
 2 - in sync - running  mastermode
 3 - in sync - running slave mode
 4 - in sync - running master mode (wait to reach state 2)
"
    ::= {BlockReportFilter 6}

inclResendLink  OBJECT-TYPE
    SYNTAX      OCTET STRING
    MAX-ACCESS  read-write
    STATUS      current
    DESCRIPTION
"
Block reports will be sent as multipart/alternative MIME messages. They contains two parts, a plain text part and a html part. If a blocked email is stored in any folder, it is possible to include a link for each email in to the report. Define here what you want ASSP to do. Default is 'in both'. If set to not to disabled ' fileLogging ' will be automaticly set to on.
"
    REFERENCE "Include a Resend-Link for every resendable email"
    DEFVAL { "3" }
    ::= {BlockReporting 853}

syncStatinclResendLink  OBJECT-TYPE
    SYNTAX      OCTET STRING
    MAX-ACCESS  read-only
    STATUS      current
    DESCRIPTION
"
synchronization status for inclResendLink
-1 - inclResendLink could not be synchronized
 0 - synchronization not configured
 1 - out of sync - running master mode
 2 - in sync - running  mastermode
 3 - in sync - running slave mode
 4 - in sync - running master mode (wait to reach state 2)
"
    ::= {inclResendLink 5}

syncStatStrinclResendLink  OBJECT-TYPE
    SYNTAX      OCTET STRING
    MAX-ACCESS  read-only
    STATUS      current
    DESCRIPTION
"
synchronization status line from file assp_sync.cfg for inclResendLink
 0 - synchronization not configured
 1 - out of sync - running master mode
 2 - in sync - running  mastermode
 3 - in sync - running slave mode
 4 - in sync - running master mode (wait to reach state 2)
"
    ::= {inclResendLink 6}

BlockResendLink  OBJECT-TYPE
    SYNTAX      OCTET STRING
    MAX-ACCESS  read-write
    STATUS      current
    DESCRIPTION
"
If HTML is enabled in inclResendLink, two links (one on the left and one on the right site) will be included in the report email by default. Depending on the used email clients it could be possible, that one of the two links will not work for you. Try out what link is working and disable the other one, if you want.
"
    REFERENCE "Which Link Should be included"
    DEFVAL { "0" }
    ::= {BlockReporting 854}

syncStatBlockResendLink  OBJECT-TYPE
    SYNTAX      OCTET STRING
    MAX-ACCESS  read-only
    STATUS      current
    DESCRIPTION
"
synchronization status for BlockResendLink
-1 - BlockResendLink could not be synchronized
 0 - synchronization not configured
 1 - out of sync - running master mode
 2 - in sync - running  mastermode
 3 - in sync - running slave mode
 4 - in sync - running master mode (wait to reach state 2)
"
    ::= {BlockResendLink 5}

syncStatStrBlockResendLink  OBJECT-TYPE
    SYNTAX      OCTET STRING
    MAX-ACCESS  read-only
    STATUS      current
    DESCRIPTION
"
synchronization status line from file assp_sync.cfg for BlockResendLink
 0 - synchronization not configured
 1 - out of sync - running master mode
 2 - in sync - running  mastermode
 3 - in sync - running slave mode
 4 - in sync - running master mode (wait to reach state 2)
"
    ::= {BlockResendLink 6}

BlockResendLinkLeft  OBJECT-TYPE
    SYNTAX      OCTET STRING
    MAX-ACCESS  read-write
    STATUS      current
    DESCRIPTION
"
List of users and domains that will get the left link only. The setting for BlockResendLink will be ignored for this entries!
"
    REFERENCE "User which get the Left link only*"
    DEFVAL { "" }
    ::= {BlockReporting 855}

syncStatBlockResendLinkLeft  OBJECT-TYPE
    SYNTAX      OCTET STRING
    MAX-ACCESS  read-only
    STATUS      current
    DESCRIPTION
"
synchronization status for BlockResendLinkLeft
-1 - BlockResendLinkLeft could not be synchronized
 0 - synchronization not configured
 1 - out of sync - running master mode
 2 - in sync - running  mastermode
 3 - in sync - running slave mode
 4 - in sync - running master mode (wait to reach state 2)
"
    ::= {BlockResendLinkLeft 5}

syncStatStrBlockResendLinkLeft  OBJECT-TYPE
    SYNTAX      OCTET STRING
    MAX-ACCESS  read-only
    STATUS      current
    DESCRIPTION
"
synchronization status line from file assp_sync.cfg for BlockResendLinkLeft
 0 - synchronization not configured
 1 - out of sync - running master mode
 2 - in sync - running  mastermode
 3 - in sync - running slave mode
 4 - in sync - running master mode (wait to reach state 2)
"
    ::= {BlockResendLinkLeft 6}

BlockResendLinkRight  OBJECT-TYPE
    SYNTAX      OCTET STRING
    MAX-ACCESS  read-write
    STATUS      current
    DESCRIPTION
"
List of users and domains that will get the right link only. The setting for BlockResendLink will be ignored for this entries!
"
    REFERENCE "User which get the right link only* "
    DEFVAL { "" }
    ::= {BlockReporting 856}

syncStatBlockResendLinkRight  OBJECT-TYPE
    SYNTAX      OCTET STRING
    MAX-ACCESS  read-only
    STATUS      current
    DESCRIPTION
"
synchronization status for BlockResendLinkRight
-1 - BlockResendLinkRight could not be synchronized
 0 - synchronization not configured
 1 - out of sync - running master mode
 2 - in sync - running  mastermode
 3 - in sync - running slave mode
 4 - in sync - running master mode (wait to reach state 2)
"
    ::= {BlockResendLinkRight 5}

syncStatStrBlockResendLinkRight  OBJECT-TYPE
    SYNTAX      OCTET STRING
    MAX-ACCESS  read-only
    STATUS      current
    DESCRIPTION
"
synchronization status line from file assp_sync.cfg for BlockResendLinkRight
 0 - synchronization not configured
 1 - out of sync - running master mode
 2 - in sync - running  mastermode
 3 - in sync - running slave mode
 4 - in sync - running master mode (wait to reach state 2)
"
    ::= {BlockResendLinkRight 6}

DelResendSpam  OBJECT-TYPE
    SYNTAX      OCTET STRING
    MAX-ACCESS  read-write
    STATUS      current
    DESCRIPTION
"
If selected, an user request to resend a blocked email will delete the file in the spamlog folder - an admin request will move the file to the correctednotspam folder.
"
    REFERENCE "Delete Mails in Spam Folder"
    DEFVAL { "1" }
    ::= {BlockReporting 857}

syncStatDelResendSpam  OBJECT-TYPE
    SYNTAX      OCTET STRING
    MAX-ACCESS  read-only
    STATUS      current
    DESCRIPTION
"
synchronization status for DelResendSpam
-1 - DelResendSpam could not be synchronized
 0 - synchronization not configured
 1 - out of sync - running master mode
 2 - in sync - running  mastermode
 3 - in sync - running slave mode
 4 - in sync - running master mode (wait to reach state 2)
"
    ::= {DelResendSpam 5}

syncStatStrDelResendSpam  OBJECT-TYPE
    SYNTAX      OCTET STRING
    MAX-ACCESS  read-only
    STATUS      current
    DESCRIPTION
"
synchronization status line from file assp_sync.cfg for DelResendSpam
 0 - synchronization not configured
 1 - out of sync - running master mode
 2 - in sync - running  mastermode
 3 - in sync - running slave mode
 4 - in sync - running master mode (wait to reach state 2)
"
    ::= {DelResendSpam 6}

autoAddResendToWhite  OBJECT-TYPE
    SYNTAX      OCTET STRING
    MAX-ACCESS  read-write
    STATUS      current
    DESCRIPTION
"
If a BlockReport resend request is made by any of the selected users, the original sender of the resent mail will be added to whitelist, also a copy file to the resend folder will do that.
  
  
"
    REFERENCE "Automatic add Resend Senders to Whitelist"
    DEFVAL { "0" }
    ::= {BlockReporting 858}

syncStatautoAddResendToWhite  OBJECT-TYPE
    SYNTAX      OCTET STRING
    MAX-ACCESS  read-only
    STATUS      current
    DESCRIPTION
"
synchronization status for autoAddResendToWhite
-1 - autoAddResendToWhite could not be synchronized
 0 - synchronization not configured
 1 - out of sync - running master mode
 2 - in sync - running  mastermode
 3 - in sync - running slave mode
 4 - in sync - running master mode (wait to reach state 2)
"
    ::= {autoAddResendToWhite 5}

syncStatStrautoAddResendToWhite  OBJECT-TYPE
    SYNTAX      OCTET STRING
    MAX-ACCESS  read-only
    STATUS      current
    DESCRIPTION
"
synchronization status line from file assp_sync.cfg for autoAddResendToWhite
 0 - synchronization not configured
 1 - out of sync - running master mode
 2 - in sync - running  mastermode
 3 - in sync - running slave mode
 4 - in sync - running master mode (wait to reach state 2)
"
    ::= {autoAddResendToWhite 6}

BlockReportHTTPName  OBJECT-TYPE
    SYNTAX      OCTET STRING
    MAX-ACCESS  read-write
    STATUS      current
    DESCRIPTION
"
The hostname for HTTP(S) links in AdminUsers Blockreports. If not defined the local hostname will be used.
"
    REFERENCE "My HTTP Name"
    DEFVAL { "" }
    ::= {BlockReporting 876}

syncStatBlockReportHTTPName  OBJECT-TYPE
    SYNTAX      OCTET STRING
    MAX-ACCESS  read-only
    STATUS      current
    DESCRIPTION
"
synchronization status for BlockReportHTTPName
-1 - BlockReportHTTPName could not be synchronized
 0 - synchronization not configured
 1 - out of sync - running master mode
 2 - in sync - running  mastermode
 3 - in sync - running slave mode
 4 - in sync - running master mode (wait to reach state 2)
"
    ::= {BlockReportHTTPName 5}

syncStatStrBlockReportHTTPName  OBJECT-TYPE
    SYNTAX      OCTET STRING
    MAX-ACCESS  read-only
    STATUS      current
    DESCRIPTION
"
synchronization status line from file assp_sync.cfg for BlockReportHTTPName
 0 - synchronization not configured
 1 - out of sync - running master mode
 2 - in sync - running  mastermode
 3 - in sync - running slave mode
 4 - in sync - running master mode (wait to reach state 2)
"
    ::= {BlockReportHTTPName 6}

EmailAdminDomains  OBJECT-TYPE
    SYNTAX      OCTET STRING
    MAX-ACCESS  read-write
    STATUS      current
    DESCRIPTION
"
Use this parameter to restrict users registered in EmailAdmins, EmailAdminReportsTo and EmailBlockTo to a list of domains or users, for which they can request BlockReports.
  It is possible to use defined GROUPS on both sites. The file: option is required. Use the following syntax to define an entry (one per line):
  EmailAdminAddress=>*@domain1,*@domain2,user@domain3,...
  EmailAdminAddress1|EmailAdminAddress2=>*@domain1,*@domain2,user@domain3,...
  [group_of_EmailAdminAddresses]=>*@domain1,*@domain2,user@domain3,...
  [group_of_EmailAdminAddresses]=>[group_of_domains],...
  Wildcards are allowed to be used only in the domain definition - like *@*.domain.tld - separate multiple domains by comma.
  If an address of an EmailAdmin is defined multiple times, all entries are used in an 'AND' logic.
  If a BlockReport is requested for a not allowed email address, the complete BlockReport request will be ignored.
  If an EmailAdmins address is not registered in this parameter, he/she is able to request BlockReports for all domains.
"
    REFERENCE "Restrict Email Admins to Domains*"
    DEFVAL { "" }
    ::= {BlockReporting 971}

syncStatEmailAdminDomains  OBJECT-TYPE
    SYNTAX      OCTET STRING
    MAX-ACCESS  read-only
    STATUS      current
    DESCRIPTION
"
synchronization status for EmailAdminDomains
-1 - EmailAdminDomains could not be synchronized
 0 - synchronization not configured
 1 - out of sync - running master mode
 2 - in sync - running  mastermode
 3 - in sync - running slave mode
 4 - in sync - running master mode (wait to reach state 2)
"
    ::= {EmailAdminDomains 5}

syncStatStrEmailAdminDomains  OBJECT-TYPE
    SYNTAX      OCTET STRING
    MAX-ACCESS  read-only
    STATUS      current
    DESCRIPTION
"
synchronization status line from file assp_sync.cfg for EmailAdminDomains
 0 - synchronization not configured
 1 - out of sync - running master mode
 2 - in sync - running  mastermode
 3 - in sync - running slave mode
 4 - in sync - running master mode (wait to reach state 2)
"
    ::= {EmailAdminDomains 6}

DoT10Stat  OBJECT-TYPE
    SYNTAX      OCTET STRING
    MAX-ACCESS  read-write
    STATUS      current
    DESCRIPTION
"
enable the top ten statistic count (blocked IP's, blocked senders, blocked recipients) and the output in the GUI and BlockReports for admins.
"
    REFERENCE "Collect multiple TopTen Statistics"
    DEFVAL { "" }
    ::= {BlockReporting 979}

syncStatDoT10Stat  OBJECT-TYPE
    SYNTAX      OCTET STRING
    MAX-ACCESS  read-only
    STATUS      current
    DESCRIPTION
"
synchronization status for DoT10Stat
-1 - DoT10Stat could not be synchronized
 0 - synchronization not configured
 1 - out of sync - running master mode
 2 - in sync - running  mastermode
 3 - in sync - running slave mode
 4 - in sync - running master mode (wait to reach state 2)
"
    ::= {DoT10Stat 5}

syncStatStrDoT10Stat  OBJECT-TYPE
    SYNTAX      OCTET STRING
    MAX-ACCESS  read-only
    STATUS      current
    DESCRIPTION
"
synchronization status line from file assp_sync.cfg for DoT10Stat
 0 - synchronization not configured
 1 - out of sync - running master mode
 2 - in sync - running  mastermode
 3 - in sync - running slave mode
 4 - in sync - running master mode (wait to reach state 2)
"
    ::= {DoT10Stat 6}

EmailResendRequester  OBJECT-TYPE
    SYNTAX      OCTET STRING
    MAX-ACCESS  read-write
    STATUS      current
    DESCRIPTION
"
A list of local addresses, which are allowed to request a resend of blocked emails for other users, even they are not EmailAdmins . Leave this field blank (default), to disable this feature.
  This is usefull, if a user gets automatic generated BlockReports (e.g via BlockReportFile ) for a group of users and should be able to manage resends for them. Added here, the user is not allowed to request BlockReports for other users - in this case use EmailAdmins and EmailAdminDomains instead.
  The resend is done to the recipient stored in the X-Assp-Intended-For: ( requires AddIntendedForHeader ) header field and the requester, if the address was found in a TO: header field. 
  Accepts specific addresses (user@domain.com), user parts (user).  Wildcards are supported (fribo*@domain.com).
  For example: fribo*@thisdomain.com|jhanna 
"
    REFERENCE "Blocked Email Resend Requester*"
    DEFVAL { "" }
    ::= {BlockReporting 1012}

syncStatEmailResendRequester  OBJECT-TYPE
    SYNTAX      OCTET STRING
    MAX-ACCESS  read-only
    STATUS      current
    DESCRIPTION
"
synchronization status for EmailResendRequester
-1 - EmailResendRequester could not be synchronized
 0 - synchronization not configured
 1 - out of sync - running master mode
 2 - in sync - running  mastermode
 3 - in sync - running slave mode
 4 - in sync - running master mode (wait to reach state 2)
"
    ::= {EmailResendRequester 5}

syncStatStrEmailResendRequester  OBJECT-TYPE
    SYNTAX      OCTET STRING
    MAX-ACCESS  read-only
    STATUS      current
    DESCRIPTION
"
synchronization status line from file assp_sync.cfg for EmailResendRequester
 0 - synchronization not configured
 1 - out of sync - running master mode
 2 - in sync - running  mastermode
 3 - in sync - running slave mode
 4 - in sync - running master mode (wait to reach state 2)
"
    ::= {EmailResendRequester 6}

SNMPConfiguration  OBJECT IDENTIFIER ::= {asspConfig 38}
SNMP  OBJECT-TYPE
    SYNTAX      OCTET STRING
    MAX-ACCESS  read-write
    STATUS      current
    DESCRIPTION
"
This enables the AgentX registration of assp to a SNMP master-AgentX. ASSP will be registered to the master-AgentX as 'assp_myName', the possible configuration file name will be assp_myName.conf . This option requires the installed perl module . The product and needed librarys could be downloaded at .
 All configuration values are accessed using the SNMPUser account. The SNMP-permission and visibility is used from the configured user GUI-permissions.
The following OIDs (relative to the SNMPBaseOID) are available for SNMP-querys. The configuration values are changeable via snmp. The file mib/ASSP-MIB could be used in SNMP browsers to get a human readable view of the OID's (copy it to the net-snmp MIB file location - eg: [C:]/usr/share/snmp/mibs and the MIB location of your SNMP browser). Please keep in mind, that an extensive usage of SNMP querys will slow down assp.
.1   - runtime information
.1.0 - assp healty status boolean 0/1
.1.1 - assp healty status text
.1.2 - ASSP runtime status boolean 0/1 0=shutdown in progress - 1=running
.1.3 - ASSP runtime status text
.1.4 - ASSP version string
.1.5 - ASSP script name
.1.6 - Perl version string
.1.7 - Perl executable name
.1.8 - operating system name
.1.9 - hostname where ASSP is running on
.1.10 - IP-host where ASSP is running on
.1.11 - myName
.1.12 - URL to new ASSP version download
.1.13 - currently running tasks
.1.14 - current assp memory usage in MB
.1.20 - schedule information
.1.20.1 - next BerkeleyDB sync
.1.20.2 - next scheduled Config reload
.1.20.3 - next BATVTag cache cleaning
.1.20.4 - next general cache cleaning
.1.20.5 - next IP-per-Domain cache cleaning
.1.20.6 - next DelayDB cache cleaning
.1.20.7 - next Penaltybox cache cleaning
.1.20.8 - next Database Backup
.1.20.9 - next Database Connection Check
.1.20.10 - next DNS Connection Check
.1.20.11 - next hourly job runs (at)
.1.20.12 - next Database Export
.1.20.13 - next upload for Global-Black
.1.20.14 - next upload for Global-White
.1.20.15 - next Hash-File-Check (option files)
.1.20.16 - next LDAP-cross-Check
.1.20.17 - next RebuildSpamDB
.1.20.18 - next ResendMail
.1.20.19 - next ASSPFileDownload (assp.pl)
.1.20.20 - next Version File Download (version.txt)
.1.20.21 - next BackDNS File Download
.1.20.22 - next Code Change Check
.1.20.23 - next Droplist Download
.1.20.24 - next Griplist Download
.1.20.25 - next POP3Collect
.1.20.26 - next Save Stats
.1.20.27 - next TLDlist Download
.1.20.28 - next Sync Config
.1.20.29 - next Groups File Reload
.1.20.30 - next BlockReport Schedule
.1.20.31 - next File Age Schedule
.1.20.32 - next BlockReport Queue Schedule


.1.30.X - worker status (boolean) X = worker
.1.30.X.1 - worker time since last loop (text) X = worker
.1.30.X.2 - worker last action (text) X = worker

.1.31.0 - general database status (boolean) 0/1
.1.31.0.1 - general database status (text)
.1.31.X - database table status (boolean) 0/1 - X >= 1
.1.31.X.1 - database table name - X >= 1 related to .1.31.X

.2 - Configuration - X is the internal value number adapted from the language files
.2.H - heading description - H is the internal GUI heading number
.2.H.X   - config value

.3 - assp module information - X is a counter up from zero
.3.X - module name
.3.X.1 - installed module version
.3.X.2 - required module version
.3.X.3 - module installation status
.3.X.4 - download URL for the module

.4 - assp runtime status
.4.1 - current stat - X is a counted number
.4.1.X - current stat value

.4.2 - cumulative stat - X is a counted number
.4.2.X - cumulative stat value

.4.3 - current total stat - X is a counted number
.4.3.X - current total value

.4.4 - cumulative total stat - X is a counted number
.4.4.X - cumulative total stat value

.4.5 - current scoring stat - X is a counted number
.4.5.X - current scoring stat value

.4.6 - cumulative scoring stat - X is a counted number
.4.6.X - cumulative scoring stat value

.5.0 - SNMP-API : is writeable - accepts internal subroutine command/call to be executed
.5.1 - the result of the last SNMP-API call (success or error)
 
"
    REFERENCE "Enable the ASSP-SNMP Interface"
    DEFVAL { "0" }
    ::= {SNMPConfiguration 94}

syncStatSNMP  OBJECT-TYPE
    SYNTAX      OCTET STRING
    MAX-ACCESS  read-only
    STATUS      current
    DESCRIPTION
"
synchronization status for SNMP
-1 - SNMP could not be synchronized
 0 - synchronization not configured
 1 - out of sync - running master mode
 2 - in sync - running  mastermode
 3 - in sync - running slave mode
 4 - in sync - running master mode (wait to reach state 2)
"
    ::= {SNMP 5}

syncStatStrSNMP  OBJECT-TYPE
    SYNTAX      OCTET STRING
    MAX-ACCESS  read-only
    STATUS      current
    DESCRIPTION
"
synchronization status line from file assp_sync.cfg for SNMP
 0 - synchronization not configured
 1 - out of sync - running master mode
 2 - in sync - running  mastermode
 3 - in sync - running slave mode
 4 - in sync - running master mode (wait to reach state 2)
"
    ::= {SNMP 6}

SNMPBaseOID  OBJECT-TYPE
    SYNTAX      OCTET STRING
    MAX-ACCESS  read-write
    STATUS      current
    DESCRIPTION
"
The Base OID that should be used by assp. This OID will be registered to the master-AgentX. The master-AgentX will then redirect all requests for this OID and sub OID's to assp! The default setting  .1.3.6.1.4.1.37058.2  is needed to use the MIB file mib/ASSP-MIB in SNMP browsers.
"
    REFERENCE "SNMP Base OID"
    DEFVAL { ".1.3.6.1.4.1.37058.2" }
    ::= {SNMPConfiguration 941}

syncStatSNMPBaseOID  OBJECT-TYPE
    SYNTAX      OCTET STRING
    MAX-ACCESS  read-only
    STATUS      current
    DESCRIPTION
"
synchronization status for SNMPBaseOID
-1 - SNMPBaseOID could not be synchronized
 0 - synchronization not configured
 1 - out of sync - running master mode
 2 - in sync - running  mastermode
 3 - in sync - running slave mode
 4 - in sync - running master mode (wait to reach state 2)
"
    ::= {SNMPBaseOID 5}

syncStatStrSNMPBaseOID  OBJECT-TYPE
    SYNTAX      OCTET STRING
    MAX-ACCESS  read-only
    STATUS      current
    DESCRIPTION
"
synchronization status line from file assp_sync.cfg for SNMPBaseOID
 0 - synchronization not configured
 1 - out of sync - running master mode
 2 - in sync - running  mastermode
 3 - in sync - running slave mode
 4 - in sync - running master mode (wait to reach state 2)
"
    ::= {SNMPBaseOID 6}

SNMPreturnBOOL  OBJECT-TYPE
    SYNTAX      OCTET STRING
    MAX-ACCESS  read-write
    STATUS      current
    DESCRIPTION
"
How should assp return boolen values for status OIDs. Use another setting than the default ASN_BOOLEAN, if your SNMP application or browser does not understand it!
"
    REFERENCE "How to return Boolean Values"
    DEFVAL { "ASN_BOOLEAN" }
    ::= {SNMPConfiguration 943}

syncStatSNMPreturnBOOL  OBJECT-TYPE
    SYNTAX      OCTET STRING
    MAX-ACCESS  read-only
    STATUS      current
    DESCRIPTION
"
synchronization status for SNMPreturnBOOL
-1 - SNMPreturnBOOL could not be synchronized
 0 - synchronization not configured
 1 - out of sync - running master mode
 2 - in sync - running  mastermode
 3 - in sync - running slave mode
 4 - in sync - running master mode (wait to reach state 2)
"
    ::= {SNMPreturnBOOL 5}

syncStatStrSNMPreturnBOOL  OBJECT-TYPE
    SYNTAX      OCTET STRING
    MAX-ACCESS  read-only
    STATUS      current
    DESCRIPTION
"
synchronization status line from file assp_sync.cfg for SNMPreturnBOOL
 0 - synchronization not configured
 1 - out of sync - running master mode
 2 - in sync - running  mastermode
 3 - in sync - running slave mode
 4 - in sync - running master mode (wait to reach state 2)
"
    ::= {SNMPreturnBOOL 6}

SNMPUser  OBJECT-TYPE
    SYNTAX      OCTET STRING
    MAX-ACCESS  read-write
    STATUS      current
    DESCRIPTION
"
The Admin Users account used for SNMP requests. If the user does no longer exists, the root account will be used!
"
    REFERENCE "ASSP User Account used for SNMP Requests"
    DEFVAL { "root" }
    ::= {SNMPConfiguration 944}

syncStatSNMPUser  OBJECT-TYPE
    SYNTAX      OCTET STRING
    MAX-ACCESS  read-only
    STATUS      current
    DESCRIPTION
"
synchronization status for SNMPUser
-1 - SNMPUser could not be synchronized
 0 - synchronization not configured
 1 - out of sync - running master mode
 2 - in sync - running  mastermode
 3 - in sync - running slave mode
 4 - in sync - running master mode (wait to reach state 2)
"
    ::= {SNMPUser 5}

syncStatStrSNMPUser  OBJECT-TYPE
    SYNTAX      OCTET STRING
    MAX-ACCESS  read-only
    STATUS      current
    DESCRIPTION
"
synchronization status line from file assp_sync.cfg for SNMPUser
 0 - synchronization not configured
 1 - out of sync - running master mode
 2 - in sync - running  mastermode
 3 - in sync - running slave mode
 4 - in sync - running master mode (wait to reach state 2)
"
    ::= {SNMPUser 6}

SNMPwriteable  OBJECT-TYPE
    SYNTAX      OCTET STRING
    MAX-ACCESS  read-write
    STATUS      current
    DESCRIPTION
"
Allow configuration changes via SNMP. Do not forget to setup your SNMP configuration file to secure the access to SNMP. All configuration changes via SNMP are done using the SNMPUser account!
"
    REFERENCE "Allow Config Changes via SNMP"
    DEFVAL { "1" }
    ::= {SNMPConfiguration 945}

syncStatSNMPwriteable  OBJECT-TYPE
    SYNTAX      OCTET STRING
    MAX-ACCESS  read-only
    STATUS      current
    DESCRIPTION
"
synchronization status for SNMPwriteable
-1 - SNMPwriteable could not be synchronized
 0 - synchronization not configured
 1 - out of sync - running master mode
 2 - in sync - running  mastermode
 3 - in sync - running slave mode
 4 - in sync - running master mode (wait to reach state 2)
"
    ::= {SNMPwriteable 5}

syncStatStrSNMPwriteable  OBJECT-TYPE
    SYNTAX      OCTET STRING
    MAX-ACCESS  read-only
    STATUS      current
    DESCRIPTION
"
synchronization status line from file assp_sync.cfg for SNMPwriteable
 0 - synchronization not configured
 1 - out of sync - running master mode
 2 - in sync - running  mastermode
 3 - in sync - running slave mode
 4 - in sync - running master mode (wait to reach state 2)
"
    ::= {SNMPwriteable 6}

SNMPAgentXSocket  OBJECT-TYPE
    SYNTAX      OCTET STRING
    MAX-ACCESS  read-write
    STATUS      current
    DESCRIPTION
"
How to connect to the master-AgentX. Please read the  documentation for more details.
  
  
"
    REFERENCE "The Socket use to connect to the master-AgentX"
    DEFVAL { "tcp:localhost:705" }
    ::= {SNMPConfiguration 946}

syncStatSNMPAgentXSocket  OBJECT-TYPE
    SYNTAX      OCTET STRING
    MAX-ACCESS  read-only
    STATUS      current
    DESCRIPTION
"
synchronization status for SNMPAgentXSocket
-1 - SNMPAgentXSocket could not be synchronized
 0 - synchronization not configured
 1 - out of sync - running master mode
 2 - in sync - running  mastermode
 3 - in sync - running slave mode
 4 - in sync - running master mode (wait to reach state 2)
"
    ::= {SNMPAgentXSocket 5}

syncStatStrSNMPAgentXSocket  OBJECT-TYPE
    SYNTAX      OCTET STRING
    MAX-ACCESS  read-only
    STATUS      current
    DESCRIPTION
"
synchronization status line from file assp_sync.cfg for SNMPAgentXSocket
 0 - synchronization not configured
 1 - out of sync - running master mode
 2 - in sync - running  mastermode
 3 - in sync - running slave mode
 4 - in sync - running master mode (wait to reach state 2)
"
    ::= {SNMPAgentXSocket 6}

POP3Collecting  OBJECT IDENTIFIER ::= {asspConfig 39}
POP3ConfigFile  OBJECT-TYPE
    SYNTAX      OCTET STRING
    MAX-ACCESS  read-write
    STATUS      current
    DESCRIPTION
"
The file with a valid POP3 configuration. Only the file: option is allowed to use. 
  If the file exists and contains at least one valid POP3 configuration line and POP3Interval is configured, assp will collect the messages from the configured POP3-servers. 
  Each line in the config file contains one configuration for one user.
  All spaces will be removed from each line.
  Anything behind a # or ; is consider a comment.
  If the same POP3-user-name is used multiple times, put two angles with a unique number behind the user name. The angles and the number will be removed while processing the configuration.
  e.g: pop3user&lt;1&gt; will result in pop3user  -  or  - myName@pop3.domain&lt;12&gt; will result in myName@pop3.domain
  It is possible to define commonly used parameters in a separate line, which begins with the case sensitive POP3-username 'COMMON:=' - followed by the parameters that should be used for every configured user.
  A commonly set parameter could be overwritten in every user definition.
  Each configuration line begins with the POP3-username followed by ':=' : e.g myPOP3userName:=
  This statement has to followed by pairs of parameter names and values which are separated by commas - the pairs inside are separated by '='. 
  e.g.: POP3username&lt;num&gt;:=POP3password=pop3_pass,POP3server=mail.gmail.com,SMTPsendto=demo@demo_smtp.local,......
  The following case sensitive keywords are supported in the config file:
  POP3password=pop3_password
  POP3server=POP3-server or IP[:Port]
  SMTPsender=email_address
  SMTPsendto=email_address or &lt;TO:&gt; or &lt;TO:email_address&gt;
  SMTPserver=SMTP-server[:Port]
  SMTPHelo=myhelo
  SMTPAUTHuser=smtpuser
  SMTPAUTHpassword=smtppass
  POP3SSL=0/1
  POP3SSL, SMTPHelo, SMTPsender, SMTPAUTHuser and SMTPAUTHpassword are optional.
  If POP3SSL is set to 1 - POP3S will be done! The Perl module  is required for POP3S!
  If SMTPsender is not defined, the FROM: address from the header line will be used - if this is not found the POP3username will be used.
  If the &lt;TO:&gt; syntax is used for SMTPsendto, the mail will be sent to any recipient that is found in the 'to: cc: bcc:' header lines if it is a local one.
  If the &lt;TO:email_address&gt; syntax is used for SMTPsendto, the literals NAME and/or DOMAIN will be replaced by the name part and/or domain part of the addresses found in the 'to: cc: bcc:' header lines. This makes it possible to collect POP3 mails from a POP3 account, which holds mails for multiple recipients.
  For example: &lt;TO:NAME@mydomain.com&gt;  or  &lt;TO:NAME@subdomain.DOMAIN&gt;  or  &lt;TO:central-account@DOMAIN&gt;
  If the &lt;TO:&gt; or &lt;TO:email_address&gt; syntax is used for SMTPsendto, 'localDomains' and/or 'localAddresses_Flat' must be configured to prevent too much error for wrong recipients defined in the 'to: cc: bcc:' header lines. The POP3collector will not do any LDAP or VRFY query!
  If you want assp to detect SPAM, use the listenPort or listenPort2 as SMTP-server.
  To use this feature, you have to install the perl script 'assp_pop3.pl' in the assp- base directory.
"
    REFERENCE "POP3 Configuration File*"
    DEFVAL { "file:files/pop3cfg.txt" }
    ::= {POP3Collecting 907}

POP3Interval  OBJECT-TYPE
    SYNTAX      OCTET STRING
    MAX-ACCESS  read-write
    STATUS      current
    DESCRIPTION
"
The interval in minutes, assp should collect messages from the configured POP3-servers. A value of zero disables this feature.
"
    REFERENCE "POP3 Collecting Interval <sup>s</sup>"
    DEFVAL { "0" }
    ::= {POP3Collecting 908}

POP3debug  OBJECT-TYPE
    SYNTAX      OCTET STRING
    MAX-ACCESS  read-write
    STATUS      current
    DESCRIPTION
"
If selected, the POP3 collection will write debug output to the log file. Do not use it, unless you have problems with the POP3 collection!
  
  
"
    REFERENCE "POP3 debug"
    DEFVAL { "" }
    ::= {POP3Collecting 909}

POP3fork  OBJECT-TYPE
    SYNTAX      OCTET STRING
    MAX-ACCESS  read-write
    STATUS      current
    DESCRIPTION
"
If selected, the POP3 collection will be started in a new process (fork). This prevents the MaintThread from waiting until the POP3 collection has finished. Do not select this option, if you are testing the POP3 collection - to get all output from the collector! It is recommended to set this option after you've verified that the POP3 collector is running well.
"
    REFERENCE "POP3 Collector forks to a new Process"
    DEFVAL { "" }
    ::= {POP3Collecting 913}

POP3KeepRejected  OBJECT-TYPE
    SYNTAX      OCTET STRING
    MAX-ACCESS  read-write
    STATUS      current
    DESCRIPTION
"
If selected, any collected POP3 mail that fails to be sent via SMTP (because of being SPAM - in case rejected by the SMTP server) will be keeped on the POP3 server.
"
    REFERENCE "POP3 Keep Rejected Mails on POP3 Server"
    DEFVAL { "" }
    ::= {POP3Collecting 914}

ModuleSetup  OBJECT IDENTIFIER ::= {asspConfig 40}
useASSPFC  OBJECT-TYPE
    SYNTAX      OCTET STRING
    MAX-ACCESS  read-write
    STATUS      current
    DESCRIPTION
"
If selected, the perl module ASSP_FC will be loaded if it is installed. If not selected, ASSP will not load the perl module ASSP_FC even it is installed and several features of ASSP will not be available! It is recommended to disable installed but unused modules to reduce the required memory. Requires ASSP restart!
"
    REFERENCE "Use Module ASSP_FC"
    DEFVAL { "1" }
    ::= {ModuleSetup 3001}

syncStatuseASSPFC  OBJECT-TYPE
    SYNTAX      OCTET STRING
    MAX-ACCESS  read-only
    STATUS      current
    DESCRIPTION
"
synchronization status for useASSPFC
-1 - useASSPFC could not be synchronized
 0 - synchronization not configured
 1 - out of sync - running master mode
 2 - in sync - running  mastermode
 3 - in sync - running slave mode
 4 - in sync - running master mode (wait to reach state 2)
"
    ::= {useASSPFC 5}

syncStatStruseASSPFC  OBJECT-TYPE
    SYNTAX      OCTET STRING
    MAX-ACCESS  read-only
    STATUS      current
    DESCRIPTION
"
synchronization status line from file assp_sync.cfg for useASSPFC
 0 - synchronization not configured
 1 - out of sync - running master mode
 2 - in sync - running  mastermode
 3 - in sync - running slave mode
 4 - in sync - running master mode (wait to reach state 2)
"
    ::= {useASSPFC 6}

useASSPSVG  OBJECT-TYPE
    SYNTAX      OCTET STRING
    MAX-ACCESS  read-write
    STATUS      current
    DESCRIPTION
"
If selected, the perl module ASSP_SVG will be loaded if it is installed. If not selected, ASSP will not load the perl module ASSP_SVG even it is installed and several features of ASSP will not be available! It is recommended to disable installed but unused modules to reduce the required memory. Requires ASSP restart!This module is possibly used for enableGraphStats and maybe some other features.
"
    REFERENCE "Use Module ASSP_SVG"
    DEFVAL { "1" }
    ::= {ModuleSetup 3002}

syncStatuseASSPSVG  OBJECT-TYPE
    SYNTAX      OCTET STRING
    MAX-ACCESS  read-only
    STATUS      current
    DESCRIPTION
"
synchronization status for useASSPSVG
-1 - useASSPSVG could not be synchronized
 0 - synchronization not configured
 1 - out of sync - running master mode
 2 - in sync - running  mastermode
 3 - in sync - running slave mode
 4 - in sync - running master mode (wait to reach state 2)
"
    ::= {useASSPSVG 5}

syncStatStruseASSPSVG  OBJECT-TYPE
    SYNTAX      OCTET STRING
    MAX-ACCESS  read-only
    STATUS      current
    DESCRIPTION
"
synchronization status line from file assp_sync.cfg for useASSPSVG
 0 - synchronization not configured
 1 - out of sync - running master mode
 2 - in sync - running  mastermode
 3 - in sync - running slave mode
 4 - in sync - running master mode (wait to reach state 2)
"
    ::= {useASSPSVG 6}

useASSPWordStem  OBJECT-TYPE
    SYNTAX      OCTET STRING
    MAX-ACCESS  read-write
    STATUS      current
    DESCRIPTION
"
If selected, the perl module ASSP_WordStem will be loaded if it is installed. If not selected, ASSP will not load the perl module ASSP_WordStem even it is installed and several features of ASSP will not be available! It is recommended to disable installed but unused modules to reduce the required memory. Requires ASSP restart!
"
    REFERENCE "Use Module ASSP_WordStem"
    DEFVAL { "1" }
    ::= {ModuleSetup 3003}

syncStatuseASSPWordStem  OBJECT-TYPE
    SYNTAX      OCTET STRING
    MAX-ACCESS  read-only
    STATUS      current
    DESCRIPTION
"
synchronization status for useASSPWordStem
-1 - useASSPWordStem could not be synchronized
 0 - synchronization not configured
 1 - out of sync - running master mode
 2 - in sync - running  mastermode
 3 - in sync - running slave mode
 4 - in sync - running master mode (wait to reach state 2)
"
    ::= {useASSPWordStem 5}

syncStatStruseASSPWordStem  OBJECT-TYPE
    SYNTAX      OCTET STRING
    MAX-ACCESS  read-only
    STATUS      current
    DESCRIPTION
"
synchronization status line from file assp_sync.cfg for useASSPWordStem
 0 - synchronization not configured
 1 - out of sync - running master mode
 2 - in sync - running  mastermode
 3 - in sync - running slave mode
 4 - in sync - running master mode (wait to reach state 2)
"
    ::= {useASSPWordStem 6}

useAsspSelfLoader  OBJECT-TYPE
    SYNTAX      OCTET STRING
    MAX-ACCESS  read-write
    STATUS      current
    DESCRIPTION
"
If selected, the perl module AsspSelfLoader will be loaded if it is installed. If not selected, ASSP will not load the perl module AsspSelfLoader even it is installed and several features of ASSP will not be available! It is recommended to disable installed but unused modules to reduce the required memory. Requires ASSP restart!
"
    REFERENCE "Use Module AsspSelfLoader"
    DEFVAL { "1" }
    ::= {ModuleSetup 3004}

syncStatuseAsspSelfLoader  OBJECT-TYPE
    SYNTAX      OCTET STRING
    MAX-ACCESS  read-only
    STATUS      current
    DESCRIPTION
"
synchronization status for useAsspSelfLoader
-1 - useAsspSelfLoader could not be synchronized
 0 - synchronization not configured
 1 - out of sync - running master mode
 2 - in sync - running  mastermode
 3 - in sync - running slave mode
 4 - in sync - running master mode (wait to reach state 2)
"
    ::= {useAsspSelfLoader 5}

syncStatStruseAsspSelfLoader  OBJECT-TYPE
    SYNTAX      OCTET STRING
    MAX-ACCESS  read-only
    STATUS      current
    DESCRIPTION
"
synchronization status line from file assp_sync.cfg for useAsspSelfLoader
 0 - synchronization not configured
 1 - out of sync - running master mode
 2 - in sync - running  mastermode
 3 - in sync - running slave mode
 4 - in sync - running master mode (wait to reach state 2)
"
    ::= {useAsspSelfLoader 6}

useAuthenSASL  OBJECT-TYPE
    SYNTAX      OCTET STRING
    MAX-ACCESS  read-write
    STATUS      current
    DESCRIPTION
"
If selected, the perl module Authen::SASL will be loaded if it is installed. If not selected, ASSP will not load the perl module Authen::SASL even it is installed and several features of ASSP will not be available! It is recommended to disable installed but unused modules to reduce the required memory. Requires ASSP restart!This module is possibly used for relayAuthUser and maybe some other features.
"
    REFERENCE "Use Module Authen::SASL"
    DEFVAL { "1" }
    ::= {ModuleSetup 3005}

syncStatuseAuthenSASL  OBJECT-TYPE
    SYNTAX      OCTET STRING
    MAX-ACCESS  read-only
    STATUS      current
    DESCRIPTION
"
synchronization status for useAuthenSASL
-1 - useAuthenSASL could not be synchronized
 0 - synchronization not configured
 1 - out of sync - running master mode
 2 - in sync - running  mastermode
 3 - in sync - running slave mode
 4 - in sync - running master mode (wait to reach state 2)
"
    ::= {useAuthenSASL 5}

syncStatStruseAuthenSASL  OBJECT-TYPE
    SYNTAX      OCTET STRING
    MAX-ACCESS  read-only
    STATUS      current
    DESCRIPTION
"
synchronization status line from file assp_sync.cfg for useAuthenSASL
 0 - synchronization not configured
 1 - out of sync - running master mode
 2 - in sync - running  mastermode
 3 - in sync - running slave mode
 4 - in sync - running master mode (wait to reach state 2)
"
    ::= {useAuthenSASL 6}

useBerkeleyDB  OBJECT-TYPE
    SYNTAX      OCTET STRING
    MAX-ACCESS  read-write
    STATUS      current
    DESCRIPTION
"
If selected, the perl module BerkeleyDB will be loaded if it is installed. If not selected, ASSP will not load the perl module BerkeleyDB even it is installed and several features of ASSP will not be available! It is recommended to disable installed but unused modules to reduce the required memory. Requires ASSP restart!This module is possibly used for DoHMM HMMusesBDB downloadBackDNSFile spamdb useDB4griplist DBdriver importDBDir useDB4IntCache useDB4Rebuild SNMP and maybe some other features.
"
    REFERENCE "Use Module BerkeleyDB"
    DEFVAL { "1" }
    ::= {ModuleSetup 3006}

syncStatuseBerkeleyDB  OBJECT-TYPE
    SYNTAX      OCTET STRING
    MAX-ACCESS  read-only
    STATUS      current
    DESCRIPTION
"
synchronization status for useBerkeleyDB
-1 - useBerkeleyDB could not be synchronized
 0 - synchronization not configured
 1 - out of sync - running master mode
 2 - in sync - running  mastermode
 3 - in sync - running slave mode
 4 - in sync - running master mode (wait to reach state 2)
"
    ::= {useBerkeleyDB 5}

syncStatStruseBerkeleyDB  OBJECT-TYPE
    SYNTAX      OCTET STRING
    MAX-ACCESS  read-only
    STATUS      current
    DESCRIPTION
"
synchronization status line from file assp_sync.cfg for useBerkeleyDB
 0 - synchronization not configured
 1 - out of sync - running master mode
 2 - in sync - running  mastermode
 3 - in sync - running slave mode
 4 - in sync - running master mode (wait to reach state 2)
"
    ::= {useBerkeleyDB 6}

useCompressZlib  OBJECT-TYPE
    SYNTAX      OCTET STRING
    MAX-ACCESS  read-write
    STATUS      current
    DESCRIPTION
"
If selected, the perl module Compress::Zlib will be loaded if it is installed. If not selected, ASSP will not load the perl module Compress::Zlib even it is installed and several features of ASSP will not be available! It is recommended to disable installed but unused modules to reduce the required memory. Requires ASSP restart!This module is possibly used for AutoUpdateASSP EnableHTTPCompression globalClientName and maybe some other features.
"
    REFERENCE "Use Module Compress::Zlib"
    DEFVAL { "1" }
    ::= {ModuleSetup 3007}

syncStatuseCompressZlib  OBJECT-TYPE
    SYNTAX      OCTET STRING
    MAX-ACCESS  read-only
    STATUS      current
    DESCRIPTION
"
synchronization status for useCompressZlib
-1 - useCompressZlib could not be synchronized
 0 - synchronization not configured
 1 - out of sync - running master mode
 2 - in sync - running  mastermode
 3 - in sync - running slave mode
 4 - in sync - running master mode (wait to reach state 2)
"
    ::= {useCompressZlib 5}

syncStatStruseCompressZlib  OBJECT-TYPE
    SYNTAX      OCTET STRING
    MAX-ACCESS  read-only
    STATUS      current
    DESCRIPTION
"
synchronization status line from file assp_sync.cfg for useCompressZlib
 0 - synchronization not configured
 1 - out of sync - running master mode
 2 - in sync - running  mastermode
 3 - in sync - running slave mode
 4 - in sync - running master mode (wait to reach state 2)
"
    ::= {useCompressZlib 6}

useConvertTNEF  OBJECT-TYPE
    SYNTAX      OCTET STRING
    MAX-ACCESS  read-write
    STATUS      current
    DESCRIPTION
"
If selected, the perl module Convert::TNEF will be loaded if it is installed. If not selected, ASSP will not load the perl module Convert::TNEF even it is installed and several features of ASSP will not be available! It is recommended to disable installed but unused modules to reduce the required memory. Requires ASSP restart!This module is possibly used for doInFixTNEF doOutFixTNEF and maybe some other features.
"
    REFERENCE "Use Module Convert::TNEF"
    DEFVAL { "0" }
    ::= {ModuleSetup 3008}

syncStatuseConvertTNEF  OBJECT-TYPE
    SYNTAX      OCTET STRING
    MAX-ACCESS  read-only
    STATUS      current
    DESCRIPTION
"
synchronization status for useConvertTNEF
-1 - useConvertTNEF could not be synchronized
 0 - synchronization not configured
 1 - out of sync - running master mode
 2 - in sync - running  mastermode
 3 - in sync - running slave mode
 4 - in sync - running master mode (wait to reach state 2)
"
    ::= {useConvertTNEF 5}

syncStatStruseConvertTNEF  OBJECT-TYPE
    SYNTAX      OCTET STRING
    MAX-ACCESS  read-only
    STATUS      current
    DESCRIPTION
"
synchronization status line from file assp_sync.cfg for useConvertTNEF
 0 - synchronization not configured
 1 - out of sync - running master mode
 2 - in sync - running  mastermode
 3 - in sync - running slave mode
 4 - in sync - running master mode (wait to reach state 2)
"
    ::= {useConvertTNEF 6}

useDBFile  OBJECT-TYPE
    SYNTAX      OCTET STRING
    MAX-ACCESS  read-write
    STATUS      current
    DESCRIPTION
"
If selected, the perl module DB_File will be loaded if it is installed. If not selected, ASSP will not load the perl module DB_File even it is installed and several features of ASSP will not be available! It is recommended to disable installed but unused modules to reduce the required memory. Requires ASSP restart!This module is possibly used for useDB4Rebuild and maybe some other features.
"
    REFERENCE "Use Module DB_File"
    DEFVAL { "0" }
    ::= {ModuleSetup 3009}

syncStatuseDBFile  OBJECT-TYPE
    SYNTAX      OCTET STRING
    MAX-ACCESS  read-only
    STATUS      current
    DESCRIPTION
"
synchronization status for useDBFile
-1 - useDBFile could not be synchronized
 0 - synchronization not configured
 1 - out of sync - running master mode
 2 - in sync - running  mastermode
 3 - in sync - running slave mode
 4 - in sync - running master mode (wait to reach state 2)
"
    ::= {useDBFile 5}

syncStatStruseDBFile  OBJECT-TYPE
    SYNTAX      OCTET STRING
    MAX-ACCESS  read-only
    STATUS      current
    DESCRIPTION
"
synchronization status line from file assp_sync.cfg for useDBFile
 0 - synchronization not configured
 1 - out of sync - running master mode
 2 - in sync - running  mastermode
 3 - in sync - running slave mode
 4 - in sync - running master mode (wait to reach state 2)
"
    ::= {useDBFile 6}

useDigestMD5  OBJECT-TYPE
    SYNTAX      OCTET STRING
    MAX-ACCESS  read-write
    STATUS      current
    DESCRIPTION
"
If selected, the perl module Digest::MD5 will be loaded if it is installed. If not selected, ASSP will not load the perl module Digest::MD5 even it is installed and several features of ASSP will not be available! It is recommended to disable installed but unused modules to reduce the required memory. Requires ASSP restart!This module is possibly used for DelayMD5 and maybe some other features.
"
    REFERENCE "Use Module Digest::MD5"
    DEFVAL { "1" }
    ::= {ModuleSetup 3010}

syncStatuseDigestMD5  OBJECT-TYPE
    SYNTAX      OCTET STRING
    MAX-ACCESS  read-only
    STATUS      current
    DESCRIPTION
"
synchronization status for useDigestMD5
-1 - useDigestMD5 could not be synchronized
 0 - synchronization not configured
 1 - out of sync - running master mode
 2 - in sync - running  mastermode
 3 - in sync - running slave mode
 4 - in sync - running master mode (wait to reach state 2)
"
    ::= {useDigestMD5 5}

syncStatStruseDigestMD5  OBJECT-TYPE
    SYNTAX      OCTET STRING
    MAX-ACCESS  read-only
    STATUS      current
    DESCRIPTION
"
synchronization status line from file assp_sync.cfg for useDigestMD5
 0 - synchronization not configured
 1 - out of sync - running master mode
 2 - in sync - running  mastermode
 3 - in sync - running slave mode
 4 - in sync - running master mode (wait to reach state 2)
"
    ::= {useDigestMD5 6}

useDigestSHA1  OBJECT-TYPE
    SYNTAX      OCTET STRING
    MAX-ACCESS  read-write
    STATUS      current
    DESCRIPTION
"
If selected, the perl module Digest::SHA1 will be loaded if it is installed. If not selected, ASSP will not load the perl module Digest::SHA1 even it is installed and several features of ASSP will not be available! It is recommended to disable installed but unused modules to reduce the required memory. Requires ASSP restart!This module is possibly used for DoMSGIDsig DoBATV and maybe some other features.
"
    REFERENCE "Use Module Digest::SHA1"
    DEFVAL { "1" }
    ::= {ModuleSetup 3011}

syncStatuseDigestSHA1  OBJECT-TYPE
    SYNTAX      OCTET STRING
    MAX-ACCESS  read-only
    STATUS      current
    DESCRIPTION
"
synchronization status for useDigestSHA1
-1 - useDigestSHA1 could not be synchronized
 0 - synchronization not configured
 1 - out of sync - running master mode
 2 - in sync - running  mastermode
 3 - in sync - running slave mode
 4 - in sync - running master mode (wait to reach state 2)
"
    ::= {useDigestSHA1 5}

syncStatStruseDigestSHA1  OBJECT-TYPE
    SYNTAX      OCTET STRING
    MAX-ACCESS  read-only
    STATUS      current
    DESCRIPTION
"
synchronization status line from file assp_sync.cfg for useDigestSHA1
 0 - synchronization not configured
 1 - out of sync - running master mode
 2 - in sync - running  mastermode
 3 - in sync - running slave mode
 4 - in sync - running master mode (wait to reach state 2)
"
    ::= {useDigestSHA1 6}

useEmailMIME  OBJECT-TYPE
    SYNTAX      OCTET STRING
    MAX-ACCESS  read-write
    STATUS      current
    DESCRIPTION
"
If selected, the perl module Email::MIME will be loaded if it is installed. If not selected, ASSP will not load the perl module Email::MIME even it is installed and several features of ASSP will not be available! It is recommended to disable installed but unused modules to reduce the required memory. Requires ASSP restart!This module is possibly used for ValidateURIBL DoBlockExes EmailSpam EmailHam EmailAnalyze UseUnicode4MaillogNames UseUnicode4SubjectLogging inChrSetConv outChrSetConv doInFixTNEF doOutFixTNEF BlockReportFile and maybe some other features.
"
    REFERENCE "Use Module Email::MIME"
    DEFVAL { "1" }
    ::= {ModuleSetup 3012}

syncStatuseEmailMIME  OBJECT-TYPE
    SYNTAX      OCTET STRING
    MAX-ACCESS  read-only
    STATUS      current
    DESCRIPTION
"
synchronization status for useEmailMIME
-1 - useEmailMIME could not be synchronized
 0 - synchronization not configured
 1 - out of sync - running master mode
 2 - in sync - running  mastermode
 3 - in sync - running slave mode
 4 - in sync - running master mode (wait to reach state 2)
"
    ::= {useEmailMIME 5}

syncStatStruseEmailMIME  OBJECT-TYPE
    SYNTAX      OCTET STRING
    MAX-ACCESS  read-only
    STATUS      current
    DESCRIPTION
"
synchronization status line from file assp_sync.cfg for useEmailMIME
 0 - synchronization not configured
 1 - out of sync - running master mode
 2 - in sync - running  mastermode
 3 - in sync - running slave mode
 4 - in sync - running master mode (wait to reach state 2)
"
    ::= {useEmailMIME 6}

useEmailSend  OBJECT-TYPE
    SYNTAX      OCTET STRING
    MAX-ACCESS  read-write
    STATUS      current
    DESCRIPTION
"
If selected, the perl module Email::Send will be loaded if it is installed. If not selected, ASSP will not load the perl module Email::Send even it is installed and several features of ASSP will not be available! It is recommended to disable installed but unused modules to reduce the required memory. Requires ASSP restart!This module is possibly used for resendmail and maybe some other features.
"
    REFERENCE "Use Module Email::Send"
    DEFVAL { "1" }
    ::= {ModuleSetup 3013}

syncStatuseEmailSend  OBJECT-TYPE
    SYNTAX      OCTET STRING
    MAX-ACCESS  read-only
    STATUS      current
    DESCRIPTION
"
synchronization status for useEmailSend
-1 - useEmailSend could not be synchronized
 0 - synchronization not configured
 1 - out of sync - running master mode
 2 - in sync - running  mastermode
 3 - in sync - running slave mode
 4 - in sync - running master mode (wait to reach state 2)
"
    ::= {useEmailSend 5}

syncStatStruseEmailSend  OBJECT-TYPE
    SYNTAX      OCTET STRING
    MAX-ACCESS  read-only
    STATUS      current
    DESCRIPTION
"
synchronization status line from file assp_sync.cfg for useEmailSend
 0 - synchronization not configured
 1 - out of sync - running master mode
 2 - in sync - running  mastermode
 3 - in sync - running slave mode
 4 - in sync - running master mode (wait to reach state 2)
"
    ::= {useEmailSend 6}

useFileReadBackwards  OBJECT-TYPE
    SYNTAX      OCTET STRING
    MAX-ACCESS  read-write
    STATUS      current
    DESCRIPTION
"
If selected, the perl module File::ReadBackwards will be loaded if it is installed. If not selected, ASSP will not load the perl module File::ReadBackwards even it is installed and several features of ASSP will not be available! It is recommended to disable installed but unused modules to reduce the required memory. Requires ASSP restart!
"
    REFERENCE "Use Module File::ReadBackwards"
    DEFVAL { "1" }
    ::= {ModuleSetup 3014}

syncStatuseFileReadBackwards  OBJECT-TYPE
    SYNTAX      OCTET STRING
    MAX-ACCESS  read-only
    STATUS      current
    DESCRIPTION
"
synchronization status for useFileReadBackwards
-1 - useFileReadBackwards could not be synchronized
 0 - synchronization not configured
 1 - out of sync - running master mode
 2 - in sync - running  mastermode
 3 - in sync - running slave mode
 4 - in sync - running master mode (wait to reach state 2)
"
    ::= {useFileReadBackwards 5}

syncStatStruseFileReadBackwards  OBJECT-TYPE
    SYNTAX      OCTET STRING
    MAX-ACCESS  read-only
    STATUS      current
    DESCRIPTION
"
synchronization status line from file assp_sync.cfg for useFileReadBackwards
 0 - synchronization not configured
 1 - out of sync - running master mode
 2 - in sync - running  mastermode
 3 - in sync - running slave mode
 4 - in sync - running master mode (wait to reach state 2)
"
    ::= {useFileReadBackwards 6}

useFileScanClamAV  OBJECT-TYPE
    SYNTAX      OCTET STRING
    MAX-ACCESS  read-write
    STATUS      current
    DESCRIPTION
"
If selected, the perl module File::Scan::ClamAV will be loaded if it is installed. If not selected, ASSP will not load the perl module File::Scan::ClamAV even it is installed and several features of ASSP will not be available! It is recommended to disable installed but unused modules to reduce the required memory. Requires ASSP restart!This module is possibly used for UseAvClamd and maybe some other features.
"
    REFERENCE "Use Module File::Scan::ClamAV"
    DEFVAL { "1" }
    ::= {ModuleSetup 3015}

syncStatuseFileScanClamAV  OBJECT-TYPE
    SYNTAX      OCTET STRING
    MAX-ACCESS  read-only
    STATUS      current
    DESCRIPTION
"
synchronization status for useFileScanClamAV
-1 - useFileScanClamAV could not be synchronized
 0 - synchronization not configured
 1 - out of sync - running master mode
 2 - in sync - running  mastermode
 3 - in sync - running slave mode
 4 - in sync - running master mode (wait to reach state 2)
"
    ::= {useFileScanClamAV 5}

syncStatStruseFileScanClamAV  OBJECT-TYPE
    SYNTAX      OCTET STRING
    MAX-ACCESS  read-only
    STATUS      current
    DESCRIPTION
"
synchronization status line from file assp_sync.cfg for useFileScanClamAV
 0 - synchronization not configured
 1 - out of sync - running master mode
 2 - in sync - running  mastermode
 3 - in sync - running slave mode
 4 - in sync - running master mode (wait to reach state 2)
"
    ::= {useFileScanClamAV 6}

useIOSocketINET6  OBJECT-TYPE
    SYNTAX      OCTET STRING
    MAX-ACCESS  read-write
    STATUS      current
    DESCRIPTION
"
If selected, the perl module IO::Socket::INET6 will be loaded if it is installed. If not selected, ASSP will not load the perl module IO::Socket::INET6 even it is installed and several features of ASSP will not be available! It is recommended to disable installed but unused modules to reduce the required memory. Requires ASSP restart!This module is possibly used for enableINET6 and maybe some other features.
"
    REFERENCE "Use Module IO::Socket::INET6"
    DEFVAL { "1" }
    ::= {ModuleSetup 3016}

syncStatuseIOSocketINET6  OBJECT-TYPE
    SYNTAX      OCTET STRING
    MAX-ACCESS  read-only
    STATUS      current
    DESCRIPTION
"
synchronization status for useIOSocketINET6
-1 - useIOSocketINET6 could not be synchronized
 0 - synchronization not configured
 1 - out of sync - running master mode
 2 - in sync - running  mastermode
 3 - in sync - running slave mode
 4 - in sync - running master mode (wait to reach state 2)
"
    ::= {useIOSocketINET6 5}

syncStatStruseIOSocketINET6  OBJECT-TYPE
    SYNTAX      OCTET STRING
    MAX-ACCESS  read-only
    STATUS      current
    DESCRIPTION
"
synchronization status line from file assp_sync.cfg for useIOSocketINET6
 0 - synchronization not configured
 1 - out of sync - running master mode
 2 - in sync - running  mastermode
 3 - in sync - running slave mode
 4 - in sync - running master mode (wait to reach state 2)
"
    ::= {useIOSocketINET6 6}

useIOSocketSSL  OBJECT-TYPE
    SYNTAX      OCTET STRING
    MAX-ACCESS  read-write
    STATUS      current
    DESCRIPTION
"
If selected, the perl module IO::Socket::SSL will be loaded if it is installed. If not selected, ASSP will not load the perl module IO::Socket::SSL even it is installed and several features of ASSP will not be available! It is recommended to disable installed but unused modules to reduce the required memory. Requires ASSP restart!This module is possibly used for syncUsesSSL smtpDestination smtpDestinationSSL smtpAuthServer relayHost EmailReportDestination DoLDAPSSL enableWebAdminSSL enableWebStatSSL DoTLS SSLWEBCertVerifyCB SSLWEBConfigure POP3ConfigFile and maybe some other features.
"
    REFERENCE "Use Module IO::Socket::SSL"
    DEFVAL { "1" }
    ::= {ModuleSetup 3017}

syncStatuseIOSocketSSL  OBJECT-TYPE
    SYNTAX      OCTET STRING
    MAX-ACCESS  read-only
    STATUS      current
    DESCRIPTION
"
synchronization status for useIOSocketSSL
-1 - useIOSocketSSL could not be synchronized
 0 - synchronization not configured
 1 - out of sync - running master mode
 2 - in sync - running  mastermode
 3 - in sync - running slave mode
 4 - in sync - running master mode (wait to reach state 2)
"
    ::= {useIOSocketSSL 5}

syncStatStruseIOSocketSSL  OBJECT-TYPE
    SYNTAX      OCTET STRING
    MAX-ACCESS  read-only
    STATUS      current
    DESCRIPTION
"
synchronization status line from file assp_sync.cfg for useIOSocketSSL
 0 - synchronization not configured
 1 - out of sync - running master mode
 2 - in sync - running  mastermode
 3 - in sync - running slave mode
 4 - in sync - running master mode (wait to reach state 2)
"
    ::= {useIOSocketSSL 6}

useLWPSimple  OBJECT-TYPE
    SYNTAX      OCTET STRING
    MAX-ACCESS  read-write
    STATUS      current
    DESCRIPTION
"
If selected, the perl module LWP::Simple will be loaded if it is installed. If not selected, ASSP will not load the perl module LWP::Simple even it is installed and several features of ASSP will not be available! It is recommended to disable installed but unused modules to reduce the required memory. Requires ASSP restart!
"
    REFERENCE "Use Module LWP::Simple"
    DEFVAL { "1" }
    ::= {ModuleSetup 3018}

syncStatuseLWPSimple  OBJECT-TYPE
    SYNTAX      OCTET STRING
    MAX-ACCESS  read-only
    STATUS      current
    DESCRIPTION
"
synchronization status for useLWPSimple
-1 - useLWPSimple could not be synchronized
 0 - synchronization not configured
 1 - out of sync - running master mode
 2 - in sync - running  mastermode
 3 - in sync - running slave mode
 4 - in sync - running master mode (wait to reach state 2)
"
    ::= {useLWPSimple 5}

syncStatStruseLWPSimple  OBJECT-TYPE
    SYNTAX      OCTET STRING
    MAX-ACCESS  read-only
    STATUS      current
    DESCRIPTION
"
synchronization status line from file assp_sync.cfg for useLWPSimple
 0 - synchronization not configured
 1 - out of sync - running master mode
 2 - in sync - running  mastermode
 3 - in sync - running slave mode
 4 - in sync - running master mode (wait to reach state 2)
"
    ::= {useLWPSimple 6}

useMIMETypes  OBJECT-TYPE
    SYNTAX      OCTET STRING
    MAX-ACCESS  read-write
    STATUS      current
    DESCRIPTION
"
If selected, the perl module MIME::Types will be loaded if it is installed. If not selected, ASSP will not load the perl module MIME::Types even it is installed and several features of ASSP will not be available! It is recommended to disable installed but unused modules to reduce the required memory. Requires ASSP restart!This module is possibly used for doInFixTNEF doOutFixTNEF and maybe some other features.
"
    REFERENCE "Use Module MIME::Types"
    DEFVAL { "1" }
    ::= {ModuleSetup 3019}

syncStatuseMIMETypes  OBJECT-TYPE
    SYNTAX      OCTET STRING
    MAX-ACCESS  read-only
    STATUS      current
    DESCRIPTION
"
synchronization status for useMIMETypes
-1 - useMIMETypes could not be synchronized
 0 - synchronization not configured
 1 - out of sync - running master mode
 2 - in sync - running  mastermode
 3 - in sync - running slave mode
 4 - in sync - running master mode (wait to reach state 2)
"
    ::= {useMIMETypes 5}

syncStatStruseMIMETypes  OBJECT-TYPE
    SYNTAX      OCTET STRING
    MAX-ACCESS  read-only
    STATUS      current
    DESCRIPTION
"
synchronization status line from file assp_sync.cfg for useMIMETypes
 0 - synchronization not configured
 1 - out of sync - running master mode
 2 - in sync - running  mastermode
 3 - in sync - running slave mode
 4 - in sync - running master mode (wait to reach state 2)
"
    ::= {useMIMETypes 6}

useMailDKIMVerifier  OBJECT-TYPE
    SYNTAX      OCTET STRING
    MAX-ACCESS  read-write
    STATUS      current
    DESCRIPTION
"
If selected, the perl module Mail::DKIM::Verifier will be loaded if it is installed. If not selected, ASSP will not load the perl module Mail::DKIM::Verifier even it is installed and several features of ASSP will not be available! It is recommended to disable installed but unused modules to reduce the required memory. Requires ASSP restart!This module is possibly used for DoDKIM and maybe some other features.
"
    REFERENCE "Use Module Mail::DKIM::Verifier"
    DEFVAL { "1" }
    ::= {ModuleSetup 3020}

syncStatuseMailDKIMVerifier  OBJECT-TYPE
    SYNTAX      OCTET STRING
    MAX-ACCESS  read-only
    STATUS      current
    DESCRIPTION
"
synchronization status for useMailDKIMVerifier
-1 - useMailDKIMVerifier could not be synchronized
 0 - synchronization not configured
 1 - out of sync - running master mode
 2 - in sync - running  mastermode
 3 - in sync - running slave mode
 4 - in sync - running master mode (wait to reach state 2)
"
    ::= {useMailDKIMVerifier 5}

syncStatStruseMailDKIMVerifier  OBJECT-TYPE
    SYNTAX      OCTET STRING
    MAX-ACCESS  read-only
    STATUS      current
    DESCRIPTION
"
synchronization status line from file assp_sync.cfg for useMailDKIMVerifier
 0 - synchronization not configured
 1 - out of sync - running master mode
 2 - in sync - running  mastermode
 3 - in sync - running slave mode
 4 - in sync - running master mode (wait to reach state 2)
"
    ::= {useMailDKIMVerifier 6}

useMailSPF  OBJECT-TYPE
    SYNTAX      OCTET STRING
    MAX-ACCESS  read-write
    STATUS      current
    DESCRIPTION
"
If selected, the perl module Mail::SPF will be loaded if it is installed. If not selected, ASSP will not load the perl module Mail::SPF even it is installed and several features of ASSP will not be available! It is recommended to disable installed but unused modules to reduce the required memory. Requires ASSP restart!This module is possibly used for ValidateSPF SPF2 LocalPolicySPF DebugSPF and maybe some other features.
"
    REFERENCE "Use Module Mail::SPF"
    DEFVAL { "1" }
    ::= {ModuleSetup 3021}

syncStatuseMailSPF  OBJECT-TYPE
    SYNTAX      OCTET STRING
    MAX-ACCESS  read-only
    STATUS      current
    DESCRIPTION
"
synchronization status for useMailSPF
-1 - useMailSPF could not be synchronized
 0 - synchronization not configured
 1 - out of sync - running master mode
 2 - in sync - running  mastermode
 3 - in sync - running slave mode
 4 - in sync - running master mode (wait to reach state 2)
"
    ::= {useMailSPF 5}

syncStatStruseMailSPF  OBJECT-TYPE
    SYNTAX      OCTET STRING
    MAX-ACCESS  read-only
    STATUS      current
    DESCRIPTION
"
synchronization status line from file assp_sync.cfg for useMailSPF
 0 - synchronization not configured
 1 - out of sync - running master mode
 2 - in sync - running  mastermode
 3 - in sync - running slave mode
 4 - in sync - running master mode (wait to reach state 2)
"
    ::= {useMailSPF 6}

useMailSPFQuery  OBJECT-TYPE
    SYNTAX      OCTET STRING
    MAX-ACCESS  read-write
    STATUS      current
    DESCRIPTION
"
If selected, the perl module Mail::SPF::Query will be loaded if it is installed. If not selected, ASSP will not load the perl module Mail::SPF::Query even it is installed and several features of ASSP will not be available! It is recommended to disable installed but unused modules to reduce the required memory. Requires ASSP restart!This module is possibly used for SPF2 LocalPolicySPF and maybe some other features.
"
    REFERENCE "Use Module Mail::SPF::Query"
    DEFVAL { "1" }
    ::= {ModuleSetup 3022}

syncStatuseMailSPFQuery  OBJECT-TYPE
    SYNTAX      OCTET STRING
    MAX-ACCESS  read-only
    STATUS      current
    DESCRIPTION
"
synchronization status for useMailSPFQuery
-1 - useMailSPFQuery could not be synchronized
 0 - synchronization not configured
 1 - out of sync - running master mode
 2 - in sync - running  mastermode
 3 - in sync - running slave mode
 4 - in sync - running master mode (wait to reach state 2)
"
    ::= {useMailSPFQuery 5}

syncStatStruseMailSPFQuery  OBJECT-TYPE
    SYNTAX      OCTET STRING
    MAX-ACCESS  read-only
    STATUS      current
    DESCRIPTION
"
synchronization status line from file assp_sync.cfg for useMailSPFQuery
 0 - synchronization not configured
 1 - out of sync - running master mode
 2 - in sync - running  mastermode
 3 - in sync - running slave mode
 4 - in sync - running master mode (wait to reach state 2)
"
    ::= {useMailSPFQuery 6}

useMailSRS  OBJECT-TYPE
    SYNTAX      OCTET STRING
    MAX-ACCESS  read-write
    STATUS      current
    DESCRIPTION
"
If selected, the perl module Mail::SRS will be loaded if it is installed. If not selected, ASSP will not load the perl module Mail::SRS even it is installed and several features of ASSP will not be available! It is recommended to disable installed but unused modules to reduce the required memory. Requires ASSP restart!This module is possibly used for EnableSRS and maybe some other features.
"
    REFERENCE "Use Module Mail::SRS"
    DEFVAL { "0" }
    ::= {ModuleSetup 3023}

syncStatuseMailSRS  OBJECT-TYPE
    SYNTAX      OCTET STRING
    MAX-ACCESS  read-only
    STATUS      current
    DESCRIPTION
"
synchronization status for useMailSRS
-1 - useMailSRS could not be synchronized
 0 - synchronization not configured
 1 - out of sync - running master mode
 2 - in sync - running  mastermode
 3 - in sync - running slave mode
 4 - in sync - running master mode (wait to reach state 2)
"
    ::= {useMailSRS 5}

syncStatStruseMailSRS  OBJECT-TYPE
    SYNTAX      OCTET STRING
    MAX-ACCESS  read-only
    STATUS      current
    DESCRIPTION
"
synchronization status line from file assp_sync.cfg for useMailSRS
 0 - synchronization not configured
 1 - out of sync - running master mode
 2 - in sync - running  mastermode
 3 - in sync - running slave mode
 4 - in sync - running master mode (wait to reach state 2)
"
    ::= {useMailSRS 6}

useNetCIDRLite  OBJECT-TYPE
    SYNTAX      OCTET STRING
    MAX-ACCESS  read-write
    STATUS      current
    DESCRIPTION
"
If selected, the perl module Net::CIDR::Lite will be loaded if it is installed. If not selected, ASSP will not load the perl module Net::CIDR::Lite even it is installed and several features of ASSP will not be available! It is recommended to disable installed but unused modules to reduce the required memory. Requires ASSP restart!
"
    REFERENCE "Use Module Net::CIDR::Lite"
    DEFVAL { "1" }
    ::= {ModuleSetup 3024}

syncStatuseNetCIDRLite  OBJECT-TYPE
    SYNTAX      OCTET STRING
    MAX-ACCESS  read-only
    STATUS      current
    DESCRIPTION
"
synchronization status for useNetCIDRLite
-1 - useNetCIDRLite could not be synchronized
 0 - synchronization not configured
 1 - out of sync - running master mode
 2 - in sync - running  mastermode
 3 - in sync - running slave mode
 4 - in sync - running master mode (wait to reach state 2)
"
    ::= {useNetCIDRLite 5}

syncStatStruseNetCIDRLite  OBJECT-TYPE
    SYNTAX      OCTET STRING
    MAX-ACCESS  read-only
    STATUS      current
    DESCRIPTION
"
synchronization status line from file assp_sync.cfg for useNetCIDRLite
 0 - synchronization not configured
 1 - out of sync - running master mode
 2 - in sync - running  mastermode
 3 - in sync - running slave mode
 4 - in sync - running master mode (wait to reach state 2)
"
    ::= {useNetCIDRLite 6}

useNetDNS  OBJECT-TYPE
    SYNTAX      OCTET STRING
    MAX-ACCESS  read-write
    STATUS      current
    DESCRIPTION
"
If selected, the perl module Net::DNS will be loaded if it is installed. If not selected, ASSP will not load the perl module Net::DNS even it is installed and several features of ASSP will not be available! It is recommended to disable installed but unused modules to reduce the required memory. Requires ASSP restart!This module is possibly used for ValidateRWL DoReversed DoInvalidPTR DebugSPF ValidateRBL ValidateURIBL DoBackSctr and maybe some other features.
"
    REFERENCE "Use Module Net::DNS"
    DEFVAL { "1" }
    ::= {ModuleSetup 3025}

syncStatuseNetDNS  OBJECT-TYPE
    SYNTAX      OCTET STRING
    MAX-ACCESS  read-only
    STATUS      current
    DESCRIPTION
"
synchronization status for useNetDNS
-1 - useNetDNS could not be synchronized
 0 - synchronization not configured
 1 - out of sync - running master mode
 2 - in sync - running  mastermode
 3 - in sync - running slave mode
 4 - in sync - running master mode (wait to reach state 2)
"
    ::= {useNetDNS 5}

syncStatStruseNetDNS  OBJECT-TYPE
    SYNTAX      OCTET STRING
    MAX-ACCESS  read-only
    STATUS      current
    DESCRIPTION
"
synchronization status line from file assp_sync.cfg for useNetDNS
 0 - synchronization not configured
 1 - out of sync - running master mode
 2 - in sync - running  mastermode
 3 - in sync - running slave mode
 4 - in sync - running master mode (wait to reach state 2)
"
    ::= {useNetDNS 6}

useNetIP  OBJECT-TYPE
    SYNTAX      OCTET STRING
    MAX-ACCESS  read-write
    STATUS      current
    DESCRIPTION
"
If selected, the perl module Net::IP will be loaded if it is installed. If not selected, ASSP will not load the perl module Net::IP even it is installed and several features of ASSP will not be available! It is recommended to disable installed but unused modules to reduce the required memory. Requires ASSP restart!
"
    REFERENCE "Use Module Net::IP"
    DEFVAL { "1" }
    ::= {ModuleSetup 3026}

syncStatuseNetIP  OBJECT-TYPE
    SYNTAX      OCTET STRING
    MAX-ACCESS  read-only
    STATUS      current
    DESCRIPTION
"
synchronization status for useNetIP
-1 - useNetIP could not be synchronized
 0 - synchronization not configured
 1 - out of sync - running master mode
 2 - in sync - running  mastermode
 3 - in sync - running slave mode
 4 - in sync - running master mode (wait to reach state 2)
"
    ::= {useNetIP 5}

syncStatStruseNetIP  OBJECT-TYPE
    SYNTAX      OCTET STRING
    MAX-ACCESS  read-only
    STATUS      current
    DESCRIPTION
"
synchronization status line from file assp_sync.cfg for useNetIP
 0 - synchronization not configured
 1 - out of sync - running master mode
 2 - in sync - running  mastermode
 3 - in sync - running slave mode
 4 - in sync - running master mode (wait to reach state 2)
"
    ::= {useNetIP 6}

useNetLDAP  OBJECT-TYPE
    SYNTAX      OCTET STRING
    MAX-ACCESS  read-write
    STATUS      current
    DESCRIPTION
"
If selected, the perl module Net::LDAP will be loaded if it is installed. If not selected, ASSP will not load the perl module Net::LDAP even it is installed and several features of ASSP will not be available! It is recommended to disable installed but unused modules to reduce the required memory. Requires ASSP restart!This module is possibly used for ldLDAP DoLDAP and maybe some other features.
"
    REFERENCE "Use Module Net::LDAP"
    DEFVAL { "1" }
    ::= {ModuleSetup 3027}

syncStatuseNetLDAP  OBJECT-TYPE
    SYNTAX      OCTET STRING
    MAX-ACCESS  read-only
    STATUS      current
    DESCRIPTION
"
synchronization status for useNetLDAP
-1 - useNetLDAP could not be synchronized
 0 - synchronization not configured
 1 - out of sync - running master mode
 2 - in sync - running  mastermode
 3 - in sync - running slave mode
 4 - in sync - running master mode (wait to reach state 2)
"
    ::= {useNetLDAP 5}

syncStatStruseNetLDAP  OBJECT-TYPE
    SYNTAX      OCTET STRING
    MAX-ACCESS  read-only
    STATUS      current
    DESCRIPTION
"
synchronization status line from file assp_sync.cfg for useNetLDAP
 0 - synchronization not configured
 1 - out of sync - running master mode
 2 - in sync - running  mastermode
 3 - in sync - running slave mode
 4 - in sync - running master mode (wait to reach state 2)
"
    ::= {useNetLDAP 6}

useNetSMTP  OBJECT-TYPE
    SYNTAX      OCTET STRING
    MAX-ACCESS  read-write
    STATUS      current
    DESCRIPTION
"
If selected, the perl module Net::SMTP will be loaded if it is installed. If not selected, ASSP will not load the perl module Net::SMTP even it is installed and several features of ASSP will not be available! It is recommended to disable installed but unused modules to reduce the required memory. Requires ASSP restart!This module is possibly used for enableCFGShare syncUsesSSL localDomains BlockRepForwHost BlockReportFile and maybe some other features.
"
    REFERENCE "Use Module Net::SMTP"
    DEFVAL { "1" }
    ::= {ModuleSetup 3028}

syncStatuseNetSMTP  OBJECT-TYPE
    SYNTAX      OCTET STRING
    MAX-ACCESS  read-only
    STATUS      current
    DESCRIPTION
"
synchronization status for useNetSMTP
-1 - useNetSMTP could not be synchronized
 0 - synchronization not configured
 1 - out of sync - running master mode
 2 - in sync - running  mastermode
 3 - in sync - running slave mode
 4 - in sync - running master mode (wait to reach state 2)
"
    ::= {useNetSMTP 5}

syncStatStruseNetSMTP  OBJECT-TYPE
    SYNTAX      OCTET STRING
    MAX-ACCESS  read-only
    STATUS      current
    DESCRIPTION
"
synchronization status line from file assp_sync.cfg for useNetSMTP
 0 - synchronization not configured
 1 - out of sync - running master mode
 2 - in sync - running  mastermode
 3 - in sync - running slave mode
 4 - in sync - running master mode (wait to reach state 2)
"
    ::= {useNetSMTP 6}

useNetSMTPSSL  OBJECT-TYPE
    SYNTAX      OCTET STRING
    MAX-ACCESS  read-write
    STATUS      current
    DESCRIPTION
"
If selected, the perl module Net::SMTP::SSL will be loaded if it is installed. If not selected, ASSP will not load the perl module Net::SMTP::SSL even it is installed and several features of ASSP will not be available! It is recommended to disable installed but unused modules to reduce the required memory. Requires ASSP restart!This module is possibly used for syncUsesSSL BlockRepForwHost and maybe some other features.
"
    REFERENCE "Use Module Net::SMTP::SSL"
    DEFVAL { "1" }
    ::= {ModuleSetup 3029}

syncStatuseNetSMTPSSL  OBJECT-TYPE
    SYNTAX      OCTET STRING
    MAX-ACCESS  read-only
    STATUS      current
    DESCRIPTION
"
synchronization status for useNetSMTPSSL
-1 - useNetSMTPSSL could not be synchronized
 0 - synchronization not configured
 1 - out of sync - running master mode
 2 - in sync - running  mastermode
 3 - in sync - running slave mode
 4 - in sync - running master mode (wait to reach state 2)
"
    ::= {useNetSMTPSSL 5}

syncStatStruseNetSMTPSSL  OBJECT-TYPE
    SYNTAX      OCTET STRING
    MAX-ACCESS  read-only
    STATUS      current
    DESCRIPTION
"
synchronization status line from file assp_sync.cfg for useNetSMTPSSL
 0 - synchronization not configured
 1 - out of sync - running master mode
 2 - in sync - running  mastermode
 3 - in sync - running slave mode
 4 - in sync - running master mode (wait to reach state 2)
"
    ::= {useNetSMTPSSL 6}

useNetAddrIPLite  OBJECT-TYPE
    SYNTAX      OCTET STRING
    MAX-ACCESS  read-write
    STATUS      current
    DESCRIPTION
"
If selected, the perl module NetAddr::IP::Lite will be loaded if it is installed. If not selected, ASSP will not load the perl module NetAddr::IP::Lite even it is installed and several features of ASSP will not be available! It is recommended to disable installed but unused modules to reduce the required memory. Requires ASSP restart!
"
    REFERENCE "Use Module NetAddr::IP::Lite"
    DEFVAL { "1" }
    ::= {ModuleSetup 3030}

syncStatuseNetAddrIPLite  OBJECT-TYPE
    SYNTAX      OCTET STRING
    MAX-ACCESS  read-only
    STATUS      current
    DESCRIPTION
"
synchronization status for useNetAddrIPLite
-1 - useNetAddrIPLite could not be synchronized
 0 - synchronization not configured
 1 - out of sync - running master mode
 2 - in sync - running  mastermode
 3 - in sync - running slave mode
 4 - in sync - running master mode (wait to reach state 2)
"
    ::= {useNetAddrIPLite 5}

syncStatStruseNetAddrIPLite  OBJECT-TYPE
    SYNTAX      OCTET STRING
    MAX-ACCESS  read-only
    STATUS      current
    DESCRIPTION
"
synchronization status line from file assp_sync.cfg for useNetAddrIPLite
 0 - synchronization not configured
 1 - out of sync - running master mode
 2 - in sync - running  mastermode
 3 - in sync - running slave mode
 4 - in sync - running master mode (wait to reach state 2)
"
    ::= {useNetAddrIPLite 6}

useNetSNMPagent  OBJECT-TYPE
    SYNTAX      OCTET STRING
    MAX-ACCESS  read-write
    STATUS      current
    DESCRIPTION
"
If selected, the perl module NetSNMP::agent will be loaded if it is installed. If not selected, ASSP will not load the perl module NetSNMP::agent even it is installed and several features of ASSP will not be available! It is recommended to disable installed but unused modules to reduce the required memory. Requires ASSP restart!This module is possibly used for SNMP and maybe some other features.
"
    REFERENCE "Use Module NetSNMP::agent"
    DEFVAL { "0" }
    ::= {ModuleSetup 3031}

syncStatuseNetSNMPagent  OBJECT-TYPE
    SYNTAX      OCTET STRING
    MAX-ACCESS  read-only
    STATUS      current
    DESCRIPTION
"
synchronization status for useNetSNMPagent
-1 - useNetSNMPagent could not be synchronized
 0 - synchronization not configured
 1 - out of sync - running master mode
 2 - in sync - running  mastermode
 3 - in sync - running slave mode
 4 - in sync - running master mode (wait to reach state 2)
"
    ::= {useNetSNMPagent 5}

syncStatStruseNetSNMPagent  OBJECT-TYPE
    SYNTAX      OCTET STRING
    MAX-ACCESS  read-only
    STATUS      current
    DESCRIPTION
"
synchronization status line from file assp_sync.cfg for useNetSNMPagent
 0 - synchronization not configured
 1 - out of sync - running master mode
 2 - in sync - running  mastermode
 3 - in sync - running slave mode
 4 - in sync - running master mode (wait to reach state 2)
"
    ::= {useNetSNMPagent 6}

usePerlIOscalar  OBJECT-TYPE
    SYNTAX      OCTET STRING
    MAX-ACCESS  read-write
    STATUS      current
    DESCRIPTION
"
If selected, the perl module PerlIO::scalar will be loaded if it is installed. If not selected, ASSP will not load the perl module PerlIO::scalar even it is installed and several features of ASSP will not be available! It is recommended to disable installed but unused modules to reduce the required memory. Requires ASSP restart!
"
    REFERENCE "Use Module PerlIO::scalar"
    DEFVAL { "1" }
    ::= {ModuleSetup 3032}

syncStatusePerlIOscalar  OBJECT-TYPE
    SYNTAX      OCTET STRING
    MAX-ACCESS  read-only
    STATUS      current
    DESCRIPTION
"
synchronization status for usePerlIOscalar
-1 - usePerlIOscalar could not be synchronized
 0 - synchronization not configured
 1 - out of sync - running master mode
 2 - in sync - running  mastermode
 3 - in sync - running slave mode
 4 - in sync - running master mode (wait to reach state 2)
"
    ::= {usePerlIOscalar 5}

syncStatStrusePerlIOscalar  OBJECT-TYPE
    SYNTAX      OCTET STRING
    MAX-ACCESS  read-only
    STATUS      current
    DESCRIPTION
"
synchronization status line from file assp_sync.cfg for usePerlIOscalar
 0 - synchronization not configured
 1 - out of sync - running master mode
 2 - in sync - running  mastermode
 3 - in sync - running slave mode
 4 - in sync - running master mode (wait to reach state 2)
"
    ::= {usePerlIOscalar 6}

useRegexpOptimizer  OBJECT-TYPE
    SYNTAX      OCTET STRING
    MAX-ACCESS  read-write
    STATUS      current
    DESCRIPTION
"
If selected, the perl module Regexp::Optimizer will be loaded if it is installed. If not selected, ASSP will not load the perl module Regexp::Optimizer even it is installed and several features of ASSP will not be available! It is recommended to disable installed but unused modules to reduce the required memory. Requires ASSP restart!
"
    REFERENCE "Use Module Regexp::Optimizer"
    DEFVAL { "1" }
    ::= {ModuleSetup 3033}

syncStatuseRegexpOptimizer  OBJECT-TYPE
    SYNTAX      OCTET STRING
    MAX-ACCESS  read-only
    STATUS      current
    DESCRIPTION
"
synchronization status for useRegexpOptimizer
-1 - useRegexpOptimizer could not be synchronized
 0 - synchronization not configured
 1 - out of sync - running master mode
 2 - in sync - running  mastermode
 3 - in sync - running slave mode
 4 - in sync - running master mode (wait to reach state 2)
"
    ::= {useRegexpOptimizer 5}

syncStatStruseRegexpOptimizer  OBJECT-TYPE
    SYNTAX      OCTET STRING
    MAX-ACCESS  read-only
    STATUS      current
    DESCRIPTION
"
synchronization status line from file assp_sync.cfg for useRegexpOptimizer
 0 - synchronization not configured
 1 - out of sync - running master mode
 2 - in sync - running  mastermode
 3 - in sync - running slave mode
 4 - in sync - running master mode (wait to reach state 2)
"
    ::= {useRegexpOptimizer 6}

useScheduleCron  OBJECT-TYPE
    SYNTAX      OCTET STRING
    MAX-ACCESS  read-write
    STATUS      current
    DESCRIPTION
"
If selected, the perl module Schedule::Cron will be loaded if it is installed. If not selected, ASSP will not load the perl module Schedule::Cron even it is installed and several features of ASSP will not be available! It is recommended to disable installed but unused modules to reduce the required memory. Requires ASSP restart!This module is possibly used for ReStartSchedule MemoryUsageCheckSchedule RebuildSchedule and maybe some other features.
"
    REFERENCE "Use Module Schedule::Cron"
    DEFVAL { "1" }
    ::= {ModuleSetup 3034}

syncStatuseScheduleCron  OBJECT-TYPE
    SYNTAX      OCTET STRING
    MAX-ACCESS  read-only
    STATUS      current
    DESCRIPTION
"
synchronization status for useScheduleCron
-1 - useScheduleCron could not be synchronized
 0 - synchronization not configured
 1 - out of sync - running master mode
 2 - in sync - running  mastermode
 3 - in sync - running slave mode
 4 - in sync - running master mode (wait to reach state 2)
"
    ::= {useScheduleCron 5}

syncStatStruseScheduleCron  OBJECT-TYPE
    SYNTAX      OCTET STRING
    MAX-ACCESS  read-only
    STATUS      current
    DESCRIPTION
"
synchronization status line from file assp_sync.cfg for useScheduleCron
 0 - synchronization not configured
 1 - out of sync - running master mode
 2 - in sync - running  mastermode
 3 - in sync - running slave mode
 4 - in sync - running master mode (wait to reach state 2)
"
    ::= {useScheduleCron 6}

useSysCpuAffinity  OBJECT-TYPE
    SYNTAX      OCTET STRING
    MAX-ACCESS  read-write
    STATUS      current
    DESCRIPTION
"
If selected, the perl module Sys::CpuAffinity will be loaded if it is installed. If not selected, ASSP will not load the perl module Sys::CpuAffinity even it is installed and several features of ASSP will not be available! It is recommended to disable installed but unused modules to reduce the required memory. Requires ASSP restart!This module is possibly used for asspCpuAffinity and maybe some other features.
"
    REFERENCE "Use Module Sys::CpuAffinity"
    DEFVAL { "1" }
    ::= {ModuleSetup 3035}

syncStatuseSysCpuAffinity  OBJECT-TYPE
    SYNTAX      OCTET STRING
    MAX-ACCESS  read-only
    STATUS      current
    DESCRIPTION
"
synchronization status for useSysCpuAffinity
-1 - useSysCpuAffinity could not be synchronized
 0 - synchronization not configured
 1 - out of sync - running master mode
 2 - in sync - running  mastermode
 3 - in sync - running slave mode
 4 - in sync - running master mode (wait to reach state 2)
"
    ::= {useSysCpuAffinity 5}

syncStatStruseSysCpuAffinity  OBJECT-TYPE
    SYNTAX      OCTET STRING
    MAX-ACCESS  read-only
    STATUS      current
    DESCRIPTION
"
synchronization status line from file assp_sync.cfg for useSysCpuAffinity
 0 - synchronization not configured
 1 - out of sync - running master mode
 2 - in sync - running  mastermode
 3 - in sync - running slave mode
 4 - in sync - running master mode (wait to reach state 2)
"
    ::= {useSysCpuAffinity 6}

useSysMemInfo  OBJECT-TYPE
    SYNTAX      OCTET STRING
    MAX-ACCESS  read-write
    STATUS      current
    DESCRIPTION
"
If selected, the perl module Sys::MemInfo will be loaded if it is installed. If not selected, ASSP will not load the perl module Sys::MemInfo even it is installed and several features of ASSP will not be available! It is recommended to disable installed but unused modules to reduce the required memory. Requires ASSP restart!
"
    REFERENCE "Use Module Sys::MemInfo"
    DEFVAL { "1" }
    ::= {ModuleSetup 3036}

syncStatuseSysMemInfo  OBJECT-TYPE
    SYNTAX      OCTET STRING
    MAX-ACCESS  read-only
    STATUS      current
    DESCRIPTION
"
synchronization status for useSysMemInfo
-1 - useSysMemInfo could not be synchronized
 0 - synchronization not configured
 1 - out of sync - running master mode
 2 - in sync - running  mastermode
 3 - in sync - running slave mode
 4 - in sync - running master mode (wait to reach state 2)
"
    ::= {useSysMemInfo 5}

syncStatStruseSysMemInfo  OBJECT-TYPE
    SYNTAX      OCTET STRING
    MAX-ACCESS  read-only
    STATUS      current
    DESCRIPTION
"
synchronization status line from file assp_sync.cfg for useSysMemInfo
 0 - synchronization not configured
 1 - out of sync - running master mode
 2 - in sync - running  mastermode
 3 - in sync - running slave mode
 4 - in sync - running master mode (wait to reach state 2)
"
    ::= {useSysMemInfo 6}

useSysSyslog  OBJECT-TYPE
    SYNTAX      OCTET STRING
    MAX-ACCESS  read-write
    STATUS      current
    DESCRIPTION
"
If selected, the perl module Sys::Syslog will be loaded if it is installed. If not selected, ASSP will not load the perl module Sys::Syslog even it is installed and several features of ASSP will not be available! It is recommended to disable installed but unused modules to reduce the required memory. Requires ASSP restart!This module is possibly used for sysLog and maybe some other features.
"
    REFERENCE "Use Module Sys::Syslog"
    DEFVAL { "1" }
    ::= {ModuleSetup 3037}

syncStatuseSysSyslog  OBJECT-TYPE
    SYNTAX      OCTET STRING
    MAX-ACCESS  read-only
    STATUS      current
    DESCRIPTION
"
synchronization status for useSysSyslog
-1 - useSysSyslog could not be synchronized
 0 - synchronization not configured
 1 - out of sync - running master mode
 2 - in sync - running  mastermode
 3 - in sync - running slave mode
 4 - in sync - running master mode (wait to reach state 2)
"
    ::= {useSysSyslog 5}

syncStatStruseSysSyslog  OBJECT-TYPE
    SYNTAX      OCTET STRING
    MAX-ACCESS  read-only
    STATUS      current
    DESCRIPTION
"
synchronization status line from file assp_sync.cfg for useSysSyslog
 0 - synchronization not configured
 1 - out of sync - running master mode
 2 - in sync - running  mastermode
 3 - in sync - running slave mode
 4 - in sync - running master mode (wait to reach state 2)
"
    ::= {useSysSyslog 6}

useTextUnidecode  OBJECT-TYPE
    SYNTAX      OCTET STRING
    MAX-ACCESS  read-write
    STATUS      current
    DESCRIPTION
"
If selected, the perl module Text::Unidecode will be loaded if it is installed. If not selected, ASSP will not load the perl module Text::Unidecode even it is installed and several features of ASSP will not be available! It is recommended to disable installed but unused modules to reduce the required memory. Requires ASSP restart!This module is possibly used for DoTransliterate and maybe some other features.
"
    REFERENCE "Use Module Text::Unidecode"
    DEFVAL { "1" }
    ::= {ModuleSetup 3038}

syncStatuseTextUnidecode  OBJECT-TYPE
    SYNTAX      OCTET STRING
    MAX-ACCESS  read-only
    STATUS      current
    DESCRIPTION
"
synchronization status for useTextUnidecode
-1 - useTextUnidecode could not be synchronized
 0 - synchronization not configured
 1 - out of sync - running master mode
 2 - in sync - running  mastermode
 3 - in sync - running slave mode
 4 - in sync - running master mode (wait to reach state 2)
"
    ::= {useTextUnidecode 5}

syncStatStruseTextUnidecode  OBJECT-TYPE
    SYNTAX      OCTET STRING
    MAX-ACCESS  read-only
    STATUS      current
    DESCRIPTION
"
synchronization status line from file assp_sync.cfg for useTextUnidecode
 0 - synchronization not configured
 1 - out of sync - running master mode
 2 - in sync - running  mastermode
 3 - in sync - running slave mode
 4 - in sync - running master mode (wait to reach state 2)
"
    ::= {useTextUnidecode 6}

useThreadState  OBJECT-TYPE
    SYNTAX      OCTET STRING
    MAX-ACCESS  read-write
    STATUS      current
    DESCRIPTION
"
If selected, the perl module Thread::State will be loaded if it is installed. If not selected, ASSP will not load the perl module Thread::State even it is installed and several features of ASSP will not be available! It is recommended to disable installed but unused modules to reduce the required memory. Requires ASSP restart!This module is possibly used for WorkerCPUPriority and maybe some other features.
"
    REFERENCE "Use Module Thread::State"
    DEFVAL { "1" }
    ::= {ModuleSetup 3039}

syncStatuseThreadState  OBJECT-TYPE
    SYNTAX      OCTET STRING
    MAX-ACCESS  read-only
    STATUS      current
    DESCRIPTION
"
synchronization status for useThreadState
-1 - useThreadState could not be synchronized
 0 - synchronization not configured
 1 - out of sync - running master mode
 2 - in sync - running  mastermode
 3 - in sync - running slave mode
 4 - in sync - running master mode (wait to reach state 2)
"
    ::= {useThreadState 5}

syncStatStruseThreadState  OBJECT-TYPE
    SYNTAX      OCTET STRING
    MAX-ACCESS  read-only
    STATUS      current
    DESCRIPTION
"
synchronization status line from file assp_sync.cfg for useThreadState
 0 - synchronization not configured
 1 - out of sync - running master mode
 2 - in sync - running  mastermode
 3 - in sync - running slave mode
 4 - in sync - running master mode (wait to reach state 2)
"
    ::= {useThreadState 6}

useTieRDBM  OBJECT-TYPE
    SYNTAX      OCTET STRING
    MAX-ACCESS  read-write
    STATUS      current
    DESCRIPTION
"
If selected, the perl module Tie::RDBM will be loaded if it is installed. If not selected, ASSP will not load the perl module Tie::RDBM even it is installed and several features of ASSP will not be available! It is recommended to disable installed but unused modules to reduce the required memory. Requires ASSP restart!This module is possibly used for myhost and maybe some other features.
"
    REFERENCE "Use Module Tie::RDBM"
    DEFVAL { "1" }
    ::= {ModuleSetup 3040}

syncStatuseTieRDBM  OBJECT-TYPE
    SYNTAX      OCTET STRING
    MAX-ACCESS  read-only
    STATUS      current
    DESCRIPTION
"
synchronization status for useTieRDBM
-1 - useTieRDBM could not be synchronized
 0 - synchronization not configured
 1 - out of sync - running master mode
 2 - in sync - running  mastermode
 3 - in sync - running slave mode
 4 - in sync - running master mode (wait to reach state 2)
"
    ::= {useTieRDBM 5}

syncStatStruseTieRDBM  OBJECT-TYPE
    SYNTAX      OCTET STRING
    MAX-ACCESS  read-only
    STATUS      current
    DESCRIPTION
"
synchronization status line from file assp_sync.cfg for useTieRDBM
 0 - synchronization not configured
 1 - out of sync - running master mode
 2 - in sync - running  mastermode
 3 - in sync - running slave mode
 4 - in sync - running master mode (wait to reach state 2)
"
    ::= {useTieRDBM 6}

useUnicodeGCString  OBJECT-TYPE
    SYNTAX      OCTET STRING
    MAX-ACCESS  read-write
    STATUS      current
    DESCRIPTION
"
If selected, the perl module Unicode::GCString will be loaded if it is installed. If not selected, ASSP will not load the perl module Unicode::GCString even it is installed and several features of ASSP will not be available! It is recommended to disable installed but unused modules to reduce the required memory. Requires ASSP restart!
"
    REFERENCE "Use Module Unicode::GCString"
    DEFVAL { "1" }
    ::= {ModuleSetup 3041}

syncStatuseUnicodeGCString  OBJECT-TYPE
    SYNTAX      OCTET STRING
    MAX-ACCESS  read-only
    STATUS      current
    DESCRIPTION
"
synchronization status for useUnicodeGCString
-1 - useUnicodeGCString could not be synchronized
 0 - synchronization not configured
 1 - out of sync - running master mode
 2 - in sync - running  mastermode
 3 - in sync - running slave mode
 4 - in sync - running master mode (wait to reach state 2)
"
    ::= {useUnicodeGCString 5}

syncStatStruseUnicodeGCString  OBJECT-TYPE
    SYNTAX      OCTET STRING
    MAX-ACCESS  read-only
    STATUS      current
    DESCRIPTION
"
synchronization status line from file assp_sync.cfg for useUnicodeGCString
 0 - synchronization not configured
 1 - out of sync - running master mode
 2 - in sync - running  mastermode
 3 - in sync - running slave mode
 4 - in sync - running master mode (wait to reach state 2)
"
    ::= {useUnicodeGCString 6}

useWin32APIOutputDebugString  OBJECT-TYPE
    SYNTAX      OCTET STRING
    MAX-ACCESS  read-write
    STATUS      current
    DESCRIPTION
"
If selected, the perl module Win32::API::OutputDebugString will be loaded if it is installed. If not selected, ASSP will not load the perl module Win32::API::OutputDebugString even it is installed and several features of ASSP will not be available! It is recommended to disable installed but unused modules to reduce the required memory. Requires ASSP restart!
"
    REFERENCE "Use Module Win32::API::OutputDebugString"
    DEFVAL { "0" }
    ::= {ModuleSetup 3042}

syncStatuseWin32APIOutputDebugString  OBJECT-TYPE
    SYNTAX      OCTET STRING
    MAX-ACCESS  read-only
    STATUS      current
    DESCRIPTION
"
synchronization status for useWin32APIOutputDebugString
-1 - useWin32APIOutputDebugString could not be synchronized
 0 - synchronization not configured
 1 - out of sync - running master mode
 2 - in sync - running  mastermode
 3 - in sync - running slave mode
 4 - in sync - running master mode (wait to reach state 2)
"
    ::= {useWin32APIOutputDebugString 5}

syncStatStruseWin32APIOutputDebugString  OBJECT-TYPE
    SYNTAX      OCTET STRING
    MAX-ACCESS  read-only
    STATUS      current
    DESCRIPTION
"
synchronization status line from file assp_sync.cfg for useWin32APIOutputDebugString
 0 - synchronization not configured
 1 - out of sync - running master mode
 2 - in sync - running  mastermode
 3 - in sync - running slave mode
 4 - in sync - running master mode (wait to reach state 2)
"
    ::= {useWin32APIOutputDebugString 6}

useWin32Daemon  OBJECT-TYPE
    SYNTAX      OCTET STRING
    MAX-ACCESS  read-write
    STATUS      current
    DESCRIPTION
"
If selected, the perl module Win32::Daemon will be loaded if it is installed. If not selected, ASSP will not load the perl module Win32::Daemon even it is installed and several features of ASSP will not be available! It is recommended to disable installed but unused modules to reduce the required memory. Requires ASSP restart!
"
    REFERENCE "Use Module Win32::Daemon"
    DEFVAL { "1" }
    ::= {ModuleSetup 3043}

syncStatuseWin32Daemon  OBJECT-TYPE
    SYNTAX      OCTET STRING
    MAX-ACCESS  read-only
    STATUS      current
    DESCRIPTION
"
synchronization status for useWin32Daemon
-1 - useWin32Daemon could not be synchronized
 0 - synchronization not configured
 1 - out of sync - running master mode
 2 - in sync - running  mastermode
 3 - in sync - running slave mode
 4 - in sync - running master mode (wait to reach state 2)
"
    ::= {useWin32Daemon 5}

syncStatStruseWin32Daemon  OBJECT-TYPE
    SYNTAX      OCTET STRING
    MAX-ACCESS  read-only
    STATUS      current
    DESCRIPTION
"
synchronization status line from file assp_sync.cfg for useWin32Daemon
 0 - synchronization not configured
 1 - out of sync - running master mode
 2 - in sync - running  mastermode
 3 - in sync - running slave mode
 4 - in sync - running master mode (wait to reach state 2)
"
    ::= {useWin32Daemon 6}

useWin32Unicode  OBJECT-TYPE
    SYNTAX      OCTET STRING
    MAX-ACCESS  read-write
    STATUS      current
    DESCRIPTION
"
If selected, the perl module Win32::Unicode will be loaded if it is installed. If not selected, ASSP will not load the perl module Win32::Unicode even it is installed and several features of ASSP will not be available! It is recommended to disable installed but unused modules to reduce the required memory. Requires ASSP restart!This module is possibly used for UseUnicode4MaillogNames and maybe some other features.
"
    REFERENCE "Use Module Win32::Unicode"
    DEFVAL { "1" }
    ::= {ModuleSetup 3044}

syncStatuseWin32Unicode  OBJECT-TYPE
    SYNTAX      OCTET STRING
    MAX-ACCESS  read-only
    STATUS      current
    DESCRIPTION
"
synchronization status for useWin32Unicode
-1 - useWin32Unicode could not be synchronized
 0 - synchronization not configured
 1 - out of sync - running master mode
 2 - in sync - running  mastermode
 3 - in sync - running slave mode
 4 - in sync - running master mode (wait to reach state 2)
"
    ::= {useWin32Unicode 5}

syncStatStruseWin32Unicode  OBJECT-TYPE
    SYNTAX      OCTET STRING
    MAX-ACCESS  read-only
    STATUS      current
    DESCRIPTION
"
synchronization status line from file assp_sync.cfg for useWin32Unicode
 0 - synchronization not configured
 1 - out of sync - running master mode
 2 - in sync - running  mastermode
 3 - in sync - running slave mode
 4 - in sync - running master mode (wait to reach state 2)
"
    ::= {useWin32Unicode 6}

ASSPAFCPlugin  OBJECT IDENTIFIER ::= {asspConfig 41}
DoASSPAFC  OBJECT-TYPE
    SYNTAX      OCTET STRING
    MAX-ACCESS  read-write
    STATUS      current
    DESCRIPTION
"
This plugin is an addon to the default attachment- and ClamAV- engine of ASSP. The default engines only scannes the first MaxBytes/ClamAVBytes of an email. If you enable this plugin, the complete mail will be scanned for bad attachments and/or viruses!
 The default engine(s) will be disabled by this enhanced version. Before you enable this plugin, please go to the configuration section(s) and configure the values for attachments and/or ClamAV! This plugin requires an installed  module in PERL.
 This plugin is designed for- and running in call/run level 'complete mail'!
"
    REFERENCE "Do the ASSP_AFC Plugin"
    DEFVAL { "0" }
    ::= {ASSPAFCPlugin 10000}

syncStatDoASSPAFC  OBJECT-TYPE
    SYNTAX      OCTET STRING
    MAX-ACCESS  read-only
    STATUS      current
    DESCRIPTION
"
synchronization status for DoASSPAFC
-1 - DoASSPAFC could not be synchronized
 0 - synchronization not configured
 1 - out of sync - running master mode
 2 - in sync - running  mastermode
 3 - in sync - running slave mode
 4 - in sync - running master mode (wait to reach state 2)
"
    ::= {DoASSPAFC 5}

syncStatStrDoASSPAFC  OBJECT-TYPE
    SYNTAX      OCTET STRING
    MAX-ACCESS  read-only
    STATUS      current
    DESCRIPTION
"
synchronization status line from file assp_sync.cfg for DoASSPAFC
 0 - synchronization not configured
 1 - out of sync - running master mode
 2 - in sync - running  mastermode
 3 - in sync - running slave mode
 4 - in sync - running master mode (wait to reach state 2)
"
    ::= {DoASSPAFC 6}

ASSPAFCSelect  OBJECT-TYPE
    SYNTAX      OCTET STRING
    MAX-ACCESS  read-write
    STATUS      current
    DESCRIPTION
"
If you enable one or both options of this plugin, the complete mail will be scanned for bad attachments and/or viruses!
"
    REFERENCE "Select the ASSP_AFC Plugin Action"
    DEFVAL { "3" }
    ::= {ASSPAFCPlugin 10001}

syncStatASSPAFCSelect  OBJECT-TYPE
    SYNTAX      OCTET STRING
    MAX-ACCESS  read-only
    STATUS      current
    DESCRIPTION
"
synchronization status for ASSPAFCSelect
-1 - ASSPAFCSelect could not be synchronized
 0 - synchronization not configured
 1 - out of sync - running master mode
 2 - in sync - running  mastermode
 3 - in sync - running slave mode
 4 - in sync - running master mode (wait to reach state 2)
"
    ::= {ASSPAFCSelect 5}

syncStatStrASSPAFCSelect  OBJECT-TYPE
    SYNTAX      OCTET STRING
    MAX-ACCESS  read-only
    STATUS      current
    DESCRIPTION
"
synchronization status line from file assp_sync.cfg for ASSPAFCSelect
 0 - synchronization not configured
 1 - out of sync - running master mode
 2 - in sync - running  mastermode
 3 - in sync - running slave mode
 4 - in sync - running master mode (wait to reach state 2)
"
    ::= {ASSPAFCSelect 6}

ASSPAFCPriority  OBJECT-TYPE
    SYNTAX      OCTET STRING
    MAX-ACCESS  read-write
    STATUS      current
    DESCRIPTION
"
Sets the priority of this Plugin within the call/run-level 'complete mail'. The Plugin with the lowest priority value is processed first!
"
    REFERENCE "the priority of the Plugin"
    DEFVAL { "6" }
    ::= {ASSPAFCPlugin 10002}

syncStatASSPAFCPriority  OBJECT-TYPE
    SYNTAX      OCTET STRING
    MAX-ACCESS  read-only
    STATUS      current
    DESCRIPTION
"
synchronization status for ASSPAFCPriority
-1 - ASSPAFCPriority could not be synchronized
 0 - synchronization not configured
 1 - out of sync - running master mode
 2 - in sync - running  mastermode
 3 - in sync - running slave mode
 4 - in sync - running master mode (wait to reach state 2)
"
    ::= {ASSPAFCPriority 5}

syncStatStrASSPAFCPriority  OBJECT-TYPE
    SYNTAX      OCTET STRING
    MAX-ACCESS  read-only
    STATUS      current
    DESCRIPTION
"
synchronization status line from file assp_sync.cfg for ASSPAFCPriority
 0 - synchronization not configured
 1 - out of sync - running master mode
 2 - in sync - running  mastermode
 3 - in sync - running slave mode
 4 - in sync - running master mode (wait to reach state 2)
"
    ::= {ASSPAFCPriority 6}

ASSPAFCReplBadAttach  OBJECT-TYPE
    SYNTAX      OCTET STRING
    MAX-ACCESS  read-write
    STATUS      current
    DESCRIPTION
"
If set and AttachmentBlocking is set to block, the mail will not be blocked but the bad attachment will be replaced with a text!
"
    REFERENCE "Replace Bad Attachments"
    DEFVAL { "0" }
    ::= {ASSPAFCPlugin 10003}

syncStatASSPAFCReplBadAttach  OBJECT-TYPE
    SYNTAX      OCTET STRING
    MAX-ACCESS  read-only
    STATUS      current
    DESCRIPTION
"
synchronization status for ASSPAFCReplBadAttach
-1 - ASSPAFCReplBadAttach could not be synchronized
 0 - synchronization not configured
 1 - out of sync - running master mode
 2 - in sync - running  mastermode
 3 - in sync - running slave mode
 4 - in sync - running master mode (wait to reach state 2)
"
    ::= {ASSPAFCReplBadAttach 5}

syncStatStrASSPAFCReplBadAttach  OBJECT-TYPE
    SYNTAX      OCTET STRING
    MAX-ACCESS  read-only
    STATUS      current
    DESCRIPTION
"
synchronization status line from file assp_sync.cfg for ASSPAFCReplBadAttach
 0 - synchronization not configured
 1 - out of sync - running master mode
 2 - in sync - running  mastermode
 3 - in sync - running slave mode
 4 - in sync - running master mode (wait to reach state 2)
"
    ::= {ASSPAFCReplBadAttach 6}

ASSPAFCReplBadAttachText  OBJECT-TYPE
    SYNTAX      OCTET STRING
    MAX-ACCESS  read-write
    STATUS      current
    DESCRIPTION
"
The text which replaces the bad attachment. The litteral FILENAME will be replaced with the name of the bad attachment!
"
    REFERENCE "Replace Bad Attachments Text"
    DEFVAL { "The attached file (FILENAME) was removed from this email by ASSP for policy reasons!" }
    ::= {ASSPAFCPlugin 10004}

syncStatASSPAFCReplBadAttachText  OBJECT-TYPE
    SYNTAX      OCTET STRING
    MAX-ACCESS  read-only
    STATUS      current
    DESCRIPTION
"
synchronization status for ASSPAFCReplBadAttachText
-1 - ASSPAFCReplBadAttachText could not be synchronized
 0 - synchronization not configured
 1 - out of sync - running master mode
 2 - in sync - running  mastermode
 3 - in sync - running slave mode
 4 - in sync - running master mode (wait to reach state 2)
"
    ::= {ASSPAFCReplBadAttachText 5}

syncStatStrASSPAFCReplBadAttachText  OBJECT-TYPE
    SYNTAX      OCTET STRING
    MAX-ACCESS  read-only
    STATUS      current
    DESCRIPTION
"
synchronization status line from file assp_sync.cfg for ASSPAFCReplBadAttachText
 0 - synchronization not configured
 1 - out of sync - running master mode
 2 - in sync - running  mastermode
 3 - in sync - running slave mode
 4 - in sync - running master mode (wait to reach state 2)
"
    ::= {ASSPAFCReplBadAttachText 6}

ASSPAFCReplViriParts  OBJECT-TYPE
    SYNTAX      OCTET STRING
    MAX-ACCESS  read-write
    STATUS      current
    DESCRIPTION
"
If set and virus scanning (UseClamAV) is enabled, the mail will not be blocked but the bad attachment or mail part will be replaced with a text!
"
    REFERENCE "Replace Virus Parts"
    DEFVAL { "0" }
    ::= {ASSPAFCPlugin 10005}

syncStatASSPAFCReplViriParts  OBJECT-TYPE
    SYNTAX      OCTET STRING
    MAX-ACCESS  read-only
    STATUS      current
    DESCRIPTION
"
synchronization status for ASSPAFCReplViriParts
-1 - ASSPAFCReplViriParts could not be synchronized
 0 - synchronization not configured
 1 - out of sync - running master mode
 2 - in sync - running  mastermode
 3 - in sync - running slave mode
 4 - in sync - running master mode (wait to reach state 2)
"
    ::= {ASSPAFCReplViriParts 5}

syncStatStrASSPAFCReplViriParts  OBJECT-TYPE
    SYNTAX      OCTET STRING
    MAX-ACCESS  read-only
    STATUS      current
    DESCRIPTION
"
synchronization status line from file assp_sync.cfg for ASSPAFCReplViriParts
 0 - synchronization not configured
 1 - out of sync - running master mode
 2 - in sync - running  mastermode
 3 - in sync - running slave mode
 4 - in sync - running master mode (wait to reach state 2)
"
    ::= {ASSPAFCReplViriParts 6}

ASSPAFCReplViriPartsText  OBJECT-TYPE
    SYNTAX      OCTET STRING
    MAX-ACCESS  read-write
    STATUS      current
    DESCRIPTION
"
The text which replaces the bad mailparts that contains a virus. The litteral FILENAME will be replaced with the name of a bad attachment!
"
    REFERENCE "Replace Virus Parts Text"
    DEFVAL { "There was a virus removed from this email (attachment FILENAME) by ASSP!" }
    ::= {ASSPAFCPlugin 10006}

syncStatASSPAFCReplViriPartsText  OBJECT-TYPE
    SYNTAX      OCTET STRING
    MAX-ACCESS  read-only
    STATUS      current
    DESCRIPTION
"
synchronization status for ASSPAFCReplViriPartsText
-1 - ASSPAFCReplViriPartsText could not be synchronized
 0 - synchronization not configured
 1 - out of sync - running master mode
 2 - in sync - running  mastermode
 3 - in sync - running slave mode
 4 - in sync - running master mode (wait to reach state 2)
"
    ::= {ASSPAFCReplViriPartsText 5}

syncStatStrASSPAFCReplViriPartsText  OBJECT-TYPE
    SYNTAX      OCTET STRING
    MAX-ACCESS  read-only
    STATUS      current
    DESCRIPTION
"
synchronization status line from file assp_sync.cfg for ASSPAFCReplViriPartsText
 0 - synchronization not configured
 1 - out of sync - running master mode
 2 - in sync - running  mastermode
 3 - in sync - running slave mode
 4 - in sync - running master mode (wait to reach state 2)
"
    ::= {ASSPAFCReplViriPartsText 6}

ASSPAFCMSGSIZEscore  OBJECT-TYPE
    SYNTAX      OCTET STRING
    MAX-ACCESS  read-write
    STATUS      current
    DESCRIPTION
"
You can increase the message score of a mail because of its size (in byte). Define the size and scores in a comma separated list using the syntax 'size=&gt;score[,othersize=&gt;otherscore]'. The list will be processed in reversed numerical order of the size value. If the size of a mail is equal or higher as the defined size, the associated message score will be added. An possible definition could be:
  500000=&gt;10,1000000=&gt;5,1500000=&gt;0
  which meens:
  if the message size is &gt;= 1500000 byte no score will be added
  if the message size is &gt;= 1000000 byte and &lt; 1500000 byte a score of 5 will be added
  if the message size is &gt;= 500000 byte and &lt; 1000000 byte a score of 10 will be added
  if the message size is &lt; 500000 byte no score will be added.
  This feature will not process incomming mails, whitelisted mails and mail that are noprocessing - except mails, that are noprocessing only because of there message size (npSize).
"
    REFERENCE "Increase MSG-Score on MSG Size"
    DEFVAL { "" }
    ::= {ASSPAFCPlugin 10007}

ASSPAFCDetectSpamAttachRe  OBJECT-TYPE
    SYNTAX      OCTET STRING
    MAX-ACCESS  read-write
    STATUS      current
    DESCRIPTION
"
An regular expression used on the 'Content-Type' header tag to detect MIME parts that should be checked to be known spam or not. The rebuildspamdb task will build spamdb entries for these attachements and inlines (in assp build 12022 and higher). The plugin will block an email, if a bad attachment is found and was not removed/replaced by any other rule in this plugin. Leave this blank to disable the feature.
 for example:
 image\/
 application\/pd[ft]
 application\/zip
 
"
    REFERENCE "Detect Spam Attachments*"
    DEFVAL { "image\/" }
    ::= {ASSPAFCPlugin 10008}

ASSPAFCWebScript  OBJECT-TYPE
    SYNTAX      OCTET STRING
    MAX-ACCESS  read-write
    STATUS      current
    DESCRIPTION
"
If the size of an undecoded attachment exceeds the ASSP_AFCinsize or ASSP_AFCoutsize parameter, assp will call this script and will replace the attachment with the text returned by this script or executable.
  If no text is returned by the script (a warning is written to the maillog.txt) or the returned text begins with the word 'error', the attachment will not be replaced.
  The script has to write the resulting text or error to STDOUT.
  The resulting text could be any of plain text or html code. The MIME-enconding and the Content-Type value of the resulting MIME-part will be set accordingly.
  The text should contain the link to download the attachment, possibly some explanation (eg. download life time), web login information or a web-session-identifier - what ever is needed to fit the requirements of your web server.
  You have to define the full path to the script and all parameters that should be pass to the script. The literal FILENAME will be replaced with the attachment filename (including the full path) that was stored in the /transfer folder. Any literal starting with an '$', will be replaced by the according connection hash value or the global variable with the name.
  for example:
  $relayok will be replaced by $Con->{relayok} - which identifies if it is an incoming (1) or outgoing/local (0) mail
  So a possible definition of this parameter could be: 
  '/usr/bin/move_attachment_to_web.sh $relayok FILENAME' 
  or 
  'c:/assp/move_attachment_to_web.cmd $relayok FILENAME'
  The file has to be removed by the script. If not, assp will warn about this and will remove the file in the /transfer folder.
  To keep the filenames unique, the assp message identifier is placed in front of the filename - like: M1-30438-02027_attachmentfilename. Notice: if the filename contains unicode characters, assp will pass this characters in UTF-8 to your script!
  Keep in mind, that if this script terminates it's own process - ASSP will die!
 
"
    REFERENCE "Script to move large attachments to a web server"
    DEFVAL { "" }
    ::= {ASSPAFCPlugin 10009}

ASSPAFCinsize  OBJECT-TYPE
    SYNTAX      OCTET STRING
    MAX-ACCESS  read-write
    STATUS      current
    DESCRIPTION
"
The size in KB of an attachment in incoming mails that must be reached, to call the ASSP_AFCWebScript. This parameter is ignored if left blank or set to zero.
"
    REFERENCE "Attachment size incoming"
    DEFVAL { "1024" }
    ::= {ASSPAFCPlugin 10010}

ASSPAFCoutsize  OBJECT-TYPE
    SYNTAX      OCTET STRING
    MAX-ACCESS  read-write
    STATUS      current
    DESCRIPTION
"
The size in KB of an attachment in outgoing or local mails that must be reached, to call the ASSP_AFCWebScript. This parameter is ignored if left blank or set to zero.
"
    REFERENCE "Attachment size outgoing/local"
    DEFVAL { "1024" }
    ::= {ASSPAFCPlugin 10011}

ASSPAFCblockEncryptedZIP  OBJECT-TYPE
    SYNTAX      OCTET STRING
    MAX-ACCESS  read-write
    STATUS      current
    DESCRIPTION
"
If set, encrypted or password protected compressed attachments will be blocked or replaced according to ASSP_AFCSelect and ASSP_AFCReplBadAttach .
 To define a user based check of compressed attachments, configure 'UserAttach'. This plugin enhance the definiton options for UserAttach. In addition to the existing options, the following syntax could be used:
 For example:
 zip:user@domain.tld => good => ai|asc|bhx|dat|doc|eps|zip
 zip:*@domain.tld => good => ai|asc|bhx , good-out => eps|gif , good-in => htm|html , block => pdf|ppt , block-out => rar|rpt , block-in => xls|exe\-bin|crypt\-zip|encrypt
 Those definitions (leading zip:) are only used inside compressed files.
 The extension 'crypt-zip' could be used to allow or deni encrypted compressed attachments for users at any compression level.
 The extension 'encrypt' could be used to allow or deni encrypted (eg. aes) for users.
 The following compression formats/extensions are supported: tar.gz,tgz,gz,tar,zip,jar,ear,war,par,tbz,tbz2,tar.bz,tar.bz2,bz2,Z,lzma,txz,tar.xz,xz.
 The detection of compressed files is done content based not filename extension based.
 Depending on your Perl distribution, it could be possible that you must install additionaly 'IO::Compress::...' (for example: IO::Compress:Lzma) modules to support the compression methodes.
 
"
    REFERENCE "Block Encrypted Compressed Attachments"
    DEFVAL { "0" }
    ::= {ASSPAFCPlugin 10012}

ASSPAFCMaxZIPLevel  OBJECT-TYPE
    SYNTAX      OCTET STRING
    MAX-ACCESS  read-write
    STATUS      current
    DESCRIPTION
"
The maximum decompression cycles use on a compressed attachment (eg: zip in zip in zip ...). Default value is 10 - zero is not allowed to be used!
"
    REFERENCE "Maximum Decompression Level"
    DEFVAL { "10" }
    ::= {ASSPAFCPlugin 10013}

ASSPAFCSMIME  OBJECT-TYPE
    SYNTAX      OCTET STRING
    MAX-ACCESS  read-write
    STATUS      current
    DESCRIPTION
"
If configured, outgoing mails will be digitaly signed according to the SMIME specifications.
 It is possible to configure privat and/or corporate signatures. In any case, the 'file:' option must be used - specify one configuration per line.
 The domain or user is separated by '=&gt;' from the signing configuration/policy. It is possible to use group definitions of domains and users using the [ Groups ] option. Define one line per domain or user or group.
 Configuration entries are separated by comma.
 Configuration entry pairs (tag and value) are separated by '='.
 File definitions for the certificate and privat key have to include the full path to the file! Certificate and privat key have to be provided in PEM format
 If you exchange any certificate or key file, click 'Edit file' and save the file again to force a reload of the internal certificate store.
 The domain / user part accepts full email addresses , domains and groups - wildcards are supported and must be used for domain definitions.
 The domain / user part is compaired to the envelope sender - the first matching entry (in reverse generic order) will be used. Entries starting with a minus sign, explicit exclude the domain/user/group from SMIME processing.
 certfile - is required and specifys the full path to the certificate to use. The subject of the certificate has to include a valid email address. In normal case, this email address is specified by the cert-subject-tag 'emailAddress'. The 'FROM:' address in the mail header will be replaced by this email address and a 'Reply-To:' line with the original sender is added (or replaced) to the mail header.
 If the subject of the certificate specifys the email address in another tag, define this tag (NOT the email address) after 'emailaddress='.
 keyfile - is required and specifys the full path to the file that contains the privat key
 keypass - the tag is required, the value is optional - defines the password required (or not) for the privat key
 emailaddress - is optional - please read 'certfile'
 rcpt - is optional - include/[-]exclude mails to specified users and/or domains (recipients) - to exclude addresses, write a minus in front - separate multiple entries by space
 examples:
 - (1) user@your.domain =&gt; certfile=/certs/user_cert.pem, keyfile=/certs/user_key.pem, keypass=, rcpt=-otheruser@other.domain
 - (2) *your.domain =&gt; certfile=/certs/corporate_cert.pem, keyfile=/certs/corporate_key.pem, keypass=mypassword
 - (3) *@your.domain =&gt; certfile=/certs/corporate_cert.pem, keyfile=/certs/corporate_key.pem, keypass= , emailaddress=Email
 - (4) -user4@your.domain
 - (5) -*@*.your.domain
 - (6) -[no_smime]
 The first example specifys a privat signing policy which exclude the recipient otheruser@other.domain, the second and third example specifys a corporate signing policy (with and without subdomains). The fourth example excludes the user 'user4@your.domain' from SMIME processing. The fives example excludes all subdomains of 'your.domain' from SMIME processing. The last example excludes all domains, subdomains and users defined in the group '[no_smime]' from SMIME processing.
 corporate SMIME signing:
 Assume we define the following configuration line:
 *@your.domain.com =&gt; certfile=/certs/corporate_cert.pem, keyfile=/certs/corporate_key.pem, keypass=
 Now let's say, the subject of the specified certificate (corporate_cert.pem) contains .../emailAddress=central.office@your.domain.com/...
 Your local user 'mark.schmitz@your.domain.com' sends a mail to an external recipient. The related mail header is:
 From: 'Mark Schmitz' &lt;mark.schmitz@your.domain.com&gt;
 Disposition-Notification-To: &lt;mark.schmitz@your.domain.com&gt;
 After SMIME signing the mail, the related mail headers are the following:
 From: 'Mark Schmitz' &lt;central.office@your.domain.com&gt;
 Disposition-Notification-To: &lt;mark.schmitz@your.domain.com&gt;
 Reply-To: &lt;mark.schmitz@your.domain.com&gt;
 The mail client of the recipient will validate the signature against the 'From' address - which corresponds to the email address specified in the subject of the certificate -> VALID
 Pressing the 'REPLY/ANSWER' button, the mail client will provide 'mark.schmitz@your.domain.com' as recipient address using the entry in the 'Reply-To:' header.
 Notice, that some bad and/or older mail clients are ignoring the 'Reply-To:' header tag - in such case an answered mail will go to 'central.office@your.domain.com'.
 ASSP will help you a bit to prevent this. In addition to the required mail header changes, assp will add or enhance the 'References:' mail header tag with a value of 'assp-corp-smime-EMAILADDRESS' , where EMAILADDRESS is the original sender address.
 If assp receives an answered mail, it will look for such an entry in the mail header and will add the found email address to the 'To' header, if it is not already found there.
 
"
    REFERENCE "SMIME sign outgoing mails*"
    DEFVAL { "file:files/smime_cfg.txt" }
    ::= {ASSPAFCPlugin 10014}

ASSPARCPlugin  OBJECT IDENTIFIER ::= {asspConfig 42}
DoASSPARC  OBJECT-TYPE
    SYNTAX      OCTET STRING
    MAX-ACCESS  read-write
    STATUS      current
    DESCRIPTION
"
Enable or disables the archiving of mails.
 If this plugin is installed ' StoreCompleteMail ' will be set to 'no limit'!
 Only collected mails could be archived!
 This Plugin is designed for- and running in call/run level 'complete mail' after the mail is collected!
 The archive request is pushed by the SMTP-workers in to the MaintThread, which will copy the collected file in to the archive folder.
"
    REFERENCE "Do the ASSP_ARC Plugin"
    DEFVAL { "0" }
    ::= {ASSPARCPlugin 11000}

syncStatDoASSPARC  OBJECT-TYPE
    SYNTAX      OCTET STRING
    MAX-ACCESS  read-only
    STATUS      current
    DESCRIPTION
"
synchronization status for DoASSPARC
-1 - DoASSPARC could not be synchronized
 0 - synchronization not configured
 1 - out of sync - running master mode
 2 - in sync - running  mastermode
 3 - in sync - running slave mode
 4 - in sync - running master mode (wait to reach state 2)
"
    ::= {DoASSPARC 5}

syncStatStrDoASSPARC  OBJECT-TYPE
    SYNTAX      OCTET STRING
    MAX-ACCESS  read-only
    STATUS      current
    DESCRIPTION
"
synchronization status line from file assp_sync.cfg for DoASSPARC
 0 - synchronization not configured
 1 - out of sync - running master mode
 2 - in sync - running  mastermode
 3 - in sync - running slave mode
 4 - in sync - running master mode (wait to reach state 2)
"
    ::= {DoASSPARC 6}

ASSPARCPriority  OBJECT-TYPE
    SYNTAX      OCTET STRING
    MAX-ACCESS  read-write
    STATUS      current
    DESCRIPTION
"
Sets the priority of this Plugin within the call/run-level 'complete mail'. The Plugin with the lowest priority value is processed first!
"
    REFERENCE "the priority of the Plugin"
    DEFVAL { "9" }
    ::= {ASSPARCPlugin 11001}

syncStatASSPARCPriority  OBJECT-TYPE
    SYNTAX      OCTET STRING
    MAX-ACCESS  read-only
    STATUS      current
    DESCRIPTION
"
synchronization status for ASSPARCPriority
-1 - ASSPARCPriority could not be synchronized
 0 - synchronization not configured
 1 - out of sync - running master mode
 2 - in sync - running  mastermode
 3 - in sync - running slave mode
 4 - in sync - running master mode (wait to reach state 2)
"
    ::= {ASSPARCPriority 5}

syncStatStrASSPARCPriority  OBJECT-TYPE
    SYNTAX      OCTET STRING
    MAX-ACCESS  read-only
    STATUS      current
    DESCRIPTION
"
synchronization status line from file assp_sync.cfg for ASSPARCPriority
 0 - synchronization not configured
 1 - out of sync - running master mode
 2 - in sync - running  mastermode
 3 - in sync - running slave mode
 4 - in sync - running master mode (wait to reach state 2)
"
    ::= {ASSPARCPriority 6}

ASSPARCinPATH  OBJECT-TYPE
    SYNTAX      OCTET STRING
    MAX-ACCESS  read-write
    STATUS      current
    DESCRIPTION
"
Where to store the archived files for incoming mails. You can build a folder structure if you want. Read below to get more details.
"
    REFERENCE "Archive in PATH"
    DEFVAL { "" }
    ::= {ASSPARCPlugin 11002}

syncStatASSPARCinPATH  OBJECT-TYPE
    SYNTAX      OCTET STRING
    MAX-ACCESS  read-only
    STATUS      current
    DESCRIPTION
"
synchronization status for ASSPARCinPATH
-1 - ASSPARCinPATH could not be synchronized
 0 - synchronization not configured
 1 - out of sync - running master mode
 2 - in sync - running  mastermode
 3 - in sync - running slave mode
 4 - in sync - running master mode (wait to reach state 2)
"
    ::= {ASSPARCinPATH 5}

syncStatStrASSPARCinPATH  OBJECT-TYPE
    SYNTAX      OCTET STRING
    MAX-ACCESS  read-only
    STATUS      current
    DESCRIPTION
"
synchronization status line from file assp_sync.cfg for ASSPARCinPATH
 0 - synchronization not configured
 1 - out of sync - running master mode
 2 - in sync - running  mastermode
 3 - in sync - running slave mode
 4 - in sync - running master mode (wait to reach state 2)
"
    ::= {ASSPARCinPATH 6}

ASSPARCoutPATH  OBJECT-TYPE
    SYNTAX      OCTET STRING
    MAX-ACCESS  read-write
    STATUS      current
    DESCRIPTION
"
Where to store the archived files for outgoing mails. You can build a folder structure if you want.
  The following uppercase literals will be replaced by:
  YEAR - year in format yyyy
  MONTH - month in the format mm
  DAY - day in the format dd
  LOG - the folder name defined by ASSP. notspamlog is used if the mail is HAM in every other case spamlog is used
  RCPT - the full mail address of the receipient
  FROM - the full mail address of the sender
  RNAME - the receipient name without @domain
  FNAME - the sender name without @domain
  RDOMAIN - the recipient domain without @
  FDOMAIN - the sender domain without @
  The filename (without folders) build by assp will be added to the end of the resulting string. Not existing folders will be created by the plugin.
  UNC pathes are supported. For example using a share on windows : \\hostname[or IP]/share/[your path definition]. Only in this case it is allowed to use
  backslashes in the path definition (only the two at start !!!).
  
"
    REFERENCE "Archive out PATH"
    DEFVAL { "" }
    ::= {ASSPARCPlugin 11003}

syncStatASSPARCoutPATH  OBJECT-TYPE
    SYNTAX      OCTET STRING
    MAX-ACCESS  read-only
    STATUS      current
    DESCRIPTION
"
synchronization status for ASSPARCoutPATH
-1 - ASSPARCoutPATH could not be synchronized
 0 - synchronization not configured
 1 - out of sync - running master mode
 2 - in sync - running  mastermode
 3 - in sync - running slave mode
 4 - in sync - running master mode (wait to reach state 2)
"
    ::= {ASSPARCoutPATH 5}

syncStatStrASSPARCoutPATH  OBJECT-TYPE
    SYNTAX      OCTET STRING
    MAX-ACCESS  read-only
    STATUS      current
    DESCRIPTION
"
synchronization status line from file assp_sync.cfg for ASSPARCoutPATH
 0 - synchronization not configured
 1 - out of sync - running master mode
 2 - in sync - running  mastermode
 3 - in sync - running slave mode
 4 - in sync - running master mode (wait to reach state 2)
"
    ::= {ASSPARCoutPATH 6}

ASSPARCLog  OBJECT-TYPE
    SYNTAX      OCTET STRING
    MAX-ACCESS  read-write
    STATUS      current
    DESCRIPTION
"

"
    REFERENCE "Enable Plugin logging"
    DEFVAL { "1" }
    ::= {ASSPARCPlugin 11004}

syncStatASSPARCLog  OBJECT-TYPE
    SYNTAX      OCTET STRING
    MAX-ACCESS  read-only
    STATUS      current
    DESCRIPTION
"
synchronization status for ASSPARCLog
-1 - ASSPARCLog could not be synchronized
 0 - synchronization not configured
 1 - out of sync - running master mode
 2 - in sync - running  mastermode
 3 - in sync - running slave mode
 4 - in sync - running master mode (wait to reach state 2)
"
    ::= {ASSPARCLog 5}

syncStatStrASSPARCLog  OBJECT-TYPE
    SYNTAX      OCTET STRING
    MAX-ACCESS  read-only
    STATUS      current
    DESCRIPTION
"
synchronization status line from file assp_sync.cfg for ASSPARCLog
 0 - synchronization not configured
 1 - out of sync - running master mode
 2 - in sync - running  mastermode
 3 - in sync - running slave mode
 4 - in sync - running master mode (wait to reach state 2)
"
    ::= {ASSPARCLog 6}

ASSPARCSelectCode  OBJECT-TYPE
    SYNTAX      OCTET STRING
    MAX-ACCESS  read-write
    STATUS      current
    DESCRIPTION
"
Put a code line here, to detect messages that you want to archive (or not). The code line has to return 0 or 1. A return of 1 will start archiving.
  for example:
  return $this->{signed} ? 1 : 0;
  This code line will switch on archiving for all digital signed messages.
  if ($this->{relayok} && ! $this->{isbounce}) {return 1;} else {return 0;}
  This code line will switch on archiving for all outgoing not bounce messages.
  if ($this->{ispip} && $this->{cip} =~ /^193\.2\.1\./) {return 1;} else {return 0;}
  This code line will switch on archiving if the messages is from ISP and the IP of the server that was connected to the ISP begins with 193.2.1. .
  sample detection switches are:
  - $this->{relayok} - 1 = outgoing
  - $this->{noprocessing} 1 = noprocessing
  - $this->{whitelisted} 1 = whitelisted
  - $this->{isbounce} 1 = bounced message
  - $this->{signed} 1 = digital signed
  - $this->{ispip} 1 = comes from an ISP
  - $this->{spamfound} 1 = 'SPAM-found' flag is set
  - $this->{error} 1 = blocked message
  To use this option, you need to know the internal ASSP variables and there usage!
"
    REFERENCE "Run this Code to select Messages"
    DEFVAL { "" }
    ::= {ASSPARCPlugin 11005}

syncStatASSPARCSelectCode  OBJECT-TYPE
    SYNTAX      OCTET STRING
    MAX-ACCESS  read-only
    STATUS      current
    DESCRIPTION
"
synchronization status for ASSPARCSelectCode
-1 - ASSPARCSelectCode could not be synchronized
 0 - synchronization not configured
 1 - out of sync - running master mode
 2 - in sync - running  mastermode
 3 - in sync - running slave mode
 4 - in sync - running master mode (wait to reach state 2)
"
    ::= {ASSPARCSelectCode 5}

syncStatStrASSPARCSelectCode  OBJECT-TYPE
    SYNTAX      OCTET STRING
    MAX-ACCESS  read-only
    STATUS      current
    DESCRIPTION
"
synchronization status line from file assp_sync.cfg for ASSPARCSelectCode
 0 - synchronization not configured
 1 - out of sync - running master mode
 2 - in sync - running  mastermode
 3 - in sync - running slave mode
 4 - in sync - running master mode (wait to reach state 2)
"
    ::= {ASSPARCSelectCode 6}

ASSPARCmyhost  OBJECT-TYPE
    SYNTAX      OCTET STRING
    MAX-ACCESS  read-write
    STATUS      current
    DESCRIPTION
"
The hostname or IP where a record is written for each archived file. The database and the tables must be already created. The type and length of each database field depends on your needs. Mappings between archive variables and database fields are done with the mapping file below! Leave this blank, if do not want to use a database.
"
    REFERENCE "database hostname or IP"
    DEFVAL { "" }
    ::= {ASSPARCPlugin 11007}

syncStatASSPARCmyhost  OBJECT-TYPE
    SYNTAX      OCTET STRING
    MAX-ACCESS  read-only
    STATUS      current
    DESCRIPTION
"
synchronization status for ASSPARCmyhost
-1 - ASSPARCmyhost could not be synchronized
 0 - synchronization not configured
 1 - out of sync - running master mode
 2 - in sync - running  mastermode
 3 - in sync - running slave mode
 4 - in sync - running master mode (wait to reach state 2)
"
    ::= {ASSPARCmyhost 5}

syncStatStrASSPARCmyhost  OBJECT-TYPE
    SYNTAX      OCTET STRING
    MAX-ACCESS  read-only
    STATUS      current
    DESCRIPTION
"
synchronization status line from file assp_sync.cfg for ASSPARCmyhost
 0 - synchronization not configured
 1 - out of sync - running master mode
 2 - in sync - running  mastermode
 3 - in sync - running slave mode
 4 - in sync - running master mode (wait to reach state 2)
"
    ::= {ASSPARCmyhost 6}

ASSPARCDBdriver  OBJECT-TYPE
    SYNTAX      OCTET STRING
    MAX-ACCESS  read-write
    STATUS      current
    DESCRIPTION
"
The database driver used to access your database - DBD-driver. The following drivers are available on your system:
  BerkeleyDB, ADO, AnyData, CSV, DBM, ExampleP, File, Gofer, LDAP, Log, MVS_FTPSQL, Mock, Multiplex, ODBC, Oracle, Ovrimos, Pg, PgPP, Proxy, SQLite, Sponge, Sprite, Template, TemplateSS, mysql, mysqlPP
  If you can not find the driver for your database in this list, you should install it via cpan or ppm!
  -  or if you have installed an ODBC-driver for your database and DBD-ODBC, just create a DSN and use ODBC.
  Usefull are ADO|DB2|Informix|ODBC|Oracle|Pg|Sybase|mysql|mysqlPP - but any other SQL compatible database should also work.
  syntax examples: driver,option1,option2,...,...
  ADO,[DSN=mydsn]
  DB2
  Informix
  ODBC,DSN=mydsn|driver={SQL Server},Server=server_name
  Oracle,SID=1|INSTANCE_NAME=myinstance|SERVER=myserver|SERVICE_NAME=myservice_name,[PORT=myport]
  Pg,[PORT=myport]
  Sybase,SERVER=myserver,[PORT=myport]
  mysql,[PORT=myport]
  mysqlPP,[PORT=myport]
  The options for all drivers and there possible or required order depending on the used DBD-driver, please read the drivers documentation, if you do not know the needed option.
  The username, password, host and databasename are always used from this configuration page.
  Leave this blank, if do not want to use a database.
"
    REFERENCE "database driver name"
    DEFVAL { "" }
    ::= {ASSPARCPlugin 11008}

syncStatASSPARCDBdriver  OBJECT-TYPE
    SYNTAX      OCTET STRING
    MAX-ACCESS  read-only
    STATUS      current
    DESCRIPTION
"
synchronization status for ASSPARCDBdriver
-1 - ASSPARCDBdriver could not be synchronized
 0 - synchronization not configured
 1 - out of sync - running master mode
 2 - in sync - running  mastermode
 3 - in sync - running slave mode
 4 - in sync - running master mode (wait to reach state 2)
"
    ::= {ASSPARCDBdriver 5}

syncStatStrASSPARCDBdriver  OBJECT-TYPE
    SYNTAX      OCTET STRING
    MAX-ACCESS  read-only
    STATUS      current
    DESCRIPTION
"
synchronization status line from file assp_sync.cfg for ASSPARCDBdriver
 0 - synchronization not configured
 1 - out of sync - running master mode
 2 - in sync - running  mastermode
 3 - in sync - running slave mode
 4 - in sync - running master mode (wait to reach state 2)
"
    ::= {ASSPARCDBdriver 6}

ASSPARCmydb  OBJECT-TYPE
    SYNTAX      OCTET STRING
    MAX-ACCESS  read-write
    STATUS      current
    DESCRIPTION
"
This database must exist before archiving is started.  Leave this blank, if do not want to use a database.
"
    REFERENCE "database name"
    DEFVAL { "" }
    ::= {ASSPARCPlugin 11009}

syncStatASSPARCmydb  OBJECT-TYPE
    SYNTAX      OCTET STRING
    MAX-ACCESS  read-only
    STATUS      current
    DESCRIPTION
"
synchronization status for ASSPARCmydb
-1 - ASSPARCmydb could not be synchronized
 0 - synchronization not configured
 1 - out of sync - running master mode
 2 - in sync - running  mastermode
 3 - in sync - running slave mode
 4 - in sync - running master mode (wait to reach state 2)
"
    ::= {ASSPARCmydb 5}

syncStatStrASSPARCmydb  OBJECT-TYPE
    SYNTAX      OCTET STRING
    MAX-ACCESS  read-only
    STATUS      current
    DESCRIPTION
"
synchronization status line from file assp_sync.cfg for ASSPARCmydb
 0 - synchronization not configured
 1 - out of sync - running master mode
 2 - in sync - running  mastermode
 3 - in sync - running slave mode
 4 - in sync - running master mode (wait to reach state 2)
"
    ::= {ASSPARCmydb 6}

ASSPARCmytable  OBJECT-TYPE
    SYNTAX      OCTET STRING
    MAX-ACCESS  read-write
    STATUS      current
    DESCRIPTION
"
This table must exist before archiving is started.  Leave this blank, if do not want to use a database.
"
    REFERENCE "database table name"
    DEFVAL { "" }
    ::= {ASSPARCPlugin 11010}

syncStatASSPARCmytable  OBJECT-TYPE
    SYNTAX      OCTET STRING
    MAX-ACCESS  read-only
    STATUS      current
    DESCRIPTION
"
synchronization status for ASSPARCmytable
-1 - ASSPARCmytable could not be synchronized
 0 - synchronization not configured
 1 - out of sync - running master mode
 2 - in sync - running  mastermode
 3 - in sync - running slave mode
 4 - in sync - running master mode (wait to reach state 2)
"
    ::= {ASSPARCmytable 5}

syncStatStrASSPARCmytable  OBJECT-TYPE
    SYNTAX      OCTET STRING
    MAX-ACCESS  read-only
    STATUS      current
    DESCRIPTION
"
synchronization status line from file assp_sync.cfg for ASSPARCmytable
 0 - synchronization not configured
 1 - out of sync - running master mode
 2 - in sync - running  mastermode
 3 - in sync - running slave mode
 4 - in sync - running master mode (wait to reach state 2)
"
    ::= {ASSPARCmytable 6}

ASSPARCmyuser  OBJECT-TYPE
    SYNTAX      OCTET STRING
    MAX-ACCESS  read-write
    STATUS      current
    DESCRIPTION
"
This user should have CREATE privilege on the database. Leave this blank, if do not want to use a database.
"
    REFERENCE "database username"
    DEFVAL { "" }
    ::= {ASSPARCPlugin 11011}

syncStatASSPARCmyuser  OBJECT-TYPE
    SYNTAX      OCTET STRING
    MAX-ACCESS  read-only
    STATUS      current
    DESCRIPTION
"
synchronization status for ASSPARCmyuser
-1 - ASSPARCmyuser could not be synchronized
 0 - synchronization not configured
 1 - out of sync - running master mode
 2 - in sync - running  mastermode
 3 - in sync - running slave mode
 4 - in sync - running master mode (wait to reach state 2)
"
    ::= {ASSPARCmyuser 5}

syncStatStrASSPARCmyuser  OBJECT-TYPE
    SYNTAX      OCTET STRING
    MAX-ACCESS  read-only
    STATUS      current
    DESCRIPTION
"
synchronization status line from file assp_sync.cfg for ASSPARCmyuser
 0 - synchronization not configured
 1 - out of sync - running master mode
 2 - in sync - running  mastermode
 3 - in sync - running slave mode
 4 - in sync - running master mode (wait to reach state 2)
"
    ::= {ASSPARCmyuser 6}

ASSPARCmypassword  OBJECT-TYPE
    SYNTAX      OCTET STRING
    MAX-ACCESS  read-write
    STATUS      current
    DESCRIPTION
"

"
    REFERENCE "database password"
    DEFVAL { "" }
    ::= {ASSPARCPlugin 11012}

syncStatASSPARCmypassword  OBJECT-TYPE
    SYNTAX      OCTET STRING
    MAX-ACCESS  read-only
    STATUS      current
    DESCRIPTION
"
synchronization status for ASSPARCmypassword
-1 - ASSPARCmypassword could not be synchronized
 0 - synchronization not configured
 1 - out of sync - running master mode
 2 - in sync - running  mastermode
 3 - in sync - running slave mode
 4 - in sync - running master mode (wait to reach state 2)
"
    ::= {ASSPARCmypassword 5}

syncStatStrASSPARCmypassword  OBJECT-TYPE
    SYNTAX      OCTET STRING
    MAX-ACCESS  read-only
    STATUS      current
    DESCRIPTION
"
synchronization status line from file assp_sync.cfg for ASSPARCmypassword
 0 - synchronization not configured
 1 - out of sync - running master mode
 2 - in sync - running  mastermode
 3 - in sync - running slave mode
 4 - in sync - running master mode (wait to reach state 2)
"
    ::= {ASSPARCmypassword 6}

ASSPARCfieldMap  OBJECT-TYPE
    SYNTAX      OCTET STRING
    MAX-ACCESS  read-write
    STATUS      current
    DESCRIPTION
"
The file which contains the field mapping table DB-field => ArchiveVariable . If set, the value has to begin with   file:   ! Leave this blank, if do not want to use a database.
"
    REFERENCE "DB field mapping file*"
    DEFVAL { "files/arc_default_map_file.txt" }
    ::= {ASSPARCPlugin 11013}

syncStatASSPARCfieldMap  OBJECT-TYPE
    SYNTAX      OCTET STRING
    MAX-ACCESS  read-only
    STATUS      current
    DESCRIPTION
"
synchronization status for ASSPARCfieldMap
-1 - ASSPARCfieldMap could not be synchronized
 0 - synchronization not configured
 1 - out of sync - running master mode
 2 - in sync - running  mastermode
 3 - in sync - running slave mode
 4 - in sync - running master mode (wait to reach state 2)
"
    ::= {ASSPARCfieldMap 5}

syncStatStrASSPARCfieldMap  OBJECT-TYPE
    SYNTAX      OCTET STRING
    MAX-ACCESS  read-only
    STATUS      current
    DESCRIPTION
"
synchronization status line from file assp_sync.cfg for ASSPARCfieldMap
 0 - synchronization not configured
 1 - out of sync - running master mode
 2 - in sync - running  mastermode
 3 - in sync - running slave mode
 4 - in sync - running master mode (wait to reach state 2)
"
    ::= {ASSPARCfieldMap 6}

ASSPDCCPlugin  OBJECT IDENTIFIER ::= {asspConfig 43}
DoASSPDCC  OBJECT-TYPE
    SYNTAX      OCTET STRING
    MAX-ACCESS  read-write
    STATUS      current
    DESCRIPTION
"
This Plugin uses a service provided by www.rhyolite.com to detect spam on a statistical (checksum) base.
 You have to open UDP port 6277 on your firewall for outgoing connections and dccifd must be installed an running. This port is used by dccifd to connect to the DCC-Servers.
 Please notice that dccifd is not available on windows systems. To use DCC on windows you must install the DCC components on a second linux system and you have to configure ASSP_DCCdccifd to use an IP socket to connect to the dccifd. Please follow the installation instructions on 
 DCC is a distributed, collaborative, spam detection and filtering network. Through user contribution, DCC establishes a distributed and constantly updating catalogue of spam in propagation that is consulted by email clients to filter out known spam. Detection is done with statistical signatures that efficiently spot mutating spam content. User input is validated through reputation assignments based on consensus on report and revoke assertions which in turn is used for computing confidence values associated with individual signatures.
 This plugin is designed for- and running in call/run level 'complete mail'!
"
    REFERENCE "Do the ASSP_DCC Plugin"
    DEFVAL { "0" }
    ::= {ASSPDCCPlugin 15000}

ASSPDCCPriority  OBJECT-TYPE
    SYNTAX      OCTET STRING
    MAX-ACCESS  read-write
    STATUS      current
    DESCRIPTION
"
Sets the priority of this Plugin within the call/run-level 'complete mail'. The Plugin with the lowest priority value is processed first!
"
    REFERENCE "the priority of the Plugin"
    DEFVAL { "8" }
    ::= {ASSPDCCPlugin 15001}

TestASSPDCC  OBJECT-TYPE
    SYNTAX      OCTET STRING
    MAX-ACCESS  read-write
    STATUS      current
    DESCRIPTION
"
Set this Plugin in to Testmode. The Plugin returns true in any case!
"
    REFERENCE "Set the Plugin in Testmode"
    DEFVAL { "" }
    ::= {ASSPDCCPlugin 15002}

ASSPDCCLog  OBJECT-TYPE
    SYNTAX      OCTET STRING
    MAX-ACCESS  read-write
    STATUS      current
    DESCRIPTION
"

"
    REFERENCE "Enable Plugin logging"
    DEFVAL { "1" }
    ::= {ASSPDCCPlugin 15003}

ASSPDCCValencePB  OBJECT-TYPE
    SYNTAX      OCTET STRING
    MAX-ACCESS  read-write
    STATUS      current
    DESCRIPTION
"
Message scoring for ASSP_DCC Plugin
"
    REFERENCE "PenaltyBox valance for ASSP_DCC Plugin +"
    DEFVAL { "15" }
    ::= {ASSPDCCPlugin 15004}

procWhiteASSPDCC  OBJECT-TYPE
    SYNTAX      OCTET STRING
    MAX-ACCESS  read-write
    STATUS      current
    DESCRIPTION
"
Whitelisted mails will be processed by this Plugin!
"
    REFERENCE "process whitlisted mails"
    DEFVAL { "1" }
    ::= {ASSPDCCPlugin 15005}

ASSPDCCLogTo  OBJECT-TYPE
    SYNTAX      OCTET STRING
    MAX-ACCESS  read-write
    STATUS      current
    DESCRIPTION
"
Where to store rejected mail for this Plugin. Recommended: spamfolder &amp; ccallspam 1 = spamfolder, 2 = notspam folder, 3 = spamfolder &amp; ccallspam, 4 = mailok folder, 5 = attachment folder, 6 = discard, 7 = discard &amp; ccallspam.
"
    REFERENCE "location to log the failed mails"
    DEFVAL { "3" }
    ::= {ASSPDCCPlugin 15006}

ASSPDCChomedir  OBJECT-TYPE
    SYNTAX      OCTET STRING
    MAX-ACCESS  read-write
    STATUS      current
    DESCRIPTION
"
The home Directory of DCC on linux systems. dccifd will listen on a unix socket in this folder. This parameter will be ignored if ASSP_DCCdccifd is configured!
"
    REFERENCE "Home Directory of DCC on linux"
    DEFVAL { "/var/dcc" }
    ::= {ASSPDCCPlugin 15007}

ASSPDCCdccifd  OBJECT-TYPE
    SYNTAX      OCTET STRING
    MAX-ACCESS  read-write
    STATUS      current
    DESCRIPTION
"
If you are running dccifd on a second system, define the IP address or hostname and port of that daemon here. For example: 192.168.0.100:11111 or dccifd.mydomain.com:11111 . If this parameter is configured, the setting of ASSP_DCChomedir will be ignored!
"
    REFERENCE "dccifd IP/Host Information"
    DEFVAL { "" }
    ::= {ASSPDCCPlugin 15008}

ASSPDCCTimeout  OBJECT-TYPE
    SYNTAX      OCTET STRING
    MAX-ACCESS  read-write
    STATUS      current
    DESCRIPTION
"
Define the maximum time in seconds, assp will wait for an Answer of the dccifd. Recommended setting are between 10 an 16 - default is 16 seconds.
"
    REFERENCE "dccifd Socket Timeout"
    DEFVAL { "16" }
    ::= {ASSPDCCPlugin 15009}

ASSPDCCClientIP  OBJECT-TYPE
    SYNTAX      OCTET STRING
    MAX-ACCESS  read-write
    STATUS      current
    DESCRIPTION
"
Define the IP address that is used to authenticate assp at the dccifd here.
"
    REFERENCE "DCC Auth Client IP"
    DEFVAL { "" }
    ::= {ASSPDCCPlugin 15010}

ASSPDCCClientName  OBJECT-TYPE
    SYNTAX      OCTET STRING
    MAX-ACCESS  read-write
    STATUS      current
    DESCRIPTION
"
Define the hostname that is used to authenticate assp at the dccifd here.
"
    REFERENCE "DCC Auth Client Name"
    DEFVAL { "" }
    ::= {ASSPDCCPlugin 15011}

ASSPDCCReportToDCC  OBJECT-TYPE
    SYNTAX      OCTET STRING
    MAX-ACCESS  read-write
    STATUS      current
    DESCRIPTION
"
Define how the reporting function of DCC should be used. If set to 'query only' - no reporting is be done. If set to 'report' of the current DCC result will be reported to the DCC servers. If set to 'report and known spam' the same behavior like 'report' belongs and additionaly - if the mail is still detected as SPAM by assp, this will be reported to the DCC servers.
"
    REFERENCE "Report to DCC-Server"
    DEFVAL { "0" }
    ::= {ASSPDCCPlugin 15012}

ASSPOCRPlugin  OBJECT IDENTIFIER ::= {asspConfig 44}
DoASSPOCR  OBJECT-TYPE
    SYNTAX      OCTET STRING
    MAX-ACCESS  read-write
    STATUS      current
    DESCRIPTION
"
This Plugin resolves the ASCII part of attached images.
 This Plugin is designed for- and running in call/run level 'complete mail'!
"
    REFERENCE "Do the ASSP_OCR Plugin"
    DEFVAL { "2" }
    ::= {ASSPOCRPlugin 12000}

syncStatDoASSPOCR  OBJECT-TYPE
    SYNTAX      OCTET STRING
    MAX-ACCESS  read-only
    STATUS      current
    DESCRIPTION
"
synchronization status for DoASSPOCR
-1 - DoASSPOCR could not be synchronized
 0 - synchronization not configured
 1 - out of sync - running master mode
 2 - in sync - running  mastermode
 3 - in sync - running slave mode
 4 - in sync - running master mode (wait to reach state 2)
"
    ::= {DoASSPOCR 5}

syncStatStrDoASSPOCR  OBJECT-TYPE
    SYNTAX      OCTET STRING
    MAX-ACCESS  read-only
    STATUS      current
    DESCRIPTION
"
synchronization status line from file assp_sync.cfg for DoASSPOCR
 0 - synchronization not configured
 1 - out of sync - running master mode
 2 - in sync - running  mastermode
 3 - in sync - running slave mode
 4 - in sync - running master mode (wait to reach state 2)
"
    ::= {DoASSPOCR 6}

ASSPOCRPriority  OBJECT-TYPE
    SYNTAX      OCTET STRING
    MAX-ACCESS  read-write
    STATUS      current
    DESCRIPTION
"
Sets the priority of this Plugin within the call/run-level 'complete mail'. The Plugin with the lowest priority value is processed first!
"
    REFERENCE "the priority of the Plugin"
    DEFVAL { "5" }
    ::= {ASSPOCRPlugin 12001}

syncStatASSPOCRPriority  OBJECT-TYPE
    SYNTAX      OCTET STRING
    MAX-ACCESS  read-only
    STATUS      current
    DESCRIPTION
"
synchronization status for ASSPOCRPriority
-1 - ASSPOCRPriority could not be synchronized
 0 - synchronization not configured
 1 - out of sync - running master mode
 2 - in sync - running  mastermode
 3 - in sync - running slave mode
 4 - in sync - running master mode (wait to reach state 2)
"
    ::= {ASSPOCRPriority 5}

syncStatStrASSPOCRPriority  OBJECT-TYPE
    SYNTAX      OCTET STRING
    MAX-ACCESS  read-only
    STATUS      current
    DESCRIPTION
"
synchronization status line from file assp_sync.cfg for ASSPOCRPriority
 0 - synchronization not configured
 1 - out of sync - running master mode
 2 - in sync - running  mastermode
 3 - in sync - running slave mode
 4 - in sync - running master mode (wait to reach state 2)
"
    ::= {ASSPOCRPriority 6}

ASSPOCRLog  OBJECT-TYPE
    SYNTAX      OCTET STRING
    MAX-ACCESS  read-write
    STATUS      current
    DESCRIPTION
"

"
    REFERENCE "Enable Plugin logging"
    DEFVAL { "1" }
    ::= {ASSPOCRPlugin 12002}

syncStatASSPOCRLog  OBJECT-TYPE
    SYNTAX      OCTET STRING
    MAX-ACCESS  read-only
    STATUS      current
    DESCRIPTION
"
synchronization status for ASSPOCRLog
-1 - ASSPOCRLog could not be synchronized
 0 - synchronization not configured
 1 - out of sync - running master mode
 2 - in sync - running  mastermode
 3 - in sync - running slave mode
 4 - in sync - running master mode (wait to reach state 2)
"
    ::= {ASSPOCRLog 5}

syncStatStrASSPOCRLog  OBJECT-TYPE
    SYNTAX      OCTET STRING
    MAX-ACCESS  read-only
    STATUS      current
    DESCRIPTION
"
synchronization status line from file assp_sync.cfg for ASSPOCRLog
 0 - synchronization not configured
 1 - out of sync - running master mode
 2 - in sync - running  mastermode
 3 - in sync - running slave mode
 4 - in sync - running master mode (wait to reach state 2)
"
    ::= {ASSPOCRLog 6}

procWhiteASSPOCR  OBJECT-TYPE
    SYNTAX      OCTET STRING
    MAX-ACCESS  read-write
    STATUS      current
    DESCRIPTION
"
Whitelisted mails will be processed by this Plugin!
"
    REFERENCE "process whitelisted mails"
    DEFVAL { "1" }
    ::= {ASSPOCRPlugin 12003}

syncStatprocWhiteASSPOCR  OBJECT-TYPE
    SYNTAX      OCTET STRING
    MAX-ACCESS  read-only
    STATUS      current
    DESCRIPTION
"
synchronization status for procWhiteASSPOCR
-1 - procWhiteASSPOCR could not be synchronized
 0 - synchronization not configured
 1 - out of sync - running master mode
 2 - in sync - running  mastermode
 3 - in sync - running slave mode
 4 - in sync - running master mode (wait to reach state 2)
"
    ::= {procWhiteASSPOCR 5}

syncStatStrprocWhiteASSPOCR  OBJECT-TYPE
    SYNTAX      OCTET STRING
    MAX-ACCESS  read-only
    STATUS      current
    DESCRIPTION
"
synchronization status line from file assp_sync.cfg for procWhiteASSPOCR
 0 - synchronization not configured
 1 - out of sync - running master mode
 2 - in sync - running  mastermode
 3 - in sync - running slave mode
 4 - in sync - running master mode (wait to reach state 2)
"
    ::= {procWhiteASSPOCR 6}

DoPDFTextASSPOCR  OBJECT-TYPE
    SYNTAX      OCTET STRING
    MAX-ACCESS  read-write
    STATUS      current
    DESCRIPTION
"
The text components of attached pdf files will be extracted!
"
    REFERENCE "extract text from pdf files"
    DEFVAL { "1" }
    ::= {ASSPOCRPlugin 12004}

syncStatDoPDFTextASSPOCR  OBJECT-TYPE
    SYNTAX      OCTET STRING
    MAX-ACCESS  read-only
    STATUS      current
    DESCRIPTION
"
synchronization status for DoPDFTextASSPOCR
-1 - DoPDFTextASSPOCR could not be synchronized
 0 - synchronization not configured
 1 - out of sync - running master mode
 2 - in sync - running  mastermode
 3 - in sync - running slave mode
 4 - in sync - running master mode (wait to reach state 2)
"
    ::= {DoPDFTextASSPOCR 5}

syncStatStrDoPDFTextASSPOCR  OBJECT-TYPE
    SYNTAX      OCTET STRING
    MAX-ACCESS  read-only
    STATUS      current
    DESCRIPTION
"
synchronization status line from file assp_sync.cfg for DoPDFTextASSPOCR
 0 - synchronization not configured
 1 - out of sync - running master mode
 2 - in sync - running  mastermode
 3 - in sync - running slave mode
 4 - in sync - running master mode (wait to reach state 2)
"
    ::= {DoPDFTextASSPOCR 6}

DoPDFImageASSPOCR  OBJECT-TYPE
    SYNTAX      OCTET STRING
    MAX-ACCESS  read-write
    STATUS      current
    DESCRIPTION
"
The text components of images insite of attached pdf files will be extracted!
"
    REFERENCE "extract text from images insite pdf files"
    DEFVAL { "1" }
    ::= {ASSPOCRPlugin 12005}

syncStatDoPDFImageASSPOCR  OBJECT-TYPE
    SYNTAX      OCTET STRING
    MAX-ACCESS  read-only
    STATUS      current
    DESCRIPTION
"
synchronization status for DoPDFImageASSPOCR
-1 - DoPDFImageASSPOCR could not be synchronized
 0 - synchronization not configured
 1 - out of sync - running master mode
 2 - in sync - running  mastermode
 3 - in sync - running slave mode
 4 - in sync - running master mode (wait to reach state 2)
"
    ::= {DoPDFImageASSPOCR 5}

syncStatStrDoPDFImageASSPOCR  OBJECT-TYPE
    SYNTAX      OCTET STRING
    MAX-ACCESS  read-only
    STATUS      current
    DESCRIPTION
"
synchronization status line from file assp_sync.cfg for DoPDFImageASSPOCR
 0 - synchronization not configured
 1 - out of sync - running master mode
 2 - in sync - running  mastermode
 3 - in sync - running slave mode
 4 - in sync - running master mode (wait to reach state 2)
"
    ::= {DoPDFImageASSPOCR 6}

DoImageASSPOCR  OBJECT-TYPE
    SYNTAX      OCTET STRING
    MAX-ACCESS  read-write
    STATUS      current
    DESCRIPTION
"
The text components of attached images be extracted!
"
    REFERENCE "extract text from attached image files"
    DEFVAL { "1" }
    ::= {ASSPOCRPlugin 12006}

syncStatDoImageASSPOCR  OBJECT-TYPE
    SYNTAX      OCTET STRING
    MAX-ACCESS  read-only
    STATUS      current
    DESCRIPTION
"
synchronization status for DoImageASSPOCR
-1 - DoImageASSPOCR could not be synchronized
 0 - synchronization not configured
 1 - out of sync - running master mode
 2 - in sync - running  mastermode
 3 - in sync - running slave mode
 4 - in sync - running master mode (wait to reach state 2)
"
    ::= {DoImageASSPOCR 5}

syncStatStrDoImageASSPOCR  OBJECT-TYPE
    SYNTAX      OCTET STRING
    MAX-ACCESS  read-only
    STATUS      current
    DESCRIPTION
"
synchronization status line from file assp_sync.cfg for DoImageASSPOCR
 0 - synchronization not configured
 1 - out of sync - running master mode
 2 - in sync - running  mastermode
 3 - in sync - running slave mode
 4 - in sync - running master mode (wait to reach state 2)
"
    ::= {DoImageASSPOCR 6}

ASSPOCRExec  OBJECT-TYPE
    SYNTAX      OCTET STRING
    MAX-ACCESS  read-write
    STATUS      current
    DESCRIPTION
"
The full path to the ImageMagick executable (convert). For example: c:/progams/ImageMagick/convert or /opt/ImageMagick/convert .
 If not defined, ASSP will search for this executable and set this value automaticly, if any of the both Image options is set.
 The path to ImageMagic must be defined in the systems PATH variable!
 If the executable was not found, this value will be set to 'convert not found in path'. In this case set your systems PATH variable correct, restart ASSP and clear this value - ASSP will then retry to find convert!
"
    REFERENCE "Full Path to ImageMagick Executable"
    DEFVAL { "" }
    ::= {ASSPOCRPlugin 12007}

syncStatASSPOCRExec  OBJECT-TYPE
    SYNTAX      OCTET STRING
    MAX-ACCESS  read-only
    STATUS      current
    DESCRIPTION
"
synchronization status for ASSPOCRExec
-1 - ASSPOCRExec could not be synchronized
 0 - synchronization not configured
 1 - out of sync - running master mode
 2 - in sync - running  mastermode
 3 - in sync - running slave mode
 4 - in sync - running master mode (wait to reach state 2)
"
    ::= {ASSPOCRExec 5}

syncStatStrASSPOCRExec  OBJECT-TYPE
    SYNTAX      OCTET STRING
    MAX-ACCESS  read-only
    STATUS      current
    DESCRIPTION
"
synchronization status line from file assp_sync.cfg for ASSPOCRExec
 0 - synchronization not configured
 1 - out of sync - running master mode
 2 - in sync - running  mastermode
 3 - in sync - running slave mode
 4 - in sync - running master mode (wait to reach state 2)
"
    ::= {ASSPOCRExec 6}

ASSPOCRocrmaxsize  OBJECT-TYPE
    SYNTAX      OCTET STRING
    MAX-ACCESS  read-write
    STATUS      current
    DESCRIPTION
"
The maximum size of the converted images to scan with tesseract - default is 1024000
"
    REFERENCE "maxsize of the converted images"
    DEFVAL { "1024000" }
    ::= {ASSPOCRPlugin 12008}

syncStatASSPOCRocrmaxsize  OBJECT-TYPE
    SYNTAX      OCTET STRING
    MAX-ACCESS  read-only
    STATUS      current
    DESCRIPTION
"
synchronization status for ASSPOCRocrmaxsize
-1 - ASSPOCRocrmaxsize could not be synchronized
 0 - synchronization not configured
 1 - out of sync - running master mode
 2 - in sync - running  mastermode
 3 - in sync - running slave mode
 4 - in sync - running master mode (wait to reach state 2)
"
    ::= {ASSPOCRocrmaxsize 5}

syncStatStrASSPOCRocrmaxsize  OBJECT-TYPE
    SYNTAX      OCTET STRING
    MAX-ACCESS  read-only
    STATUS      current
    DESCRIPTION
"
synchronization status line from file assp_sync.cfg for ASSPOCRocrmaxsize
 0 - synchronization not configured
 1 - out of sync - running master mode
 2 - in sync - running  mastermode
 3 - in sync - running slave mode
 4 - in sync - running master mode (wait to reach state 2)
"
    ::= {ASSPOCRocrmaxsize 6}

ASSPOCRocrmaxprocesses  OBJECT-TYPE
    SYNTAX      OCTET STRING
    MAX-ACCESS  read-write
    STATUS      current
    DESCRIPTION
"
The maximum number of concurrent running image processing tasks (tesseract / convert). This number should be less than the number of available CPU cores - default is 3. Changing this value requires an ASSP restart!
"
    REFERENCE "maximum number of allowed concurrent running image processing tasks"
    DEFVAL { "3" }
    ::= {ASSPOCRPlugin 12009}

ASSPRazorPlugin  OBJECT IDENTIFIER ::= {asspConfig 45}
DoASSPRazor  OBJECT-TYPE
    SYNTAX      OCTET STRING
    MAX-ACCESS  read-write
    STATUS      current
    DESCRIPTION
"
This Plugin uses a service provided by www.cloudmark.com to detect spam on a statistical base.
 You have to open port 2703 on your firewall for outgoing connections. This port is used by Razor to connect to the Razor-Servers.
 Razor is a distributed, collaborative, spam detection and filtering network. Through user contribution, Razor establishes a distributed and constantly updating catalogue of spam in propagation that is consulted by email clients to filter out known spam. Detection is done with statistical and randomized signatures that efficiently spot mutating spam content. User input is validated through reputation assignments based on consensus on report and revoke assertions which in turn is used for computing confidence values associated with individual signatures.
 This plugin is designed for- and running in call/run level 'complete mail'!
"
    REFERENCE "Do the ASSP_Razor Plugin"
    DEFVAL { "0" }
    ::= {ASSPRazorPlugin 14000}

ASSPRazorPriority  OBJECT-TYPE
    SYNTAX      OCTET STRING
    MAX-ACCESS  read-write
    STATUS      current
    DESCRIPTION
"
Sets the priority of this Plugin within the call/run-level 'complete mail'. The Plugin with the lowest priority value is processed first!
"
    REFERENCE "the priority of the Plugin"
    DEFVAL { "7" }
    ::= {ASSPRazorPlugin 14002}

TestASSPRazor  OBJECT-TYPE
    SYNTAX      OCTET STRING
    MAX-ACCESS  read-write
    STATUS      current
    DESCRIPTION
"
Set this Plugin in to Testmode. The Plugin returns true in any case!
"
    REFERENCE "Set the Plugin in Testmode"
    DEFVAL { "0" }
    ::= {ASSPRazorPlugin 14003}

ASSPRazorLog  OBJECT-TYPE
    SYNTAX      OCTET STRING
    MAX-ACCESS  read-write
    STATUS      current
    DESCRIPTION
"

"
    REFERENCE "Enable Plugin logging"
    DEFVAL { "1" }
    ::= {ASSPRazorPlugin 14004}

procWhiteASSPRazor  OBJECT-TYPE
    SYNTAX      OCTET STRING
    MAX-ACCESS  read-write
    STATUS      current
    DESCRIPTION
"
Whitelisted mails will be processed by this Plugin!
"
    REFERENCE "process whitlisted mails"
    DEFVAL { "1" }
    ::= {ASSPRazorPlugin 14005}

ASSPRazorLogTo  OBJECT-TYPE
    SYNTAX      OCTET STRING
    MAX-ACCESS  read-write
    STATUS      current
    DESCRIPTION
"
Where to store rejected mail for this Plugin. Recommended: spamfolder &amp; ccallspam 1 = spamfolder, 2 = notspam folder, 3 = spamfolder &amp; ccallspam, 4 = mailok folder, 5 = attachment folder, 6 = discard, 7 = discard &amp; ccallspam.
"
    REFERENCE "location to log the failed mails"
    DEFVAL { "3" }
    ::= {ASSPRazorPlugin 14006}

ASSPRazorMaxNotSpamConf  OBJECT-TYPE
    SYNTAX      OCTET STRING
    MAX-ACCESS  read-write
    STATUS      current
    DESCRIPTION
"
The Razor-Server will return a confidence/spam level for each mail between 0 and 100, where 0 meens no spam and 100 absolute spam. Under default conditions Razor uses a pre calculated default value, but if you want, you can set this to an absolute value between 0 and 99 or a value relative to the default (use 'default-dd' or 'default+dd' without quotes - dd must be digits). If the Razor-score is higher than this value, the mail will consider spam. To use the default value (recommended), set the value to the word 'default'.
"
    REFERENCE "Maximum Confidence by Razor for NOT SPAM"
    DEFVAL { "default" }
    ::= {ASSPRazorPlugin 14007}

ASSPRazorValencePB  OBJECT-TYPE
    SYNTAX      OCTET STRING
    MAX-ACCESS  read-write
    STATUS      current
    DESCRIPTION
"
Message/IP scoring for ASSP_Razor Plugin
"
    REFERENCE "PenaltyBox valence for ASSP_Razor Plugin +"
    DEFVAL { "15" }
    ::= {ASSPRazorPlugin 14008}

ASSPFC  OBJECT-TYPE
    SYNTAX      OCTET STRING
    MAX-ACCESS  read-only
    STATUS      current
    DESCRIPTION
"
ASSP Perl module information for ASSP_FC;
"
    ::= {asspPerlModuleInfo 0}

iVASSPFC  OBJECT-TYPE
    SYNTAX      OCTET STRING
    MAX-ACCESS  read-only
    STATUS      current
    DESCRIPTION
"
installed module version
"
    ::= {ASSPFC 1}

rVASSPFC  OBJECT-TYPE
    SYNTAX      OCTET STRING
    MAX-ACCESS  read-only
    STATUS      current
    DESCRIPTION
"
required/recommended module version
"
    ::= {ASSPFC 2}

iSASSPFC  OBJECT-TYPE
    SYNTAX      OCTET STRING
    MAX-ACCESS  read-only
    STATUS      current
    DESCRIPTION
"
module installation status
"
    ::= {ASSPFC 3}

dUASSPFC  OBJECT-TYPE
    SYNTAX      OCTET STRING
    MAX-ACCESS  read-only
    STATUS      current
    DESCRIPTION
"
download URL for the module
"
    ::= {ASSPFC 4}

ASSPSVG  OBJECT-TYPE
    SYNTAX      OCTET STRING
    MAX-ACCESS  read-only
    STATUS      current
    DESCRIPTION
"
ASSP Perl module information for ASSP_SVG;
"
    ::= {asspPerlModuleInfo 1}

iVASSPSVG  OBJECT-TYPE
    SYNTAX      OCTET STRING
    MAX-ACCESS  read-only
    STATUS      current
    DESCRIPTION
"
installed module version
"
    ::= {ASSPSVG 1}

rVASSPSVG  OBJECT-TYPE
    SYNTAX      OCTET STRING
    MAX-ACCESS  read-only
    STATUS      current
    DESCRIPTION
"
required/recommended module version
"
    ::= {ASSPSVG 2}

iSASSPSVG  OBJECT-TYPE
    SYNTAX      OCTET STRING
    MAX-ACCESS  read-only
    STATUS      current
    DESCRIPTION
"
module installation status
"
    ::= {ASSPSVG 3}

dUASSPSVG  OBJECT-TYPE
    SYNTAX      OCTET STRING
    MAX-ACCESS  read-only
    STATUS      current
    DESCRIPTION
"
download URL for the module
"
    ::= {ASSPSVG 4}

ASSPWordStem  OBJECT-TYPE
    SYNTAX      OCTET STRING
    MAX-ACCESS  read-only
    STATUS      current
    DESCRIPTION
"
ASSP Perl module information for ASSP_WordStem;
"
    ::= {asspPerlModuleInfo 2}

iVASSPWordStem  OBJECT-TYPE
    SYNTAX      OCTET STRING
    MAX-ACCESS  read-only
    STATUS      current
    DESCRIPTION
"
installed module version
"
    ::= {ASSPWordStem 1}

rVASSPWordStem  OBJECT-TYPE
    SYNTAX      OCTET STRING
    MAX-ACCESS  read-only
    STATUS      current
    DESCRIPTION
"
required/recommended module version
"
    ::= {ASSPWordStem 2}

iSASSPWordStem  OBJECT-TYPE
    SYNTAX      OCTET STRING
    MAX-ACCESS  read-only
    STATUS      current
    DESCRIPTION
"
module installation status
"
    ::= {ASSPWordStem 3}

dUASSPWordStem  OBJECT-TYPE
    SYNTAX      OCTET STRING
    MAX-ACCESS  read-only
    STATUS      current
    DESCRIPTION
"
download URL for the module
"
    ::= {ASSPWordStem 4}

AsspSelfLoader  OBJECT-TYPE
    SYNTAX      OCTET STRING
    MAX-ACCESS  read-only
    STATUS      current
    DESCRIPTION
"
ASSP Perl module information for AsspSelfLoader;
"
    ::= {asspPerlModuleInfo 3}

iVAsspSelfLoader  OBJECT-TYPE
    SYNTAX      OCTET STRING
    MAX-ACCESS  read-only
    STATUS      current
    DESCRIPTION
"
installed module version
"
    ::= {AsspSelfLoader 1}

rVAsspSelfLoader  OBJECT-TYPE
    SYNTAX      OCTET STRING
    MAX-ACCESS  read-only
    STATUS      current
    DESCRIPTION
"
required/recommended module version
"
    ::= {AsspSelfLoader 2}

iSAsspSelfLoader  OBJECT-TYPE
    SYNTAX      OCTET STRING
    MAX-ACCESS  read-only
    STATUS      current
    DESCRIPTION
"
module installation status
"
    ::= {AsspSelfLoader 3}

dUAsspSelfLoader  OBJECT-TYPE
    SYNTAX      OCTET STRING
    MAX-ACCESS  read-only
    STATUS      current
    DESCRIPTION
"
download URL for the module
"
    ::= {AsspSelfLoader 4}

AuthenSASL  OBJECT-TYPE
    SYNTAX      OCTET STRING
    MAX-ACCESS  read-only
    STATUS      current
    DESCRIPTION
"
ASSP Perl module information for Authen::SASL;
"
    ::= {asspPerlModuleInfo 4}

iVAuthenSASL  OBJECT-TYPE
    SYNTAX      OCTET STRING
    MAX-ACCESS  read-only
    STATUS      current
    DESCRIPTION
"
installed module version
"
    ::= {AuthenSASL 1}

rVAuthenSASL  OBJECT-TYPE
    SYNTAX      OCTET STRING
    MAX-ACCESS  read-only
    STATUS      current
    DESCRIPTION
"
required/recommended module version
"
    ::= {AuthenSASL 2}

iSAuthenSASL  OBJECT-TYPE
    SYNTAX      OCTET STRING
    MAX-ACCESS  read-only
    STATUS      current
    DESCRIPTION
"
module installation status
"
    ::= {AuthenSASL 3}

dUAuthenSASL  OBJECT-TYPE
    SYNTAX      OCTET STRING
    MAX-ACCESS  read-only
    STATUS      current
    DESCRIPTION
"
download URL for the module
"
    ::= {AuthenSASL 4}

BerkeleyDB  OBJECT-TYPE
    SYNTAX      OCTET STRING
    MAX-ACCESS  read-only
    STATUS      current
    DESCRIPTION
"
ASSP Perl module information for BerkeleyDB;
"
    ::= {asspPerlModuleInfo 5}

iVBerkeleyDB  OBJECT-TYPE
    SYNTAX      OCTET STRING
    MAX-ACCESS  read-only
    STATUS      current
    DESCRIPTION
"
installed module version
"
    ::= {BerkeleyDB 1}

rVBerkeleyDB  OBJECT-TYPE
    SYNTAX      OCTET STRING
    MAX-ACCESS  read-only
    STATUS      current
    DESCRIPTION
"
required/recommended module version
"
    ::= {BerkeleyDB 2}

iSBerkeleyDB  OBJECT-TYPE
    SYNTAX      OCTET STRING
    MAX-ACCESS  read-only
    STATUS      current
    DESCRIPTION
"
module installation status
"
    ::= {BerkeleyDB 3}

dUBerkeleyDB  OBJECT-TYPE
    SYNTAX      OCTET STRING
    MAX-ACCESS  read-only
    STATUS      current
    DESCRIPTION
"
download URL for the module
"
    ::= {BerkeleyDB 4}

BerkeleyDBDBEngine  OBJECT-TYPE
    SYNTAX      OCTET STRING
    MAX-ACCESS  read-only
    STATUS      current
    DESCRIPTION
"
ASSP Perl module information for BerkeleyDB_DBEngine;
"
    ::= {asspPerlModuleInfo 6}

iVBerkeleyDBDBEngine  OBJECT-TYPE
    SYNTAX      OCTET STRING
    MAX-ACCESS  read-only
    STATUS      current
    DESCRIPTION
"
installed module version
"
    ::= {BerkeleyDBDBEngine 1}

rVBerkeleyDBDBEngine  OBJECT-TYPE
    SYNTAX      OCTET STRING
    MAX-ACCESS  read-only
    STATUS      current
    DESCRIPTION
"
required/recommended module version
"
    ::= {BerkeleyDBDBEngine 2}

iSBerkeleyDBDBEngine  OBJECT-TYPE
    SYNTAX      OCTET STRING
    MAX-ACCESS  read-only
    STATUS      current
    DESCRIPTION
"
module installation status
"
    ::= {BerkeleyDBDBEngine 3}

dUBerkeleyDBDBEngine  OBJECT-TYPE
    SYNTAX      OCTET STRING
    MAX-ACCESS  read-only
    STATUS      current
    DESCRIPTION
"
download URL for the module
"
    ::= {BerkeleyDBDBEngine 4}

CompressZlib  OBJECT-TYPE
    SYNTAX      OCTET STRING
    MAX-ACCESS  read-only
    STATUS      current
    DESCRIPTION
"
ASSP Perl module information for Compress::Zlib;
"
    ::= {asspPerlModuleInfo 7}

iVCompressZlib  OBJECT-TYPE
    SYNTAX      OCTET STRING
    MAX-ACCESS  read-only
    STATUS      current
    DESCRIPTION
"
installed module version
"
    ::= {CompressZlib 1}

rVCompressZlib  OBJECT-TYPE
    SYNTAX      OCTET STRING
    MAX-ACCESS  read-only
    STATUS      current
    DESCRIPTION
"
required/recommended module version
"
    ::= {CompressZlib 2}

iSCompressZlib  OBJECT-TYPE
    SYNTAX      OCTET STRING
    MAX-ACCESS  read-only
    STATUS      current
    DESCRIPTION
"
module installation status
"
    ::= {CompressZlib 3}

dUCompressZlib  OBJECT-TYPE
    SYNTAX      OCTET STRING
    MAX-ACCESS  read-only
    STATUS      current
    DESCRIPTION
"
download URL for the module
"
    ::= {CompressZlib 4}

ConvertTNEF  OBJECT-TYPE
    SYNTAX      OCTET STRING
    MAX-ACCESS  read-only
    STATUS      current
    DESCRIPTION
"
ASSP Perl module information for Convert::TNEF;
"
    ::= {asspPerlModuleInfo 8}

iVConvertTNEF  OBJECT-TYPE
    SYNTAX      OCTET STRING
    MAX-ACCESS  read-only
    STATUS      current
    DESCRIPTION
"
installed module version
"
    ::= {ConvertTNEF 1}

rVConvertTNEF  OBJECT-TYPE
    SYNTAX      OCTET STRING
    MAX-ACCESS  read-only
    STATUS      current
    DESCRIPTION
"
required/recommended module version
"
    ::= {ConvertTNEF 2}

iSConvertTNEF  OBJECT-TYPE
    SYNTAX      OCTET STRING
    MAX-ACCESS  read-only
    STATUS      current
    DESCRIPTION
"
module installation status
"
    ::= {ConvertTNEF 3}

dUConvertTNEF  OBJECT-TYPE
    SYNTAX      OCTET STRING
    MAX-ACCESS  read-only
    STATUS      current
    DESCRIPTION
"
download URL for the module
"
    ::= {ConvertTNEF 4}

CryptSMIME  OBJECT-TYPE
    SYNTAX      OCTET STRING
    MAX-ACCESS  read-only
    STATUS      current
    DESCRIPTION
"
ASSP Perl module information for Crypt::SMIME;
"
    ::= {asspPerlModuleInfo 9}

iVCryptSMIME  OBJECT-TYPE
    SYNTAX      OCTET STRING
    MAX-ACCESS  read-only
    STATUS      current
    DESCRIPTION
"
installed module version
"
    ::= {CryptSMIME 1}

rVCryptSMIME  OBJECT-TYPE
    SYNTAX      OCTET STRING
    MAX-ACCESS  read-only
    STATUS      current
    DESCRIPTION
"
required/recommended module version
"
    ::= {CryptSMIME 2}

iSCryptSMIME  OBJECT-TYPE
    SYNTAX      OCTET STRING
    MAX-ACCESS  read-only
    STATUS      current
    DESCRIPTION
"
module installation status
"
    ::= {CryptSMIME 3}

dUCryptSMIME  OBJECT-TYPE
    SYNTAX      OCTET STRING
    MAX-ACCESS  read-only
    STATUS      current
    DESCRIPTION
"
download URL for the module
"
    ::= {CryptSMIME 4}

DBFile  OBJECT-TYPE
    SYNTAX      OCTET STRING
    MAX-ACCESS  read-only
    STATUS      current
    DESCRIPTION
"
ASSP Perl module information for DB_File;
"
    ::= {asspPerlModuleInfo 10}

iVDBFile  OBJECT-TYPE
    SYNTAX      OCTET STRING
    MAX-ACCESS  read-only
    STATUS      current
    DESCRIPTION
"
installed module version
"
    ::= {DBFile 1}

rVDBFile  OBJECT-TYPE
    SYNTAX      OCTET STRING
    MAX-ACCESS  read-only
    STATUS      current
    DESCRIPTION
"
required/recommended module version
"
    ::= {DBFile 2}

iSDBFile  OBJECT-TYPE
    SYNTAX      OCTET STRING
    MAX-ACCESS  read-only
    STATUS      current
    DESCRIPTION
"
module installation status
"
    ::= {DBFile 3}

dUDBFile  OBJECT-TYPE
    SYNTAX      OCTET STRING
    MAX-ACCESS  read-only
    STATUS      current
    DESCRIPTION
"
download URL for the module
"
    ::= {DBFile 4}

DigestMD5  OBJECT-TYPE
    SYNTAX      OCTET STRING
    MAX-ACCESS  read-only
    STATUS      current
    DESCRIPTION
"
ASSP Perl module information for Digest::MD5;
"
    ::= {asspPerlModuleInfo 11}

iVDigestMD5  OBJECT-TYPE
    SYNTAX      OCTET STRING
    MAX-ACCESS  read-only
    STATUS      current
    DESCRIPTION
"
installed module version
"
    ::= {DigestMD5 1}

rVDigestMD5  OBJECT-TYPE
    SYNTAX      OCTET STRING
    MAX-ACCESS  read-only
    STATUS      current
    DESCRIPTION
"
required/recommended module version
"
    ::= {DigestMD5 2}

iSDigestMD5  OBJECT-TYPE
    SYNTAX      OCTET STRING
    MAX-ACCESS  read-only
    STATUS      current
    DESCRIPTION
"
module installation status
"
    ::= {DigestMD5 3}

dUDigestMD5  OBJECT-TYPE
    SYNTAX      OCTET STRING
    MAX-ACCESS  read-only
    STATUS      current
    DESCRIPTION
"
download URL for the module
"
    ::= {DigestMD5 4}

DigestSHA1  OBJECT-TYPE
    SYNTAX      OCTET STRING
    MAX-ACCESS  read-only
    STATUS      current
    DESCRIPTION
"
ASSP Perl module information for Digest::SHA1;
"
    ::= {asspPerlModuleInfo 12}

iVDigestSHA1  OBJECT-TYPE
    SYNTAX      OCTET STRING
    MAX-ACCESS  read-only
    STATUS      current
    DESCRIPTION
"
installed module version
"
    ::= {DigestSHA1 1}

rVDigestSHA1  OBJECT-TYPE
    SYNTAX      OCTET STRING
    MAX-ACCESS  read-only
    STATUS      current
    DESCRIPTION
"
required/recommended module version
"
    ::= {DigestSHA1 2}

iSDigestSHA1  OBJECT-TYPE
    SYNTAX      OCTET STRING
    MAX-ACCESS  read-only
    STATUS      current
    DESCRIPTION
"
module installation status
"
    ::= {DigestSHA1 3}

dUDigestSHA1  OBJECT-TYPE
    SYNTAX      OCTET STRING
    MAX-ACCESS  read-only
    STATUS      current
    DESCRIPTION
"
download URL for the module
"
    ::= {DigestSHA1 4}

EmailMIME  OBJECT-TYPE
    SYNTAX      OCTET STRING
    MAX-ACCESS  read-only
    STATUS      current
    DESCRIPTION
"
ASSP Perl module information for Email::MIME;
"
    ::= {asspPerlModuleInfo 13}

iVEmailMIME  OBJECT-TYPE
    SYNTAX      OCTET STRING
    MAX-ACCESS  read-only
    STATUS      current
    DESCRIPTION
"
installed module version
"
    ::= {EmailMIME 1}

rVEmailMIME  OBJECT-TYPE
    SYNTAX      OCTET STRING
    MAX-ACCESS  read-only
    STATUS      current
    DESCRIPTION
"
required/recommended module version
"
    ::= {EmailMIME 2}

iSEmailMIME  OBJECT-TYPE
    SYNTAX      OCTET STRING
    MAX-ACCESS  read-only
    STATUS      current
    DESCRIPTION
"
module installation status
"
    ::= {EmailMIME 3}

dUEmailMIME  OBJECT-TYPE
    SYNTAX      OCTET STRING
    MAX-ACCESS  read-only
    STATUS      current
    DESCRIPTION
"
download URL for the module
"
    ::= {EmailMIME 4}

EmailSend  OBJECT-TYPE
    SYNTAX      OCTET STRING
    MAX-ACCESS  read-only
    STATUS      current
    DESCRIPTION
"
ASSP Perl module information for Email::Send;
"
    ::= {asspPerlModuleInfo 14}

iVEmailSend  OBJECT-TYPE
    SYNTAX      OCTET STRING
    MAX-ACCESS  read-only
    STATUS      current
    DESCRIPTION
"
installed module version
"
    ::= {EmailSend 1}

rVEmailSend  OBJECT-TYPE
    SYNTAX      OCTET STRING
    MAX-ACCESS  read-only
    STATUS      current
    DESCRIPTION
"
required/recommended module version
"
    ::= {EmailSend 2}

iSEmailSend  OBJECT-TYPE
    SYNTAX      OCTET STRING
    MAX-ACCESS  read-only
    STATUS      current
    DESCRIPTION
"
module installation status
"
    ::= {EmailSend 3}

dUEmailSend  OBJECT-TYPE
    SYNTAX      OCTET STRING
    MAX-ACCESS  read-only
    STATUS      current
    DESCRIPTION
"
download URL for the module
"
    ::= {EmailSend 4}

FileReadBackwards  OBJECT-TYPE
    SYNTAX      OCTET STRING
    MAX-ACCESS  read-only
    STATUS      current
    DESCRIPTION
"
ASSP Perl module information for File::ReadBackwards;
"
    ::= {asspPerlModuleInfo 15}

iVFileReadBackwards  OBJECT-TYPE
    SYNTAX      OCTET STRING
    MAX-ACCESS  read-only
    STATUS      current
    DESCRIPTION
"
installed module version
"
    ::= {FileReadBackwards 1}

rVFileReadBackwards  OBJECT-TYPE
    SYNTAX      OCTET STRING
    MAX-ACCESS  read-only
    STATUS      current
    DESCRIPTION
"
required/recommended module version
"
    ::= {FileReadBackwards 2}

iSFileReadBackwards  OBJECT-TYPE
    SYNTAX      OCTET STRING
    MAX-ACCESS  read-only
    STATUS      current
    DESCRIPTION
"
module installation status
"
    ::= {FileReadBackwards 3}

dUFileReadBackwards  OBJECT-TYPE
    SYNTAX      OCTET STRING
    MAX-ACCESS  read-only
    STATUS      current
    DESCRIPTION
"
download URL for the module
"
    ::= {FileReadBackwards 4}

FileScanClamAV  OBJECT-TYPE
    SYNTAX      OCTET STRING
    MAX-ACCESS  read-only
    STATUS      current
    DESCRIPTION
"
ASSP Perl module information for File::Scan::ClamAV;
"
    ::= {asspPerlModuleInfo 16}

iVFileScanClamAV  OBJECT-TYPE
    SYNTAX      OCTET STRING
    MAX-ACCESS  read-only
    STATUS      current
    DESCRIPTION
"
installed module version
"
    ::= {FileScanClamAV 1}

rVFileScanClamAV  OBJECT-TYPE
    SYNTAX      OCTET STRING
    MAX-ACCESS  read-only
    STATUS      current
    DESCRIPTION
"
required/recommended module version
"
    ::= {FileScanClamAV 2}

iSFileScanClamAV  OBJECT-TYPE
    SYNTAX      OCTET STRING
    MAX-ACCESS  read-only
    STATUS      current
    DESCRIPTION
"
module installation status
"
    ::= {FileScanClamAV 3}

dUFileScanClamAV  OBJECT-TYPE
    SYNTAX      OCTET STRING
    MAX-ACCESS  read-only
    STATUS      current
    DESCRIPTION
"
download URL for the module
"
    ::= {FileScanClamAV 4}

FileWhich  OBJECT-TYPE
    SYNTAX      OCTET STRING
    MAX-ACCESS  read-only
    STATUS      current
    DESCRIPTION
"
ASSP Perl module information for File::Which;
"
    ::= {asspPerlModuleInfo 17}

iVFileWhich  OBJECT-TYPE
    SYNTAX      OCTET STRING
    MAX-ACCESS  read-only
    STATUS      current
    DESCRIPTION
"
installed module version
"
    ::= {FileWhich 1}

rVFileWhich  OBJECT-TYPE
    SYNTAX      OCTET STRING
    MAX-ACCESS  read-only
    STATUS      current
    DESCRIPTION
"
required/recommended module version
"
    ::= {FileWhich 2}

iSFileWhich  OBJECT-TYPE
    SYNTAX      OCTET STRING
    MAX-ACCESS  read-only
    STATUS      current
    DESCRIPTION
"
module installation status
"
    ::= {FileWhich 3}

dUFileWhich  OBJECT-TYPE
    SYNTAX      OCTET STRING
    MAX-ACCESS  read-only
    STATUS      current
    DESCRIPTION
"
download URL for the module
"
    ::= {FileWhich 4}

IOPoll  OBJECT-TYPE
    SYNTAX      OCTET STRING
    MAX-ACCESS  read-only
    STATUS      current
    DESCRIPTION
"
ASSP Perl module information for IO::Poll;
"
    ::= {asspPerlModuleInfo 18}

iVIOPoll  OBJECT-TYPE
    SYNTAX      OCTET STRING
    MAX-ACCESS  read-only
    STATUS      current
    DESCRIPTION
"
installed module version
"
    ::= {IOPoll 1}

rVIOPoll  OBJECT-TYPE
    SYNTAX      OCTET STRING
    MAX-ACCESS  read-only
    STATUS      current
    DESCRIPTION
"
required/recommended module version
"
    ::= {IOPoll 2}

iSIOPoll  OBJECT-TYPE
    SYNTAX      OCTET STRING
    MAX-ACCESS  read-only
    STATUS      current
    DESCRIPTION
"
module installation status
"
    ::= {IOPoll 3}

dUIOPoll  OBJECT-TYPE
    SYNTAX      OCTET STRING
    MAX-ACCESS  read-only
    STATUS      current
    DESCRIPTION
"
download URL for the module
"
    ::= {IOPoll 4}

IOSelect  OBJECT-TYPE
    SYNTAX      OCTET STRING
    MAX-ACCESS  read-only
    STATUS      current
    DESCRIPTION
"
ASSP Perl module information for IO::Select;
"
    ::= {asspPerlModuleInfo 19}

iVIOSelect  OBJECT-TYPE
    SYNTAX      OCTET STRING
    MAX-ACCESS  read-only
    STATUS      current
    DESCRIPTION
"
installed module version
"
    ::= {IOSelect 1}

rVIOSelect  OBJECT-TYPE
    SYNTAX      OCTET STRING
    MAX-ACCESS  read-only
    STATUS      current
    DESCRIPTION
"
required/recommended module version
"
    ::= {IOSelect 2}

iSIOSelect  OBJECT-TYPE
    SYNTAX      OCTET STRING
    MAX-ACCESS  read-only
    STATUS      current
    DESCRIPTION
"
module installation status
"
    ::= {IOSelect 3}

dUIOSelect  OBJECT-TYPE
    SYNTAX      OCTET STRING
    MAX-ACCESS  read-only
    STATUS      current
    DESCRIPTION
"
download URL for the module
"
    ::= {IOSelect 4}

IOSocketINET6  OBJECT-TYPE
    SYNTAX      OCTET STRING
    MAX-ACCESS  read-only
    STATUS      current
    DESCRIPTION
"
ASSP Perl module information for IO::Socket::INET6;
"
    ::= {asspPerlModuleInfo 20}

iVIOSocketINET6  OBJECT-TYPE
    SYNTAX      OCTET STRING
    MAX-ACCESS  read-only
    STATUS      current
    DESCRIPTION
"
installed module version
"
    ::= {IOSocketINET6 1}

rVIOSocketINET6  OBJECT-TYPE
    SYNTAX      OCTET STRING
    MAX-ACCESS  read-only
    STATUS      current
    DESCRIPTION
"
required/recommended module version
"
    ::= {IOSocketINET6 2}

iSIOSocketINET6  OBJECT-TYPE
    SYNTAX      OCTET STRING
    MAX-ACCESS  read-only
    STATUS      current
    DESCRIPTION
"
module installation status
"
    ::= {IOSocketINET6 3}

dUIOSocketINET6  OBJECT-TYPE
    SYNTAX      OCTET STRING
    MAX-ACCESS  read-only
    STATUS      current
    DESCRIPTION
"
download URL for the module
"
    ::= {IOSocketINET6 4}

IOSocketSSL  OBJECT-TYPE
    SYNTAX      OCTET STRING
    MAX-ACCESS  read-only
    STATUS      current
    DESCRIPTION
"
ASSP Perl module information for IO::Socket::SSL;
"
    ::= {asspPerlModuleInfo 21}

iVIOSocketSSL  OBJECT-TYPE
    SYNTAX      OCTET STRING
    MAX-ACCESS  read-only
    STATUS      current
    DESCRIPTION
"
installed module version
"
    ::= {IOSocketSSL 1}

rVIOSocketSSL  OBJECT-TYPE
    SYNTAX      OCTET STRING
    MAX-ACCESS  read-only
    STATUS      current
    DESCRIPTION
"
required/recommended module version
"
    ::= {IOSocketSSL 2}

iSIOSocketSSL  OBJECT-TYPE
    SYNTAX      OCTET STRING
    MAX-ACCESS  read-only
    STATUS      current
    DESCRIPTION
"
module installation status
"
    ::= {IOSocketSSL 3}

dUIOSocketSSL  OBJECT-TYPE
    SYNTAX      OCTET STRING
    MAX-ACCESS  read-only
    STATUS      current
    DESCRIPTION
"
download URL for the module
"
    ::= {IOSocketSSL 4}

ImageOCRTesseract  OBJECT-TYPE
    SYNTAX      OCTET STRING
    MAX-ACCESS  read-only
    STATUS      current
    DESCRIPTION
"
ASSP Perl module information for Image::OCR::Tesseract;
"
    ::= {asspPerlModuleInfo 22}

iVImageOCRTesseract  OBJECT-TYPE
    SYNTAX      OCTET STRING
    MAX-ACCESS  read-only
    STATUS      current
    DESCRIPTION
"
installed module version
"
    ::= {ImageOCRTesseract 1}

rVImageOCRTesseract  OBJECT-TYPE
    SYNTAX      OCTET STRING
    MAX-ACCESS  read-only
    STATUS      current
    DESCRIPTION
"
required/recommended module version
"
    ::= {ImageOCRTesseract 2}

iSImageOCRTesseract  OBJECT-TYPE
    SYNTAX      OCTET STRING
    MAX-ACCESS  read-only
    STATUS      current
    DESCRIPTION
"
module installation status
"
    ::= {ImageOCRTesseract 3}

dUImageOCRTesseract  OBJECT-TYPE
    SYNTAX      OCTET STRING
    MAX-ACCESS  read-only
    STATUS      current
    DESCRIPTION
"
download URL for the module
"
    ::= {ImageOCRTesseract 4}

LWPSimple  OBJECT-TYPE
    SYNTAX      OCTET STRING
    MAX-ACCESS  read-only
    STATUS      current
    DESCRIPTION
"
ASSP Perl module information for LWP::Simple;
"
    ::= {asspPerlModuleInfo 23}

iVLWPSimple  OBJECT-TYPE
    SYNTAX      OCTET STRING
    MAX-ACCESS  read-only
    STATUS      current
    DESCRIPTION
"
installed module version
"
    ::= {LWPSimple 1}

rVLWPSimple  OBJECT-TYPE
    SYNTAX      OCTET STRING
    MAX-ACCESS  read-only
    STATUS      current
    DESCRIPTION
"
required/recommended module version
"
    ::= {LWPSimple 2}

iSLWPSimple  OBJECT-TYPE
    SYNTAX      OCTET STRING
    MAX-ACCESS  read-only
    STATUS      current
    DESCRIPTION
"
module installation status
"
    ::= {LWPSimple 3}

dULWPSimple  OBJECT-TYPE
    SYNTAX      OCTET STRING
    MAX-ACCESS  read-only
    STATUS      current
    DESCRIPTION
"
download URL for the module
"
    ::= {LWPSimple 4}

MIMETypes  OBJECT-TYPE
    SYNTAX      OCTET STRING
    MAX-ACCESS  read-only
    STATUS      current
    DESCRIPTION
"
ASSP Perl module information for MIME::Types;
"
    ::= {asspPerlModuleInfo 24}

iVMIMETypes  OBJECT-TYPE
    SYNTAX      OCTET STRING
    MAX-ACCESS  read-only
    STATUS      current
    DESCRIPTION
"
installed module version
"
    ::= {MIMETypes 1}

rVMIMETypes  OBJECT-TYPE
    SYNTAX      OCTET STRING
    MAX-ACCESS  read-only
    STATUS      current
    DESCRIPTION
"
required/recommended module version
"
    ::= {MIMETypes 2}

iSMIMETypes  OBJECT-TYPE
    SYNTAX      OCTET STRING
    MAX-ACCESS  read-only
    STATUS      current
    DESCRIPTION
"
module installation status
"
    ::= {MIMETypes 3}

dUMIMETypes  OBJECT-TYPE
    SYNTAX      OCTET STRING
    MAX-ACCESS  read-only
    STATUS      current
    DESCRIPTION
"
download URL for the module
"
    ::= {MIMETypes 4}

MailDKIMVerifier  OBJECT-TYPE
    SYNTAX      OCTET STRING
    MAX-ACCESS  read-only
    STATUS      current
    DESCRIPTION
"
ASSP Perl module information for Mail::DKIM::Verifier;
"
    ::= {asspPerlModuleInfo 25}

iVMailDKIMVerifier  OBJECT-TYPE
    SYNTAX      OCTET STRING
    MAX-ACCESS  read-only
    STATUS      current
    DESCRIPTION
"
installed module version
"
    ::= {MailDKIMVerifier 1}

rVMailDKIMVerifier  OBJECT-TYPE
    SYNTAX      OCTET STRING
    MAX-ACCESS  read-only
    STATUS      current
    DESCRIPTION
"
required/recommended module version
"
    ::= {MailDKIMVerifier 2}

iSMailDKIMVerifier  OBJECT-TYPE
    SYNTAX      OCTET STRING
    MAX-ACCESS  read-only
    STATUS      current
    DESCRIPTION
"
module installation status
"
    ::= {MailDKIMVerifier 3}

dUMailDKIMVerifier  OBJECT-TYPE
    SYNTAX      OCTET STRING
    MAX-ACCESS  read-only
    STATUS      current
    DESCRIPTION
"
download URL for the module
"
    ::= {MailDKIMVerifier 4}

MailSPF  OBJECT-TYPE
    SYNTAX      OCTET STRING
    MAX-ACCESS  read-only
    STATUS      current
    DESCRIPTION
"
ASSP Perl module information for Mail::SPF;
"
    ::= {asspPerlModuleInfo 26}

iVMailSPF  OBJECT-TYPE
    SYNTAX      OCTET STRING
    MAX-ACCESS  read-only
    STATUS      current
    DESCRIPTION
"
installed module version
"
    ::= {MailSPF 1}

rVMailSPF  OBJECT-TYPE
    SYNTAX      OCTET STRING
    MAX-ACCESS  read-only
    STATUS      current
    DESCRIPTION
"
required/recommended module version
"
    ::= {MailSPF 2}

iSMailSPF  OBJECT-TYPE
    SYNTAX      OCTET STRING
    MAX-ACCESS  read-only
    STATUS      current
    DESCRIPTION
"
module installation status
"
    ::= {MailSPF 3}

dUMailSPF  OBJECT-TYPE
    SYNTAX      OCTET STRING
    MAX-ACCESS  read-only
    STATUS      current
    DESCRIPTION
"
download URL for the module
"
    ::= {MailSPF 4}

MailSPFQuery  OBJECT-TYPE
    SYNTAX      OCTET STRING
    MAX-ACCESS  read-only
    STATUS      current
    DESCRIPTION
"
ASSP Perl module information for Mail::SPF::Query;
"
    ::= {asspPerlModuleInfo 27}

iVMailSPFQuery  OBJECT-TYPE
    SYNTAX      OCTET STRING
    MAX-ACCESS  read-only
    STATUS      current
    DESCRIPTION
"
installed module version
"
    ::= {MailSPFQuery 1}

rVMailSPFQuery  OBJECT-TYPE
    SYNTAX      OCTET STRING
    MAX-ACCESS  read-only
    STATUS      current
    DESCRIPTION
"
required/recommended module version
"
    ::= {MailSPFQuery 2}

iSMailSPFQuery  OBJECT-TYPE
    SYNTAX      OCTET STRING
    MAX-ACCESS  read-only
    STATUS      current
    DESCRIPTION
"
module installation status
"
    ::= {MailSPFQuery 3}

dUMailSPFQuery  OBJECT-TYPE
    SYNTAX      OCTET STRING
    MAX-ACCESS  read-only
    STATUS      current
    DESCRIPTION
"
download URL for the module
"
    ::= {MailSPFQuery 4}

MailSRS  OBJECT-TYPE
    SYNTAX      OCTET STRING
    MAX-ACCESS  read-only
    STATUS      current
    DESCRIPTION
"
ASSP Perl module information for Mail::SRS;
"
    ::= {asspPerlModuleInfo 28}

iVMailSRS  OBJECT-TYPE
    SYNTAX      OCTET STRING
    MAX-ACCESS  read-only
    STATUS      current
    DESCRIPTION
"
installed module version
"
    ::= {MailSRS 1}

rVMailSRS  OBJECT-TYPE
    SYNTAX      OCTET STRING
    MAX-ACCESS  read-only
    STATUS      current
    DESCRIPTION
"
required/recommended module version
"
    ::= {MailSRS 2}

iSMailSRS  OBJECT-TYPE
    SYNTAX      OCTET STRING
    MAX-ACCESS  read-only
    STATUS      current
    DESCRIPTION
"
module installation status
"
    ::= {MailSRS 3}

dUMailSRS  OBJECT-TYPE
    SYNTAX      OCTET STRING
    MAX-ACCESS  read-only
    STATUS      current
    DESCRIPTION
"
download URL for the module
"
    ::= {MailSRS 4}

NetCIDRLite  OBJECT-TYPE
    SYNTAX      OCTET STRING
    MAX-ACCESS  read-only
    STATUS      current
    DESCRIPTION
"
ASSP Perl module information for Net::CIDR::Lite;
"
    ::= {asspPerlModuleInfo 29}

iVNetCIDRLite  OBJECT-TYPE
    SYNTAX      OCTET STRING
    MAX-ACCESS  read-only
    STATUS      current
    DESCRIPTION
"
installed module version
"
    ::= {NetCIDRLite 1}

rVNetCIDRLite  OBJECT-TYPE
    SYNTAX      OCTET STRING
    MAX-ACCESS  read-only
    STATUS      current
    DESCRIPTION
"
required/recommended module version
"
    ::= {NetCIDRLite 2}

iSNetCIDRLite  OBJECT-TYPE
    SYNTAX      OCTET STRING
    MAX-ACCESS  read-only
    STATUS      current
    DESCRIPTION
"
module installation status
"
    ::= {NetCIDRLite 3}

dUNetCIDRLite  OBJECT-TYPE
    SYNTAX      OCTET STRING
    MAX-ACCESS  read-only
    STATUS      current
    DESCRIPTION
"
download URL for the module
"
    ::= {NetCIDRLite 4}

NetDNS  OBJECT-TYPE
    SYNTAX      OCTET STRING
    MAX-ACCESS  read-only
    STATUS      current
    DESCRIPTION
"
ASSP Perl module information for Net::DNS;
"
    ::= {asspPerlModuleInfo 30}

iVNetDNS  OBJECT-TYPE
    SYNTAX      OCTET STRING
    MAX-ACCESS  read-only
    STATUS      current
    DESCRIPTION
"
installed module version
"
    ::= {NetDNS 1}

rVNetDNS  OBJECT-TYPE
    SYNTAX      OCTET STRING
    MAX-ACCESS  read-only
    STATUS      current
    DESCRIPTION
"
required/recommended module version
"
    ::= {NetDNS 2}

iSNetDNS  OBJECT-TYPE
    SYNTAX      OCTET STRING
    MAX-ACCESS  read-only
    STATUS      current
    DESCRIPTION
"
module installation status
"
    ::= {NetDNS 3}

dUNetDNS  OBJECT-TYPE
    SYNTAX      OCTET STRING
    MAX-ACCESS  read-only
    STATUS      current
    DESCRIPTION
"
download URL for the module
"
    ::= {NetDNS 4}

NetIP  OBJECT-TYPE
    SYNTAX      OCTET STRING
    MAX-ACCESS  read-only
    STATUS      current
    DESCRIPTION
"
ASSP Perl module information for Net::IP;
"
    ::= {asspPerlModuleInfo 31}

iVNetIP  OBJECT-TYPE
    SYNTAX      OCTET STRING
    MAX-ACCESS  read-only
    STATUS      current
    DESCRIPTION
"
installed module version
"
    ::= {NetIP 1}

rVNetIP  OBJECT-TYPE
    SYNTAX      OCTET STRING
    MAX-ACCESS  read-only
    STATUS      current
    DESCRIPTION
"
required/recommended module version
"
    ::= {NetIP 2}

iSNetIP  OBJECT-TYPE
    SYNTAX      OCTET STRING
    MAX-ACCESS  read-only
    STATUS      current
    DESCRIPTION
"
module installation status
"
    ::= {NetIP 3}

dUNetIP  OBJECT-TYPE
    SYNTAX      OCTET STRING
    MAX-ACCESS  read-only
    STATUS      current
    DESCRIPTION
"
download URL for the module
"
    ::= {NetIP 4}

NetLDAP  OBJECT-TYPE
    SYNTAX      OCTET STRING
    MAX-ACCESS  read-only
    STATUS      current
    DESCRIPTION
"
ASSP Perl module information for Net::LDAP;
"
    ::= {asspPerlModuleInfo 32}

iVNetLDAP  OBJECT-TYPE
    SYNTAX      OCTET STRING
    MAX-ACCESS  read-only
    STATUS      current
    DESCRIPTION
"
installed module version
"
    ::= {NetLDAP 1}

rVNetLDAP  OBJECT-TYPE
    SYNTAX      OCTET STRING
    MAX-ACCESS  read-only
    STATUS      current
    DESCRIPTION
"
required/recommended module version
"
    ::= {NetLDAP 2}

iSNetLDAP  OBJECT-TYPE
    SYNTAX      OCTET STRING
    MAX-ACCESS  read-only
    STATUS      current
    DESCRIPTION
"
module installation status
"
    ::= {NetLDAP 3}

dUNetLDAP  OBJECT-TYPE
    SYNTAX      OCTET STRING
    MAX-ACCESS  read-only
    STATUS      current
    DESCRIPTION
"
download URL for the module
"
    ::= {NetLDAP 4}

NetSMTP  OBJECT-TYPE
    SYNTAX      OCTET STRING
    MAX-ACCESS  read-only
    STATUS      current
    DESCRIPTION
"
ASSP Perl module information for Net::SMTP;
"
    ::= {asspPerlModuleInfo 33}

iVNetSMTP  OBJECT-TYPE
    SYNTAX      OCTET STRING
    MAX-ACCESS  read-only
    STATUS      current
    DESCRIPTION
"
installed module version
"
    ::= {NetSMTP 1}

rVNetSMTP  OBJECT-TYPE
    SYNTAX      OCTET STRING
    MAX-ACCESS  read-only
    STATUS      current
    DESCRIPTION
"
required/recommended module version
"
    ::= {NetSMTP 2}

iSNetSMTP  OBJECT-TYPE
    SYNTAX      OCTET STRING
    MAX-ACCESS  read-only
    STATUS      current
    DESCRIPTION
"
module installation status
"
    ::= {NetSMTP 3}

dUNetSMTP  OBJECT-TYPE
    SYNTAX      OCTET STRING
    MAX-ACCESS  read-only
    STATUS      current
    DESCRIPTION
"
download URL for the module
"
    ::= {NetSMTP 4}

NetSMTPSSL  OBJECT-TYPE
    SYNTAX      OCTET STRING
    MAX-ACCESS  read-only
    STATUS      current
    DESCRIPTION
"
ASSP Perl module information for Net::SMTP::SSL;
"
    ::= {asspPerlModuleInfo 34}

iVNetSMTPSSL  OBJECT-TYPE
    SYNTAX      OCTET STRING
    MAX-ACCESS  read-only
    STATUS      current
    DESCRIPTION
"
installed module version
"
    ::= {NetSMTPSSL 1}

rVNetSMTPSSL  OBJECT-TYPE
    SYNTAX      OCTET STRING
    MAX-ACCESS  read-only
    STATUS      current
    DESCRIPTION
"
required/recommended module version
"
    ::= {NetSMTPSSL 2}

iSNetSMTPSSL  OBJECT-TYPE
    SYNTAX      OCTET STRING
    MAX-ACCESS  read-only
    STATUS      current
    DESCRIPTION
"
module installation status
"
    ::= {NetSMTPSSL 3}

dUNetSMTPSSL  OBJECT-TYPE
    SYNTAX      OCTET STRING
    MAX-ACCESS  read-only
    STATUS      current
    DESCRIPTION
"
download URL for the module
"
    ::= {NetSMTPSSL 4}

NetSSLeay  OBJECT-TYPE
    SYNTAX      OCTET STRING
    MAX-ACCESS  read-only
    STATUS      current
    DESCRIPTION
"
ASSP Perl module information for Net::SSLeay;
"
    ::= {asspPerlModuleInfo 35}

iVNetSSLeay  OBJECT-TYPE
    SYNTAX      OCTET STRING
    MAX-ACCESS  read-only
    STATUS      current
    DESCRIPTION
"
installed module version
"
    ::= {NetSSLeay 1}

rVNetSSLeay  OBJECT-TYPE
    SYNTAX      OCTET STRING
    MAX-ACCESS  read-only
    STATUS      current
    DESCRIPTION
"
required/recommended module version
"
    ::= {NetSSLeay 2}

iSNetSSLeay  OBJECT-TYPE
    SYNTAX      OCTET STRING
    MAX-ACCESS  read-only
    STATUS      current
    DESCRIPTION
"
module installation status
"
    ::= {NetSSLeay 3}

dUNetSSLeay  OBJECT-TYPE
    SYNTAX      OCTET STRING
    MAX-ACCESS  read-only
    STATUS      current
    DESCRIPTION
"
download URL for the module
"
    ::= {NetSSLeay 4}

NetAddrIPLite  OBJECT-TYPE
    SYNTAX      OCTET STRING
    MAX-ACCESS  read-only
    STATUS      current
    DESCRIPTION
"
ASSP Perl module information for NetAddr::IP::Lite;
"
    ::= {asspPerlModuleInfo 36}

iVNetAddrIPLite  OBJECT-TYPE
    SYNTAX      OCTET STRING
    MAX-ACCESS  read-only
    STATUS      current
    DESCRIPTION
"
installed module version
"
    ::= {NetAddrIPLite 1}

rVNetAddrIPLite  OBJECT-TYPE
    SYNTAX      OCTET STRING
    MAX-ACCESS  read-only
    STATUS      current
    DESCRIPTION
"
required/recommended module version
"
    ::= {NetAddrIPLite 2}

iSNetAddrIPLite  OBJECT-TYPE
    SYNTAX      OCTET STRING
    MAX-ACCESS  read-only
    STATUS      current
    DESCRIPTION
"
module installation status
"
    ::= {NetAddrIPLite 3}

dUNetAddrIPLite  OBJECT-TYPE
    SYNTAX      OCTET STRING
    MAX-ACCESS  read-only
    STATUS      current
    DESCRIPTION
"
download URL for the module
"
    ::= {NetAddrIPLite 4}

NetSNMPagent  OBJECT-TYPE
    SYNTAX      OCTET STRING
    MAX-ACCESS  read-only
    STATUS      current
    DESCRIPTION
"
ASSP Perl module information for NetSNMP::agent;
"
    ::= {asspPerlModuleInfo 37}

iVNetSNMPagent  OBJECT-TYPE
    SYNTAX      OCTET STRING
    MAX-ACCESS  read-only
    STATUS      current
    DESCRIPTION
"
installed module version
"
    ::= {NetSNMPagent 1}

rVNetSNMPagent  OBJECT-TYPE
    SYNTAX      OCTET STRING
    MAX-ACCESS  read-only
    STATUS      current
    DESCRIPTION
"
required/recommended module version
"
    ::= {NetSNMPagent 2}

iSNetSNMPagent  OBJECT-TYPE
    SYNTAX      OCTET STRING
    MAX-ACCESS  read-only
    STATUS      current
    DESCRIPTION
"
module installation status
"
    ::= {NetSNMPagent 3}

dUNetSNMPagent  OBJECT-TYPE
    SYNTAX      OCTET STRING
    MAX-ACCESS  read-only
    STATUS      current
    DESCRIPTION
"
download URL for the module
"
    ::= {NetSNMPagent 4}

OpenSSL098k  OBJECT-TYPE
    SYNTAX      OCTET STRING
    MAX-ACCESS  read-only
    STATUS      current
    DESCRIPTION
"
ASSP Perl module information for OpenSSL 0.9.8k;
"
    ::= {asspPerlModuleInfo 38}

iVOpenSSL098k  OBJECT-TYPE
    SYNTAX      OCTET STRING
    MAX-ACCESS  read-only
    STATUS      current
    DESCRIPTION
"
installed module version
"
    ::= {OpenSSL098k 1}

rVOpenSSL098k  OBJECT-TYPE
    SYNTAX      OCTET STRING
    MAX-ACCESS  read-only
    STATUS      current
    DESCRIPTION
"
required/recommended module version
"
    ::= {OpenSSL098k 2}

iSOpenSSL098k  OBJECT-TYPE
    SYNTAX      OCTET STRING
    MAX-ACCESS  read-only
    STATUS      current
    DESCRIPTION
"
module installation status
"
    ::= {OpenSSL098k 3}

dUOpenSSL098k  OBJECT-TYPE
    SYNTAX      OCTET STRING
    MAX-ACCESS  read-only
    STATUS      current
    DESCRIPTION
"
download URL for the module
"
    ::= {OpenSSL098k 4}

PDFOCR2  OBJECT-TYPE
    SYNTAX      OCTET STRING
    MAX-ACCESS  read-only
    STATUS      current
    DESCRIPTION
"
ASSP Perl module information for PDF::OCR2;
"
    ::= {asspPerlModuleInfo 39}

iVPDFOCR2  OBJECT-TYPE
    SYNTAX      OCTET STRING
    MAX-ACCESS  read-only
    STATUS      current
    DESCRIPTION
"
installed module version
"
    ::= {PDFOCR2 1}

rVPDFOCR2  OBJECT-TYPE
    SYNTAX      OCTET STRING
    MAX-ACCESS  read-only
    STATUS      current
    DESCRIPTION
"
required/recommended module version
"
    ::= {PDFOCR2 2}

iSPDFOCR2  OBJECT-TYPE
    SYNTAX      OCTET STRING
    MAX-ACCESS  read-only
    STATUS      current
    DESCRIPTION
"
module installation status
"
    ::= {PDFOCR2 3}

dUPDFOCR2  OBJECT-TYPE
    SYNTAX      OCTET STRING
    MAX-ACCESS  read-only
    STATUS      current
    DESCRIPTION
"
download URL for the module
"
    ::= {PDFOCR2 4}

PerlIOscalar  OBJECT-TYPE
    SYNTAX      OCTET STRING
    MAX-ACCESS  read-only
    STATUS      current
    DESCRIPTION
"
ASSP Perl module information for PerlIO::scalar;
"
    ::= {asspPerlModuleInfo 40}

iVPerlIOscalar  OBJECT-TYPE
    SYNTAX      OCTET STRING
    MAX-ACCESS  read-only
    STATUS      current
    DESCRIPTION
"
installed module version
"
    ::= {PerlIOscalar 1}

rVPerlIOscalar  OBJECT-TYPE
    SYNTAX      OCTET STRING
    MAX-ACCESS  read-only
    STATUS      current
    DESCRIPTION
"
required/recommended module version
"
    ::= {PerlIOscalar 2}

iSPerlIOscalar  OBJECT-TYPE
    SYNTAX      OCTET STRING
    MAX-ACCESS  read-only
    STATUS      current
    DESCRIPTION
"
module installation status
"
    ::= {PerlIOscalar 3}

dUPerlIOscalar  OBJECT-TYPE
    SYNTAX      OCTET STRING
    MAX-ACCESS  read-only
    STATUS      current
    DESCRIPTION
"
download URL for the module
"
    ::= {PerlIOscalar 4}

PluginsASSPAFC  OBJECT-TYPE
    SYNTAX      OCTET STRING
    MAX-ACCESS  read-only
    STATUS      current
    DESCRIPTION
"
ASSP Perl module information for Plugins::ASSP_AFC;
"
    ::= {asspPerlModuleInfo 41}

iVPluginsASSPAFC  OBJECT-TYPE
    SYNTAX      OCTET STRING
    MAX-ACCESS  read-only
    STATUS      current
    DESCRIPTION
"
installed module version
"
    ::= {PluginsASSPAFC 1}

rVPluginsASSPAFC  OBJECT-TYPE
    SYNTAX      OCTET STRING
    MAX-ACCESS  read-only
    STATUS      current
    DESCRIPTION
"
required/recommended module version
"
    ::= {PluginsASSPAFC 2}

iSPluginsASSPAFC  OBJECT-TYPE
    SYNTAX      OCTET STRING
    MAX-ACCESS  read-only
    STATUS      current
    DESCRIPTION
"
module installation status
"
    ::= {PluginsASSPAFC 3}

dUPluginsASSPAFC  OBJECT-TYPE
    SYNTAX      OCTET STRING
    MAX-ACCESS  read-only
    STATUS      current
    DESCRIPTION
"
download URL for the module
"
    ::= {PluginsASSPAFC 4}

PluginsASSPARC  OBJECT-TYPE
    SYNTAX      OCTET STRING
    MAX-ACCESS  read-only
    STATUS      current
    DESCRIPTION
"
ASSP Perl module information for Plugins::ASSP_ARC;
"
    ::= {asspPerlModuleInfo 42}

iVPluginsASSPARC  OBJECT-TYPE
    SYNTAX      OCTET STRING
    MAX-ACCESS  read-only
    STATUS      current
    DESCRIPTION
"
installed module version
"
    ::= {PluginsASSPARC 1}

rVPluginsASSPARC  OBJECT-TYPE
    SYNTAX      OCTET STRING
    MAX-ACCESS  read-only
    STATUS      current
    DESCRIPTION
"
required/recommended module version
"
    ::= {PluginsASSPARC 2}

iSPluginsASSPARC  OBJECT-TYPE
    SYNTAX      OCTET STRING
    MAX-ACCESS  read-only
    STATUS      current
    DESCRIPTION
"
module installation status
"
    ::= {PluginsASSPARC 3}

dUPluginsASSPARC  OBJECT-TYPE
    SYNTAX      OCTET STRING
    MAX-ACCESS  read-only
    STATUS      current
    DESCRIPTION
"
download URL for the module
"
    ::= {PluginsASSPARC 4}

PluginsASSPDCC  OBJECT-TYPE
    SYNTAX      OCTET STRING
    MAX-ACCESS  read-only
    STATUS      current
    DESCRIPTION
"
ASSP Perl module information for Plugins::ASSP_DCC;
"
    ::= {asspPerlModuleInfo 43}

iVPluginsASSPDCC  OBJECT-TYPE
    SYNTAX      OCTET STRING
    MAX-ACCESS  read-only
    STATUS      current
    DESCRIPTION
"
installed module version
"
    ::= {PluginsASSPDCC 1}

rVPluginsASSPDCC  OBJECT-TYPE
    SYNTAX      OCTET STRING
    MAX-ACCESS  read-only
    STATUS      current
    DESCRIPTION
"
required/recommended module version
"
    ::= {PluginsASSPDCC 2}

iSPluginsASSPDCC  OBJECT-TYPE
    SYNTAX      OCTET STRING
    MAX-ACCESS  read-only
    STATUS      current
    DESCRIPTION
"
module installation status
"
    ::= {PluginsASSPDCC 3}

dUPluginsASSPDCC  OBJECT-TYPE
    SYNTAX      OCTET STRING
    MAX-ACCESS  read-only
    STATUS      current
    DESCRIPTION
"
download URL for the module
"
    ::= {PluginsASSPDCC 4}

PluginsASSPOCR  OBJECT-TYPE
    SYNTAX      OCTET STRING
    MAX-ACCESS  read-only
    STATUS      current
    DESCRIPTION
"
ASSP Perl module information for Plugins::ASSP_OCR;
"
    ::= {asspPerlModuleInfo 44}

iVPluginsASSPOCR  OBJECT-TYPE
    SYNTAX      OCTET STRING
    MAX-ACCESS  read-only
    STATUS      current
    DESCRIPTION
"
installed module version
"
    ::= {PluginsASSPOCR 1}

rVPluginsASSPOCR  OBJECT-TYPE
    SYNTAX      OCTET STRING
    MAX-ACCESS  read-only
    STATUS      current
    DESCRIPTION
"
required/recommended module version
"
    ::= {PluginsASSPOCR 2}

iSPluginsASSPOCR  OBJECT-TYPE
    SYNTAX      OCTET STRING
    MAX-ACCESS  read-only
    STATUS      current
    DESCRIPTION
"
module installation status
"
    ::= {PluginsASSPOCR 3}

dUPluginsASSPOCR  OBJECT-TYPE
    SYNTAX      OCTET STRING
    MAX-ACCESS  read-only
    STATUS      current
    DESCRIPTION
"
download URL for the module
"
    ::= {PluginsASSPOCR 4}

PluginsASSPRazor  OBJECT-TYPE
    SYNTAX      OCTET STRING
    MAX-ACCESS  read-only
    STATUS      current
    DESCRIPTION
"
ASSP Perl module information for Plugins::ASSP_Razor;
"
    ::= {asspPerlModuleInfo 45}

iVPluginsASSPRazor  OBJECT-TYPE
    SYNTAX      OCTET STRING
    MAX-ACCESS  read-only
    STATUS      current
    DESCRIPTION
"
installed module version
"
    ::= {PluginsASSPRazor 1}

rVPluginsASSPRazor  OBJECT-TYPE
    SYNTAX      OCTET STRING
    MAX-ACCESS  read-only
    STATUS      current
    DESCRIPTION
"
required/recommended module version
"
    ::= {PluginsASSPRazor 2}

iSPluginsASSPRazor  OBJECT-TYPE
    SYNTAX      OCTET STRING
    MAX-ACCESS  read-only
    STATUS      current
    DESCRIPTION
"
module installation status
"
    ::= {PluginsASSPRazor 3}

dUPluginsASSPRazor  OBJECT-TYPE
    SYNTAX      OCTET STRING
    MAX-ACCESS  read-only
    STATUS      current
    DESCRIPTION
"
download URL for the module
"
    ::= {PluginsASSPRazor 4}

RegexpOptimizer  OBJECT-TYPE
    SYNTAX      OCTET STRING
    MAX-ACCESS  read-only
    STATUS      current
    DESCRIPTION
"
ASSP Perl module information for Regexp::Optimizer;
"
    ::= {asspPerlModuleInfo 46}

iVRegexpOptimizer  OBJECT-TYPE
    SYNTAX      OCTET STRING
    MAX-ACCESS  read-only
    STATUS      current
    DESCRIPTION
"
installed module version
"
    ::= {RegexpOptimizer 1}

rVRegexpOptimizer  OBJECT-TYPE
    SYNTAX      OCTET STRING
    MAX-ACCESS  read-only
    STATUS      current
    DESCRIPTION
"
required/recommended module version
"
    ::= {RegexpOptimizer 2}

iSRegexpOptimizer  OBJECT-TYPE
    SYNTAX      OCTET STRING
    MAX-ACCESS  read-only
    STATUS      current
    DESCRIPTION
"
module installation status
"
    ::= {RegexpOptimizer 3}

dURegexpOptimizer  OBJECT-TYPE
    SYNTAX      OCTET STRING
    MAX-ACCESS  read-only
    STATUS      current
    DESCRIPTION
"
download URL for the module
"
    ::= {RegexpOptimizer 4}

ScheduleCron  OBJECT-TYPE
    SYNTAX      OCTET STRING
    MAX-ACCESS  read-only
    STATUS      current
    DESCRIPTION
"
ASSP Perl module information for Schedule::Cron;
"
    ::= {asspPerlModuleInfo 47}

iVScheduleCron  OBJECT-TYPE
    SYNTAX      OCTET STRING
    MAX-ACCESS  read-only
    STATUS      current
    DESCRIPTION
"
installed module version
"
    ::= {ScheduleCron 1}

rVScheduleCron  OBJECT-TYPE
    SYNTAX      OCTET STRING
    MAX-ACCESS  read-only
    STATUS      current
    DESCRIPTION
"
required/recommended module version
"
    ::= {ScheduleCron 2}

iSScheduleCron  OBJECT-TYPE
    SYNTAX      OCTET STRING
    MAX-ACCESS  read-only
    STATUS      current
    DESCRIPTION
"
module installation status
"
    ::= {ScheduleCron 3}

dUScheduleCron  OBJECT-TYPE
    SYNTAX      OCTET STRING
    MAX-ACCESS  read-only
    STATUS      current
    DESCRIPTION
"
download URL for the module
"
    ::= {ScheduleCron 4}

SysCpuAffinity  OBJECT-TYPE
    SYNTAX      OCTET STRING
    MAX-ACCESS  read-only
    STATUS      current
    DESCRIPTION
"
ASSP Perl module information for Sys::CpuAffinity;
"
    ::= {asspPerlModuleInfo 48}

iVSysCpuAffinity  OBJECT-TYPE
    SYNTAX      OCTET STRING
    MAX-ACCESS  read-only
    STATUS      current
    DESCRIPTION
"
installed module version
"
    ::= {SysCpuAffinity 1}

rVSysCpuAffinity  OBJECT-TYPE
    SYNTAX      OCTET STRING
    MAX-ACCESS  read-only
    STATUS      current
    DESCRIPTION
"
required/recommended module version
"
    ::= {SysCpuAffinity 2}

iSSysCpuAffinity  OBJECT-TYPE
    SYNTAX      OCTET STRING
    MAX-ACCESS  read-only
    STATUS      current
    DESCRIPTION
"
module installation status
"
    ::= {SysCpuAffinity 3}

dUSysCpuAffinity  OBJECT-TYPE
    SYNTAX      OCTET STRING
    MAX-ACCESS  read-only
    STATUS      current
    DESCRIPTION
"
download URL for the module
"
    ::= {SysCpuAffinity 4}

SysMemInfo  OBJECT-TYPE
    SYNTAX      OCTET STRING
    MAX-ACCESS  read-only
    STATUS      current
    DESCRIPTION
"
ASSP Perl module information for Sys::MemInfo;
"
    ::= {asspPerlModuleInfo 49}

iVSysMemInfo  OBJECT-TYPE
    SYNTAX      OCTET STRING
    MAX-ACCESS  read-only
    STATUS      current
    DESCRIPTION
"
installed module version
"
    ::= {SysMemInfo 1}

rVSysMemInfo  OBJECT-TYPE
    SYNTAX      OCTET STRING
    MAX-ACCESS  read-only
    STATUS      current
    DESCRIPTION
"
required/recommended module version
"
    ::= {SysMemInfo 2}

iSSysMemInfo  OBJECT-TYPE
    SYNTAX      OCTET STRING
    MAX-ACCESS  read-only
    STATUS      current
    DESCRIPTION
"
module installation status
"
    ::= {SysMemInfo 3}

dUSysMemInfo  OBJECT-TYPE
    SYNTAX      OCTET STRING
    MAX-ACCESS  read-only
    STATUS      current
    DESCRIPTION
"
download URL for the module
"
    ::= {SysMemInfo 4}

SysSyslog  OBJECT-TYPE
    SYNTAX      OCTET STRING
    MAX-ACCESS  read-only
    STATUS      current
    DESCRIPTION
"
ASSP Perl module information for Sys::Syslog;
"
    ::= {asspPerlModuleInfo 50}

iVSysSyslog  OBJECT-TYPE
    SYNTAX      OCTET STRING
    MAX-ACCESS  read-only
    STATUS      current
    DESCRIPTION
"
installed module version
"
    ::= {SysSyslog 1}

rVSysSyslog  OBJECT-TYPE
    SYNTAX      OCTET STRING
    MAX-ACCESS  read-only
    STATUS      current
    DESCRIPTION
"
required/recommended module version
"
    ::= {SysSyslog 2}

iSSysSyslog  OBJECT-TYPE
    SYNTAX      OCTET STRING
    MAX-ACCESS  read-only
    STATUS      current
    DESCRIPTION
"
module installation status
"
    ::= {SysSyslog 3}

dUSysSyslog  OBJECT-TYPE
    SYNTAX      OCTET STRING
    MAX-ACCESS  read-only
    STATUS      current
    DESCRIPTION
"
download URL for the module
"
    ::= {SysSyslog 4}

TextUnidecode  OBJECT-TYPE
    SYNTAX      OCTET STRING
    MAX-ACCESS  read-only
    STATUS      current
    DESCRIPTION
"
ASSP Perl module information for Text::Unidecode;
"
    ::= {asspPerlModuleInfo 51}

iVTextUnidecode  OBJECT-TYPE
    SYNTAX      OCTET STRING
    MAX-ACCESS  read-only
    STATUS      current
    DESCRIPTION
"
installed module version
"
    ::= {TextUnidecode 1}

rVTextUnidecode  OBJECT-TYPE
    SYNTAX      OCTET STRING
    MAX-ACCESS  read-only
    STATUS      current
    DESCRIPTION
"
required/recommended module version
"
    ::= {TextUnidecode 2}

iSTextUnidecode  OBJECT-TYPE
    SYNTAX      OCTET STRING
    MAX-ACCESS  read-only
    STATUS      current
    DESCRIPTION
"
module installation status
"
    ::= {TextUnidecode 3}

dUTextUnidecode  OBJECT-TYPE
    SYNTAX      OCTET STRING
    MAX-ACCESS  read-only
    STATUS      current
    DESCRIPTION
"
download URL for the module
"
    ::= {TextUnidecode 4}

ThreadQueue  OBJECT-TYPE
    SYNTAX      OCTET STRING
    MAX-ACCESS  read-only
    STATUS      current
    DESCRIPTION
"
ASSP Perl module information for Thread::Queue;
"
    ::= {asspPerlModuleInfo 52}

iVThreadQueue  OBJECT-TYPE
    SYNTAX      OCTET STRING
    MAX-ACCESS  read-only
    STATUS      current
    DESCRIPTION
"
installed module version
"
    ::= {ThreadQueue 1}

rVThreadQueue  OBJECT-TYPE
    SYNTAX      OCTET STRING
    MAX-ACCESS  read-only
    STATUS      current
    DESCRIPTION
"
required/recommended module version
"
    ::= {ThreadQueue 2}

iSThreadQueue  OBJECT-TYPE
    SYNTAX      OCTET STRING
    MAX-ACCESS  read-only
    STATUS      current
    DESCRIPTION
"
module installation status
"
    ::= {ThreadQueue 3}

dUThreadQueue  OBJECT-TYPE
    SYNTAX      OCTET STRING
    MAX-ACCESS  read-only
    STATUS      current
    DESCRIPTION
"
download URL for the module
"
    ::= {ThreadQueue 4}

ThreadSemaphore  OBJECT-TYPE
    SYNTAX      OCTET STRING
    MAX-ACCESS  read-only
    STATUS      current
    DESCRIPTION
"
ASSP Perl module information for Thread::Semaphore;
"
    ::= {asspPerlModuleInfo 53}

iVThreadSemaphore  OBJECT-TYPE
    SYNTAX      OCTET STRING
    MAX-ACCESS  read-only
    STATUS      current
    DESCRIPTION
"
installed module version
"
    ::= {ThreadSemaphore 1}

rVThreadSemaphore  OBJECT-TYPE
    SYNTAX      OCTET STRING
    MAX-ACCESS  read-only
    STATUS      current
    DESCRIPTION
"
required/recommended module version
"
    ::= {ThreadSemaphore 2}

iSThreadSemaphore  OBJECT-TYPE
    SYNTAX      OCTET STRING
    MAX-ACCESS  read-only
    STATUS      current
    DESCRIPTION
"
module installation status
"
    ::= {ThreadSemaphore 3}

dUThreadSemaphore  OBJECT-TYPE
    SYNTAX      OCTET STRING
    MAX-ACCESS  read-only
    STATUS      current
    DESCRIPTION
"
download URL for the module
"
    ::= {ThreadSemaphore 4}

ThreadState  OBJECT-TYPE
    SYNTAX      OCTET STRING
    MAX-ACCESS  read-only
    STATUS      current
    DESCRIPTION
"
ASSP Perl module information for Thread::State;
"
    ::= {asspPerlModuleInfo 54}

iVThreadState  OBJECT-TYPE
    SYNTAX      OCTET STRING
    MAX-ACCESS  read-only
    STATUS      current
    DESCRIPTION
"
installed module version
"
    ::= {ThreadState 1}

rVThreadState  OBJECT-TYPE
    SYNTAX      OCTET STRING
    MAX-ACCESS  read-only
    STATUS      current
    DESCRIPTION
"
required/recommended module version
"
    ::= {ThreadState 2}

iSThreadState  OBJECT-TYPE
    SYNTAX      OCTET STRING
    MAX-ACCESS  read-only
    STATUS      current
    DESCRIPTION
"
module installation status
"
    ::= {ThreadState 3}

dUThreadState  OBJECT-TYPE
    SYNTAX      OCTET STRING
    MAX-ACCESS  read-only
    STATUS      current
    DESCRIPTION
"
download URL for the module
"
    ::= {ThreadState 4}

TieRDBM  OBJECT-TYPE
    SYNTAX      OCTET STRING
    MAX-ACCESS  read-only
    STATUS      current
    DESCRIPTION
"
ASSP Perl module information for Tie::RDBM;
"
    ::= {asspPerlModuleInfo 55}

iVTieRDBM  OBJECT-TYPE
    SYNTAX      OCTET STRING
    MAX-ACCESS  read-only
    STATUS      current
    DESCRIPTION
"
installed module version
"
    ::= {TieRDBM 1}

rVTieRDBM  OBJECT-TYPE
    SYNTAX      OCTET STRING
    MAX-ACCESS  read-only
    STATUS      current
    DESCRIPTION
"
required/recommended module version
"
    ::= {TieRDBM 2}

iSTieRDBM  OBJECT-TYPE
    SYNTAX      OCTET STRING
    MAX-ACCESS  read-only
    STATUS      current
    DESCRIPTION
"
module installation status
"
    ::= {TieRDBM 3}

dUTieRDBM  OBJECT-TYPE
    SYNTAX      OCTET STRING
    MAX-ACCESS  read-only
    STATUS      current
    DESCRIPTION
"
download URL for the module
"
    ::= {TieRDBM 4}

TimeHiRes  OBJECT-TYPE
    SYNTAX      OCTET STRING
    MAX-ACCESS  read-only
    STATUS      current
    DESCRIPTION
"
ASSP Perl module information for Time::HiRes;
"
    ::= {asspPerlModuleInfo 56}

iVTimeHiRes  OBJECT-TYPE
    SYNTAX      OCTET STRING
    MAX-ACCESS  read-only
    STATUS      current
    DESCRIPTION
"
installed module version
"
    ::= {TimeHiRes 1}

rVTimeHiRes  OBJECT-TYPE
    SYNTAX      OCTET STRING
    MAX-ACCESS  read-only
    STATUS      current
    DESCRIPTION
"
required/recommended module version
"
    ::= {TimeHiRes 2}

iSTimeHiRes  OBJECT-TYPE
    SYNTAX      OCTET STRING
    MAX-ACCESS  read-only
    STATUS      current
    DESCRIPTION
"
module installation status
"
    ::= {TimeHiRes 3}

dUTimeHiRes  OBJECT-TYPE
    SYNTAX      OCTET STRING
    MAX-ACCESS  read-only
    STATUS      current
    DESCRIPTION
"
download URL for the module
"
    ::= {TimeHiRes 4}

UnicodeGCString  OBJECT-TYPE
    SYNTAX      OCTET STRING
    MAX-ACCESS  read-only
    STATUS      current
    DESCRIPTION
"
ASSP Perl module information for Unicode::GCString;
"
    ::= {asspPerlModuleInfo 57}

iVUnicodeGCString  OBJECT-TYPE
    SYNTAX      OCTET STRING
    MAX-ACCESS  read-only
    STATUS      current
    DESCRIPTION
"
installed module version
"
    ::= {UnicodeGCString 1}

rVUnicodeGCString  OBJECT-TYPE
    SYNTAX      OCTET STRING
    MAX-ACCESS  read-only
    STATUS      current
    DESCRIPTION
"
required/recommended module version
"
    ::= {UnicodeGCString 2}

iSUnicodeGCString  OBJECT-TYPE
    SYNTAX      OCTET STRING
    MAX-ACCESS  read-only
    STATUS      current
    DESCRIPTION
"
module installation status
"
    ::= {UnicodeGCString 3}

dUUnicodeGCString  OBJECT-TYPE
    SYNTAX      OCTET STRING
    MAX-ACCESS  read-only
    STATUS      current
    DESCRIPTION
"
download URL for the module
"
    ::= {UnicodeGCString 4}

Win32APIOutputDebugString  OBJECT-TYPE
    SYNTAX      OCTET STRING
    MAX-ACCESS  read-only
    STATUS      current
    DESCRIPTION
"
ASSP Perl module information for Win32::API::OutputDebugString;
"
    ::= {asspPerlModuleInfo 58}

iVWin32APIOutputDebugString  OBJECT-TYPE
    SYNTAX      OCTET STRING
    MAX-ACCESS  read-only
    STATUS      current
    DESCRIPTION
"
installed module version
"
    ::= {Win32APIOutputDebugString 1}

rVWin32APIOutputDebugString  OBJECT-TYPE
    SYNTAX      OCTET STRING
    MAX-ACCESS  read-only
    STATUS      current
    DESCRIPTION
"
required/recommended module version
"
    ::= {Win32APIOutputDebugString 2}

iSWin32APIOutputDebugString  OBJECT-TYPE
    SYNTAX      OCTET STRING
    MAX-ACCESS  read-only
    STATUS      current
    DESCRIPTION
"
module installation status
"
    ::= {Win32APIOutputDebugString 3}

dUWin32APIOutputDebugString  OBJECT-TYPE
    SYNTAX      OCTET STRING
    MAX-ACCESS  read-only
    STATUS      current
    DESCRIPTION
"
download URL for the module
"
    ::= {Win32APIOutputDebugString 4}

Win32Daemon  OBJECT-TYPE
    SYNTAX      OCTET STRING
    MAX-ACCESS  read-only
    STATUS      current
    DESCRIPTION
"
ASSP Perl module information for Win32::Daemon;
"
    ::= {asspPerlModuleInfo 59}

iVWin32Daemon  OBJECT-TYPE
    SYNTAX      OCTET STRING
    MAX-ACCESS  read-only
    STATUS      current
    DESCRIPTION
"
installed module version
"
    ::= {Win32Daemon 1}

rVWin32Daemon  OBJECT-TYPE
    SYNTAX      OCTET STRING
    MAX-ACCESS  read-only
    STATUS      current
    DESCRIPTION
"
required/recommended module version
"
    ::= {Win32Daemon 2}

iSWin32Daemon  OBJECT-TYPE
    SYNTAX      OCTET STRING
    MAX-ACCESS  read-only
    STATUS      current
    DESCRIPTION
"
module installation status
"
    ::= {Win32Daemon 3}

dUWin32Daemon  OBJECT-TYPE
    SYNTAX      OCTET STRING
    MAX-ACCESS  read-only
    STATUS      current
    DESCRIPTION
"
download URL for the module
"
    ::= {Win32Daemon 4}

Win32Unicode  OBJECT-TYPE
    SYNTAX      OCTET STRING
    MAX-ACCESS  read-only
    STATUS      current
    DESCRIPTION
"
ASSP Perl module information for Win32::Unicode;
"
    ::= {asspPerlModuleInfo 60}

iVWin32Unicode  OBJECT-TYPE
    SYNTAX      OCTET STRING
    MAX-ACCESS  read-only
    STATUS      current
    DESCRIPTION
"
installed module version
"
    ::= {Win32Unicode 1}

rVWin32Unicode  OBJECT-TYPE
    SYNTAX      OCTET STRING
    MAX-ACCESS  read-only
    STATUS      current
    DESCRIPTION
"
required/recommended module version
"
    ::= {Win32Unicode 2}

iSWin32Unicode  OBJECT-TYPE
    SYNTAX      OCTET STRING
    MAX-ACCESS  read-only
    STATUS      current
    DESCRIPTION
"
module installation status
"
    ::= {Win32Unicode 3}

dUWin32Unicode  OBJECT-TYPE
    SYNTAX      OCTET STRING
    MAX-ACCESS  read-only
    STATUS      current
    DESCRIPTION
"
download URL for the module
"
    ::= {Win32Unicode 4}

threads  OBJECT-TYPE
    SYNTAX      OCTET STRING
    MAX-ACCESS  read-only
    STATUS      current
    DESCRIPTION
"
ASSP Perl module information for threads;
"
    ::= {asspPerlModuleInfo 61}

iVthreads  OBJECT-TYPE
    SYNTAX      OCTET STRING
    MAX-ACCESS  read-only
    STATUS      current
    DESCRIPTION
"
installed module version
"
    ::= {threads 1}

rVthreads  OBJECT-TYPE
    SYNTAX      OCTET STRING
    MAX-ACCESS  read-only
    STATUS      current
    DESCRIPTION
"
required/recommended module version
"
    ::= {threads 2}

iSthreads  OBJECT-TYPE
    SYNTAX      OCTET STRING
    MAX-ACCESS  read-only
    STATUS      current
    DESCRIPTION
"
module installation status
"
    ::= {threads 3}

dUthreads  OBJECT-TYPE
    SYNTAX      OCTET STRING
    MAX-ACCESS  read-only
    STATUS      current
    DESCRIPTION
"
download URL for the module
"
    ::= {threads 4}

threadsshared  OBJECT-TYPE
    SYNTAX      OCTET STRING
    MAX-ACCESS  read-only
    STATUS      current
    DESCRIPTION
"
ASSP Perl module information for threads::shared;
"
    ::= {asspPerlModuleInfo 62}

iVthreadsshared  OBJECT-TYPE
    SYNTAX      OCTET STRING
    MAX-ACCESS  read-only
    STATUS      current
    DESCRIPTION
"
installed module version
"
    ::= {threadsshared 1}

rVthreadsshared  OBJECT-TYPE
    SYNTAX      OCTET STRING
    MAX-ACCESS  read-only
    STATUS      current
    DESCRIPTION
"
required/recommended module version
"
    ::= {threadsshared 2}

iSthreadsshared  OBJECT-TYPE
    SYNTAX      OCTET STRING
    MAX-ACCESS  read-only
    STATUS      current
    DESCRIPTION
"
module installation status
"
    ::= {threadsshared 3}

dUthreadsshared  OBJECT-TYPE
    SYNTAX      OCTET STRING
    MAX-ACCESS  read-only
    STATUS      current
    DESCRIPTION
"
download URL for the module
"
    ::= {threadsshared 4}

currentDCC  OBJECT-TYPE
    SYNTAX      Counter32
    MAX-ACCESS  read-only
    STATUS      current
    DESCRIPTION
"
ASSP_DCC Plugin
"
    ::= {currentStats 0}

currentdkim  OBJECT-TYPE
    SYNTAX      Counter32
    MAX-ACCESS  read-only
    STATUS      current
    DESCRIPTION
"
DKIM Signature
"
    ::= {currentStats 1}

currentviri  OBJECT-TYPE
    SYNTAX      Counter32
    MAX-ACCESS  read-only
    STATUS      current
    DESCRIPTION
"
Bad Attachments
"
    ::= {currentStats 2}

currentRazor  OBJECT-TYPE
    SYNTAX      Counter32
    MAX-ACCESS  read-only
    STATUS      current
    DESCRIPTION
"
ASSP_Razor Plugin
"
    ::= {currentStats 3}

currentbhams  OBJECT-TYPE
    SYNTAX      Counter32
    MAX-ACCESS  read-only
    STATUS      current
    DESCRIPTION
"
Message OK
"
    ::= {currentStats 4}

currentbombs  OBJECT-TYPE
    SYNTAX      Counter32
    MAX-ACCESS  read-only
    STATUS      current
    DESCRIPTION
"
Bomb Regex
"
    ::= {currentStats 5}

currentbspams  OBJECT-TYPE
    SYNTAX      Counter32
    MAX-ACCESS  read-only
    STATUS      current
    DESCRIPTION
"
Bayesian/HMM Spams
"
    ::= {currentStats 6}

currentcpuAvg  OBJECT-TYPE
    SYNTAX      Counter32
    MAX-ACCESS  read-only
    STATUS      current
    DESCRIPTION
"
CPU Usage
"
    ::= {currentStats 7}

currentlocals  OBJECT-TYPE
    SYNTAX      Counter32
    MAX-ACCESS  read-only
    STATUS      current
    DESCRIPTION
"
Local
"
    ::= {currentStats 8}

currentuptime  OBJECT-TYPE
    SYNTAX      OCTET STRING
    MAX-ACCESS  read-only
    STATUS      current
    DESCRIPTION
"
ASSP Proxy Uptime
"
    ::= {currentStats 9}

currentwhites  OBJECT-TYPE
    SYNTAX      Counter32
    MAX-ACCESS  read-only
    STATUS      current
    DESCRIPTION
"
Whitelisted
"
    ::= {currentStats 10}

currentmailCount  OBJECT-TYPE
    SYNTAX      Counter32
    MAX-ACCESS  read-only
    STATUS      current
    DESCRIPTION
"

"
    ::= {currentStats 11}

currentadmConn  OBJECT-TYPE
    SYNTAX      Counter32
    MAX-ACCESS  read-only
    STATUS      current
    DESCRIPTION
"
Admin Connections Accepted
"
    ::= {currentStats 12}

currentcpuTime  OBJECT-TYPE
    SYNTAX      Counter32
    MAX-ACCESS  read-only
    STATUS      current
    DESCRIPTION
"

"
    ::= {currentStats 13}

currentdamping  OBJECT-TYPE
    SYNTAX      Counter32
    MAX-ACCESS  read-only
    STATUS      current
    DESCRIPTION
"
SMTP Connection damping
"
    ::= {currentStats 14}

currentdkimpre  OBJECT-TYPE
    SYNTAX      Counter32
    MAX-ACCESS  read-only
    STATUS      current
    DESCRIPTION
"
DKIM pre Check
"
    ::= {currentStats 15}

currentscripts  OBJECT-TYPE
    SYNTAX      Counter32
    MAX-ACCESS  read-only
    STATUS      current
    DESCRIPTION
"
Scripts
"
    ::= {currentStats 16}

currentdamptime  OBJECT-TYPE
    SYNTAX      OCTET STRING
    MAX-ACCESS  read-only
    STATUS      current
    DESCRIPTION
"
stolen time by damping
"
    ::= {currentStats 18}

currentpbdenied  OBJECT-TYPE
    SYNTAX      Counter32
    MAX-ACCESS  read-only
    STATUS      current
    DESCRIPTION
"
Penalty Box
"
    ::= {currentStats 20}

currentrblfails  OBJECT-TYPE
    SYNTAX      Counter32
    MAX-ACCESS  read-only
    STATUS      current
    DESCRIPTION
"
RBL Failures
"
    ::= {currentStats 21}

currentsmtpConn  OBJECT-TYPE
    SYNTAX      Counter32
    MAX-ACCESS  read-only
    STATUS      current
    DESCRIPTION
"
Accepted Logged SMTP Connections
"
    ::= {currentStats 22}

currentspffails  OBJECT-TYPE
    SYNTAX      Counter32
    MAX-ACCESS  read-only
    STATUS      current
    DESCRIPTION
"
SPF Failures
"
    ::= {currentStats 23}

currentstatConn  OBJECT-TYPE
    SYNTAX      Counter32
    MAX-ACCESS  read-only
    STATUS      current
    DESCRIPTION
"
Stat Connections Accepted
"
    ::= {currentStats 24}

currentavgdamped  OBJECT-TYPE
    SYNTAX      Counter32
    MAX-ACCESS  read-only
    STATUS      current
    DESCRIPTION
"

"
    ::= {currentStats 25}

currentbombBlack  OBJECT-TYPE
    SYNTAX      Counter32
    MAX-ACCESS  read-only
    STATUS      current
    DESCRIPTION
"
Black Regex
"
    ::= {currentStats 26}

currentmsgNoRcpt  OBJECT-TYPE
    SYNTAX      Counter32
    MAX-ACCESS  read-only
    STATUS      current
    DESCRIPTION
"
Empty Recipient
"
    ::= {currentStats 27}

currentmsgPerDay  OBJECT-TYPE
    SYNTAX      Counter32
    MAX-ACCESS  read-only
    STATUS      current
    DESCRIPTION
"

"
    ::= {currentStats 28}

currentmsgverify  OBJECT-TYPE
    SYNTAX      Counter32
    MAX-ACCESS  read-only
    STATUS      current
    DESCRIPTION
"
uuencoded and Header error
"
    ::= {currentStats 29}

currentpbextreme  OBJECT-TYPE
    SYNTAX      Counter32
    MAX-ACCESS  read-only
    STATUS      current
    DESCRIPTION
"
PenaltyBox Extreme
"
    ::= {currentStats 30}

currentpreHeader  OBJECT-TYPE
    SYNTAX      Counter32
    MAX-ACCESS  read-only
    STATUS      current
    DESCRIPTION
"
early (pre)Header
"
    ::= {currentStats 31}

currentsbblocked  OBJECT-TYPE
    SYNTAX      Counter32
    MAX-ACCESS  read-only
    STATUS      current
    DESCRIPTION
"
CountryCode blocked
"
    ::= {currentStats 33}

currentspamlover  OBJECT-TYPE
    SYNTAX      Counter32
    MAX-ACCESS  read-only
    STATUS      current
    DESCRIPTION
"
Spamlover Spams Passed
"
    ::= {currentStats 34}

currentstarttime  OBJECT-TYPE
    SYNTAX      Counter32
    MAX-ACCESS  read-only
    STATUS      current
    DESCRIPTION
"

"
    ::= {currentStats 35}

currentstatstart  OBJECT-TYPE
    SYNTAX      OCTET STRING
    MAX-ACCESS  read-only
    STATUS      current
    DESCRIPTION
"

"
    ::= {currentStats 36}

currentAUTHErrors  OBJECT-TYPE
    SYNTAX      Counter32
    MAX-ACCESS  read-only
    STATUS      current
    DESCRIPTION
"
By AUTH Errors Count
"
    ::= {currentStats 37}

currentbatvErrors  OBJECT-TYPE
    SYNTAX      Counter32
    MAX-ACCESS  read-only
    STATUS      current
    DESCRIPTION
"
BATV Errors
"
    ::= {currentStats 38}

currentbombSender  OBJECT-TYPE
    SYNTAX      Counter32
    MAX-ACCESS  read-only
    STATUS      current
    DESCRIPTION
"
Bomb - Sender/Header Regex
"
    ::= {currentStats 39}

currentforgedHelo  OBJECT-TYPE
    SYNTAX      Counter32
    MAX-ACCESS  read-only
    STATUS      current
    DESCRIPTION
"
HELO Forged
"
    ::= {currentStats 40}

currenthelolisted  OBJECT-TYPE
    SYNTAX      Counter32
    MAX-ACCESS  read-only
    STATUS      current
    DESCRIPTION
"
HELO Blacklisted
"
    ::= {currentStats 41}

currentmsgDelayed  OBJECT-TYPE
    SYNTAX      Counter32
    MAX-ACCESS  read-only
    STATUS      current
    DESCRIPTION
"
Delayed/Greylisted
"
    ::= {currentStats 42}

currentmsgscoring  OBJECT-TYPE
    SYNTAX      Counter32
    MAX-ACCESS  read-only
    STATUS      current
    DESCRIPTION
"
Message Scoring
"
    ::= {currentStats 43}

currentmxaMissing  OBJECT-TYPE
    SYNTAX      Counter32
    MAX-ACCESS  read-only
    STATUS      current
    DESCRIPTION
"
Missing MX and A Record
"
    ::= {currentStats 44}

currentnextUpload  OBJECT-TYPE
    SYNTAX      Counter32
    MAX-ACCESS  read-only
    STATUS      current
    DESCRIPTION
"

"
    ::= {currentStats 45}

currentpctBlocked  OBJECT-TYPE
    SYNTAX      Counter32
    MAX-ACCESS  read-only
    STATUS      current
    DESCRIPTION
"
Non-Local Mail Blocked
"
    ::= {currentStats 46}

currentptrInvalid  OBJECT-TYPE
    SYNTAX      Counter32
    MAX-ACCESS  read-only
    STATUS      current
    DESCRIPTION
"
Invalid PTR Record
"
    ::= {currentStats 47}

currentptrMissing  OBJECT-TYPE
    SYNTAX      Counter32
    MAX-ACCESS  read-only
    STATUS      current
    DESCRIPTION
"
Missing PTR Record
"
    ::= {currentStats 48}

currentspambucket  OBJECT-TYPE
    SYNTAX      Counter32
    MAX-ACCESS  read-only
    STATUS      current
    DESCRIPTION
"
Spam Collected Messages
"
    ::= {currentStats 50}

currenturiblfails  OBJECT-TYPE
    SYNTAX      Counter32
    MAX-ACCESS  read-only
    STATUS      current
    DESCRIPTION
"
URIBL Failures
"
    ::= {currentStats 51}

currentblacklisted  OBJECT-TYPE
    SYNTAX      Counter32
    MAX-ACCESS  read-only
    STATUS      current
    DESCRIPTION
"
Domains Blacklisted
"
    ::= {currentStats 52}

currentcpuBusyTime  OBJECT-TYPE
    SYNTAX      Counter32
    MAX-ACCESS  read-only
    STATUS      current
    DESCRIPTION
"

"
    ::= {currentStats 53}

currentinvalidHelo  OBJECT-TYPE
    SYNTAX      Counter32
    MAX-ACCESS  read-only
    STATUS      current
    DESCRIPTION
"
HELO Invalid
"
    ::= {currentStats 54}

currentpenaltytrap  OBJECT-TYPE
    SYNTAX      Counter32
    MAX-ACCESS  read-only
    STATUS      current
    DESCRIPTION
"
Penalty Trap Messages
"
    ::= {currentStats 55}

currentrcptDelayed  OBJECT-TYPE
    SYNTAX      Counter32
    MAX-ACCESS  read-only
    STATUS      current
    DESCRIPTION
"
Delayed Recipients
"
    ::= {currentStats 56}

currentsmtpConnSSL  OBJECT-TYPE
    SYNTAX      Counter32
    MAX-ACCESS  read-only
    STATUS      current
    DESCRIPTION
"
SSL-Port SMTP Connections
"
    ::= {currentStats 57}

currentsmtpConnTLS  OBJECT-TYPE
    SYNTAX      Counter32
    MAX-ACCESS  read-only
    STATUS      current
    DESCRIPTION
"
STARTTLS SMTP Connections
"
    ::= {currentStats 58}

currentcrashAnalyze  OBJECT-TYPE
    SYNTAX      Counter32
    MAX-ACCESS  read-only
    STATUS      current
    DESCRIPTION
"
Crash Analyzer
"
    ::= {currentStats 60}

currentmsgMaxErrors  OBJECT-TYPE
    SYNTAX      Counter32
    MAX-ACCESS  read-only
    STATUS      current
    DESCRIPTION
"
Max Errors Exceeded
"
    ::= {currentStats 61}

currentnoprocessing  OBJECT-TYPE
    SYNTAX      Counter32
    MAX-ACCESS  read-only
    STATUS      current
    DESCRIPTION
"
Noprocessing
"
    ::= {currentStats 62}

currentviridetected  OBJECT-TYPE
    SYNTAX      Counter32
    MAX-ACCESS  read-only
    STATUS      current
    DESCRIPTION
"
Viruses Detected
"
    ::= {currentStats 63}

currentadmConnDenied  OBJECT-TYPE
    SYNTAX      Counter32
    MAX-ACCESS  read-only
    STATUS      current
    DESCRIPTION
"
Admin Connections Rejected
"
    ::= {currentStats 64}

currentrcptEmbargoed  OBJECT-TYPE
    SYNTAX      Counter32
    MAX-ACCESS  read-only
    STATUS      current
    DESCRIPTION
"
Embargoed Recipients
"
    ::= {currentStats 65}

currentrcptReportHam  OBJECT-TYPE
    SYNTAX      Counter32
    MAX-ACCESS  read-only
    STATUS      current
    DESCRIPTION
"
Ham Reports
"
    ::= {currentStats 66}

currentrcptSpamLover  OBJECT-TYPE
    SYNTAX      Counter32
    MAX-ACCESS  read-only
    STATUS      current
    DESCRIPTION
"
Spam-Lover Recipients
"
    ::= {currentStats 67}

currentrcptUnchecked  OBJECT-TYPE
    SYNTAX      Counter32
    MAX-ACCESS  read-only
    STATUS      current
    DESCRIPTION
"
Unchecked Recipients
"
    ::= {currentStats 68}

currentrcptValidated  OBJECT-TYPE
    SYNTAX      Counter32
    MAX-ACCESS  read-only
    STATUS      current
    DESCRIPTION
"
Validated Recipients
"
    ::= {currentStats 69}

currentsmtpConnLimit  OBJECT-TYPE
    SYNTAX      Counter32
    MAX-ACCESS  read-only
    STATUS      current
    DESCRIPTION
"
Overall Limits
"
    ::= {currentStats 70}

currentdenyConnection  OBJECT-TYPE
    SYNTAX      Counter32
    MAX-ACCESS  read-only
    STATUS      current
    DESCRIPTION
"
Deny Connection
"
    ::= {currentStats 73}

currentlocalFrequency  OBJECT-TYPE
    SYNTAX      Counter32
    MAX-ACCESS  read-only
    STATUS      current
    DESCRIPTION
"
local frequency
"
    ::= {currentStats 74}

currentmsgNoSRSBounce  OBJECT-TYPE
    SYNTAX      Counter32
    MAX-ACCESS  read-only
    STATUS      current
    DESCRIPTION
"
Unsigned SRS Bounces
"
    ::= {currentStats 75}

currentrcptReportSpam  OBJECT-TYPE
    SYNTAX      Counter32
    MAX-ACCESS  read-only
    STATUS      current
    DESCRIPTION
"
Spam Reports
"
    ::= {currentStats 76}

currentrcptSpamBucket  OBJECT-TYPE
    SYNTAX      Counter32
    MAX-ACCESS  read-only
    STATUS      current
    DESCRIPTION
"
Spam Bucketed Recipients
"
    ::= {currentStats 77}

currentsmtpConnDenied  OBJECT-TYPE
    SYNTAX      Counter32
    MAX-ACCESS  read-only
    STATUS      current
    DESCRIPTION
"
Denied SMTP Connections (enforced Extreme)
"
    ::= {currentStats 78}

currentstatConnDenied  OBJECT-TYPE
    SYNTAX      Counter32
    MAX-ACCESS  read-only
    STATUS      current
    DESCRIPTION
"
Stat Connections Rejected
"
    ::= {currentStats 79}

currentdelayConnection  OBJECT-TYPE
    SYNTAX      Counter32
    MAX-ACCESS  read-only
    STATUS      current
    DESCRIPTION
"
By Delay on PB
"
    ::= {currentStats 80}

currentdenyConnectionA  OBJECT-TYPE
    SYNTAX      Counter32
    MAX-ACCESS  read-only
    STATUS      current
    DESCRIPTION
"
Denied SMTP Connections (strict)
"
    ::= {currentStats 81}

currentrcptDelayedLate  OBJECT-TYPE
    SYNTAX      Counter32
    MAX-ACCESS  read-only
    STATUS      current
    DESCRIPTION
"
Delayed (Late) Recipients
"
    ::= {currentStats 82}

currentrcptNonexistent  OBJECT-TYPE
    SYNTAX      Counter32
    MAX-ACCESS  read-only
    STATUS      current
    DESCRIPTION
"
Nonexistent Recipients
"
    ::= {currentStats 83}

currentrcptUnprocessed  OBJECT-TYPE
    SYNTAX      Counter32
    MAX-ACCESS  read-only
    STATUS      current
    DESCRIPTION
"
Noprocessed Recipients
"
    ::= {currentStats 84}

currentrcptWhitelisted  OBJECT-TYPE
    SYNTAX      Counter32
    MAX-ACCESS  read-only
    STATUS      current
    DESCRIPTION
"
Whitelisted Recipients
"
    ::= {currentStats 85}

currentsmtpConnLimitIP  OBJECT-TYPE
    SYNTAX      Counter32
    MAX-ACCESS  read-only
    STATUS      current
    DESCRIPTION
"
By IP Limits
"
    ::= {currentStats 86}

currentsmtpSameSubject  OBJECT-TYPE
    SYNTAX      Counter32
    MAX-ACCESS  read-only
    STATUS      current
    DESCRIPTION
"
By Same Subjects Limits
"
    ::= {currentStats 87}

currentmsgMSGIDtrErrors  OBJECT-TYPE
    SYNTAX      Counter32
    MAX-ACCESS  read-only
    STATUS      current
    DESCRIPTION
"
MSGID signing Errors
"
    ::= {currentStats 89}

currentmsgMaxVRFYErrors  OBJECT-TYPE
    SYNTAX      Counter32
    MAX-ACCESS  read-only
    STATUS      current
    DESCRIPTION
"
Max VRFY Errors
"
    ::= {currentStats 90}

currentsmtpConnDomainIP  OBJECT-TYPE
    SYNTAX      Counter32
    MAX-ACCESS  read-only
    STATUS      current
    DESCRIPTION
"
By Domain IP Limits
"
    ::= {currentStats 92}

currentinternaladdresses  OBJECT-TYPE
    SYNTAX      Counter32
    MAX-ACCESS  read-only
    STATUS      current
    DESCRIPTION
"
Invalid Internal Mail
"
    ::= {currentStats 93}

currentrcptAcceptedLocal  OBJECT-TYPE
    SYNTAX      Counter32
    MAX-ACCESS  read-only
    STATUS      current
    DESCRIPTION
"
Local Recipients Accepted
"
    ::= {currentStats 94}

currentrcptRelayRejected  OBJECT-TYPE
    SYNTAX      Counter32
    MAX-ACCESS  read-only
    STATUS      current
    DESCRIPTION
"
Relay Attempts Rejected
"
    ::= {currentStats 98}

currentsmtpConnLimitFreq  OBJECT-TYPE
    SYNTAX      Counter32
    MAX-ACCESS  read-only
    STATUS      current
    DESCRIPTION
"
By IP Frequency Limits
"
    ::= {currentStats 99}

currentsmtpConnNotLogged  OBJECT-TYPE
    SYNTAX      Counter32
    MAX-ACCESS  read-only
    STATUS      current
    DESCRIPTION
"
Not Logged SMTP Connections
"
    ::= {currentStats 100}

currentrcptDelayedExpired  OBJECT-TYPE
    SYNTAX      Counter32
    MAX-ACCESS  read-only
    STATUS      current
    DESCRIPTION
"
Delayed (Expired) Recipients
"
    ::= {currentStats 102}

currentrcptNotWhitelisted  OBJECT-TYPE
    SYNTAX      Counter32
    MAX-ACCESS  read-only
    STATUS      current
    DESCRIPTION
"
Not Whitelisted Recipients
"
    ::= {currentStats 103}

currentsenderInvalidLocals  OBJECT-TYPE
    SYNTAX      Counter32
    MAX-ACCESS  read-only
    STATUS      current
    DESCRIPTION
"
Invalid Sender
"
    ::= {currentStats 105}

currentsmtpConnIdleTimeout  OBJECT-TYPE
    SYNTAX      Counter32
    MAX-ACCESS  read-only
    STATUS      current
    DESCRIPTION
"
SMTP Connections Timeout
"
    ::= {currentStats 106}

currentmsgBackscatterErrors  OBJECT-TYPE
    SYNTAX      Counter32
    MAX-ACCESS  read-only
    STATUS      current
    DESCRIPTION
"
BackScatter Errors
"
    ::= {currentStats 107}

currentrcptReportRedlistAdd  OBJECT-TYPE
    SYNTAX      Counter32
    MAX-ACCESS  read-only
    STATUS      current
    DESCRIPTION
"
Redlist Additions
"
    ::= {currentStats 108}

currentrcptReportWhitelistAdd  OBJECT-TYPE
    SYNTAX      Counter32
    MAX-ACCESS  read-only
    STATUS      current
    DESCRIPTION
"
Whitelist Additions
"
    ::= {currentStats 111}

currentsmtpConcurrentSessions  OBJECT-TYPE
    SYNTAX      Counter32
    MAX-ACCESS  read-only
    STATUS      current
    DESCRIPTION
"

"
    ::= {currentStats 112}

currentsmtpConnSSLIdleTimeout  OBJECT-TYPE
    SYNTAX      Counter32
    MAX-ACCESS  read-only
    STATUS      current
    DESCRIPTION
"
SMTP SSL-Port-Connections Timeout
"
    ::= {currentStats 113}

currentsmtpConnTLSIdleTimeout  OBJECT-TYPE
    SYNTAX      Counter32
    MAX-ACCESS  read-only
    STATUS      current
    DESCRIPTION
"
SMTP STARTTLS-Connections Timeout
"
    ::= {currentStats 114}

currentrcptReportRedlistRemove  OBJECT-TYPE
    SYNTAX      Counter32
    MAX-ACCESS  read-only
    STATUS      current
    DESCRIPTION
"
Redlist Deletions
"
    ::= {currentStats 115}

currentrcptReportWhitelistRemove  OBJECT-TYPE
    SYNTAX      Counter32
    MAX-ACCESS  read-only
    STATUS      current
    DESCRIPTION
"
Whitelist Deletions
"
    ::= {currentStats 116}

currentsmtpMaxConcurrentSessions  OBJECT-TYPE
    SYNTAX      Counter32
    MAX-ACCESS  read-only
    STATUS      current
    DESCRIPTION
"
Concurrent SMTP Sessions
"
    ::= {currentStats 117}

cumulDCC  OBJECT-TYPE
    SYNTAX      Counter32
    MAX-ACCESS  read-only
    STATUS      current
    DESCRIPTION
"
ASSP_DCC Plugin
"
    ::= {cumulativeStat 0}

cumuldkim  OBJECT-TYPE
    SYNTAX      Counter32
    MAX-ACCESS  read-only
    STATUS      current
    DESCRIPTION
"
DKIM Signature
"
    ::= {cumulativeStat 1}

cumulviri  OBJECT-TYPE
    SYNTAX      Counter32
    MAX-ACCESS  read-only
    STATUS      current
    DESCRIPTION
"
Bad Attachments
"
    ::= {cumulativeStat 2}

cumulRazor  OBJECT-TYPE
    SYNTAX      Counter32
    MAX-ACCESS  read-only
    STATUS      current
    DESCRIPTION
"
ASSP_Razor Plugin
"
    ::= {cumulativeStat 3}

cumulbhams  OBJECT-TYPE
    SYNTAX      Counter32
    MAX-ACCESS  read-only
    STATUS      current
    DESCRIPTION
"
Message OK
"
    ::= {cumulativeStat 4}

cumulbombs  OBJECT-TYPE
    SYNTAX      Counter32
    MAX-ACCESS  read-only
    STATUS      current
    DESCRIPTION
"
Bomb Regex
"
    ::= {cumulativeStat 5}

cumulbspams  OBJECT-TYPE
    SYNTAX      Counter32
    MAX-ACCESS  read-only
    STATUS      current
    DESCRIPTION
"
Bayesian/HMM Spams
"
    ::= {cumulativeStat 6}

cumulcpuAvg  OBJECT-TYPE
    SYNTAX      Counter32
    MAX-ACCESS  read-only
    STATUS      current
    DESCRIPTION
"
CPU Usage
"
    ::= {cumulativeStat 7}

cumullocals  OBJECT-TYPE
    SYNTAX      Counter32
    MAX-ACCESS  read-only
    STATUS      current
    DESCRIPTION
"
Local
"
    ::= {cumulativeStat 8}

cumuluptime  OBJECT-TYPE
    SYNTAX      OCTET STRING
    MAX-ACCESS  read-only
    STATUS      current
    DESCRIPTION
"
ASSP Proxy Uptime
"
    ::= {cumulativeStat 9}

cumulwhites  OBJECT-TYPE
    SYNTAX      Counter32
    MAX-ACCESS  read-only
    STATUS      current
    DESCRIPTION
"
Whitelisted
"
    ::= {cumulativeStat 10}

cumulmailCount  OBJECT-TYPE
    SYNTAX      Counter32
    MAX-ACCESS  read-only
    STATUS      current
    DESCRIPTION
"

"
    ::= {cumulativeStat 11}

cumuladmConn  OBJECT-TYPE
    SYNTAX      Counter32
    MAX-ACCESS  read-only
    STATUS      current
    DESCRIPTION
"
Admin Connections Accepted
"
    ::= {cumulativeStat 12}

cumulcpuTime  OBJECT-TYPE
    SYNTAX      Counter32
    MAX-ACCESS  read-only
    STATUS      current
    DESCRIPTION
"

"
    ::= {cumulativeStat 13}

cumuldamping  OBJECT-TYPE
    SYNTAX      Counter32
    MAX-ACCESS  read-only
    STATUS      current
    DESCRIPTION
"
SMTP Connection damping
"
    ::= {cumulativeStat 14}

cumuldkimpre  OBJECT-TYPE
    SYNTAX      Counter32
    MAX-ACCESS  read-only
    STATUS      current
    DESCRIPTION
"
DKIM pre Check
"
    ::= {cumulativeStat 15}

cumulscripts  OBJECT-TYPE
    SYNTAX      Counter32
    MAX-ACCESS  read-only
    STATUS      current
    DESCRIPTION
"
Scripts
"
    ::= {cumulativeStat 16}

cumulversion  OBJECT-TYPE
    SYNTAX      Counter32
    MAX-ACCESS  read-only
    STATUS      current
    DESCRIPTION
"

"
    ::= {cumulativeStat 17}

cumuldamptime  OBJECT-TYPE
    SYNTAX      OCTET STRING
    MAX-ACCESS  read-only
    STATUS      current
    DESCRIPTION
"
stolen time by damping
"
    ::= {cumulativeStat 18}

cumulpbdenied  OBJECT-TYPE
    SYNTAX      Counter32
    MAX-ACCESS  read-only
    STATUS      current
    DESCRIPTION
"
Penalty Box
"
    ::= {cumulativeStat 20}

cumulrblfails  OBJECT-TYPE
    SYNTAX      Counter32
    MAX-ACCESS  read-only
    STATUS      current
    DESCRIPTION
"
RBL Failures
"
    ::= {cumulativeStat 21}

cumulsmtpConn  OBJECT-TYPE
    SYNTAX      Counter32
    MAX-ACCESS  read-only
    STATUS      current
    DESCRIPTION
"
Accepted Logged SMTP Connections
"
    ::= {cumulativeStat 22}

cumulspffails  OBJECT-TYPE
    SYNTAX      Counter32
    MAX-ACCESS  read-only
    STATUS      current
    DESCRIPTION
"
SPF Failures
"
    ::= {cumulativeStat 23}

cumulstatConn  OBJECT-TYPE
    SYNTAX      Counter32
    MAX-ACCESS  read-only
    STATUS      current
    DESCRIPTION
"
Stat Connections Accepted
"
    ::= {cumulativeStat 24}

cumulavgdamped  OBJECT-TYPE
    SYNTAX      Counter32
    MAX-ACCESS  read-only
    STATUS      current
    DESCRIPTION
"

"
    ::= {cumulativeStat 25}

cumulbombBlack  OBJECT-TYPE
    SYNTAX      Counter32
    MAX-ACCESS  read-only
    STATUS      current
    DESCRIPTION
"
Black Regex
"
    ::= {cumulativeStat 26}

cumulmsgNoRcpt  OBJECT-TYPE
    SYNTAX      Counter32
    MAX-ACCESS  read-only
    STATUS      current
    DESCRIPTION
"
Empty Recipient
"
    ::= {cumulativeStat 27}

cumulmsgPerDay  OBJECT-TYPE
    SYNTAX      Counter32
    MAX-ACCESS  read-only
    STATUS      current
    DESCRIPTION
"

"
    ::= {cumulativeStat 28}

cumulmsgverify  OBJECT-TYPE
    SYNTAX      Counter32
    MAX-ACCESS  read-only
    STATUS      current
    DESCRIPTION
"
uuencoded and Header error
"
    ::= {cumulativeStat 29}

cumulpbextreme  OBJECT-TYPE
    SYNTAX      Counter32
    MAX-ACCESS  read-only
    STATUS      current
    DESCRIPTION
"
PenaltyBox Extreme
"
    ::= {cumulativeStat 30}

cumulpreHeader  OBJECT-TYPE
    SYNTAX      Counter32
    MAX-ACCESS  read-only
    STATUS      current
    DESCRIPTION
"
early (pre)Header
"
    ::= {cumulativeStat 31}

cumulsbblocked  OBJECT-TYPE
    SYNTAX      Counter32
    MAX-ACCESS  read-only
    STATUS      current
    DESCRIPTION
"
CountryCode blocked
"
    ::= {cumulativeStat 33}

cumulspamlover  OBJECT-TYPE
    SYNTAX      Counter32
    MAX-ACCESS  read-only
    STATUS      current
    DESCRIPTION
"
Spamlover Spams Passed
"
    ::= {cumulativeStat 34}

cumulstarttime  OBJECT-TYPE
    SYNTAX      Counter32
    MAX-ACCESS  read-only
    STATUS      current
    DESCRIPTION
"

"
    ::= {cumulativeStat 35}

cumulstatstart  OBJECT-TYPE
    SYNTAX      OCTET STRING
    MAX-ACCESS  read-only
    STATUS      current
    DESCRIPTION
"

"
    ::= {cumulativeStat 36}

cumulAUTHErrors  OBJECT-TYPE
    SYNTAX      Counter32
    MAX-ACCESS  read-only
    STATUS      current
    DESCRIPTION
"
By AUTH Errors Count
"
    ::= {cumulativeStat 37}

cumulbatvErrors  OBJECT-TYPE
    SYNTAX      Counter32
    MAX-ACCESS  read-only
    STATUS      current
    DESCRIPTION
"
BATV Errors
"
    ::= {cumulativeStat 38}

cumulbombSender  OBJECT-TYPE
    SYNTAX      Counter32
    MAX-ACCESS  read-only
    STATUS      current
    DESCRIPTION
"
Bomb - Sender/Header Regex
"
    ::= {cumulativeStat 39}

cumulforgedHelo  OBJECT-TYPE
    SYNTAX      Counter32
    MAX-ACCESS  read-only
    STATUS      current
    DESCRIPTION
"
HELO Forged
"
    ::= {cumulativeStat 40}

cumulhelolisted  OBJECT-TYPE
    SYNTAX      Counter32
    MAX-ACCESS  read-only
    STATUS      current
    DESCRIPTION
"
HELO Blacklisted
"
    ::= {cumulativeStat 41}

cumulmsgDelayed  OBJECT-TYPE
    SYNTAX      Counter32
    MAX-ACCESS  read-only
    STATUS      current
    DESCRIPTION
"
Delayed/Greylisted
"
    ::= {cumulativeStat 42}

cumulmsgscoring  OBJECT-TYPE
    SYNTAX      Counter32
    MAX-ACCESS  read-only
    STATUS      current
    DESCRIPTION
"
Message Scoring
"
    ::= {cumulativeStat 43}

cumulmxaMissing  OBJECT-TYPE
    SYNTAX      Counter32
    MAX-ACCESS  read-only
    STATUS      current
    DESCRIPTION
"
Missing MX and A Record
"
    ::= {cumulativeStat 44}

cumulnextUpload  OBJECT-TYPE
    SYNTAX      Counter32
    MAX-ACCESS  read-only
    STATUS      current
    DESCRIPTION
"

"
    ::= {cumulativeStat 45}

cumulpctBlocked  OBJECT-TYPE
    SYNTAX      Counter32
    MAX-ACCESS  read-only
    STATUS      current
    DESCRIPTION
"
Non-Local Mail Blocked
"
    ::= {cumulativeStat 46}

cumulptrInvalid  OBJECT-TYPE
    SYNTAX      Counter32
    MAX-ACCESS  read-only
    STATUS      current
    DESCRIPTION
"
Invalid PTR Record
"
    ::= {cumulativeStat 47}

cumulptrMissing  OBJECT-TYPE
    SYNTAX      Counter32
    MAX-ACCESS  read-only
    STATUS      current
    DESCRIPTION
"
Missing PTR Record
"
    ::= {cumulativeStat 48}

cumulspambucket  OBJECT-TYPE
    SYNTAX      Counter32
    MAX-ACCESS  read-only
    STATUS      current
    DESCRIPTION
"
Spam Collected Messages
"
    ::= {cumulativeStat 50}

cumuluriblfails  OBJECT-TYPE
    SYNTAX      Counter32
    MAX-ACCESS  read-only
    STATUS      current
    DESCRIPTION
"
URIBL Failures
"
    ::= {cumulativeStat 51}

cumulblacklisted  OBJECT-TYPE
    SYNTAX      Counter32
    MAX-ACCESS  read-only
    STATUS      current
    DESCRIPTION
"
Domains Blacklisted
"
    ::= {cumulativeStat 52}

cumulcpuBusyTime  OBJECT-TYPE
    SYNTAX      Counter32
    MAX-ACCESS  read-only
    STATUS      current
    DESCRIPTION
"

"
    ::= {cumulativeStat 53}

cumulinvalidHelo  OBJECT-TYPE
    SYNTAX      Counter32
    MAX-ACCESS  read-only
    STATUS      current
    DESCRIPTION
"
HELO Invalid
"
    ::= {cumulativeStat 54}

cumulpenaltytrap  OBJECT-TYPE
    SYNTAX      Counter32
    MAX-ACCESS  read-only
    STATUS      current
    DESCRIPTION
"
Penalty Trap Messages
"
    ::= {cumulativeStat 55}

cumulrcptDelayed  OBJECT-TYPE
    SYNTAX      Counter32
    MAX-ACCESS  read-only
    STATUS      current
    DESCRIPTION
"
Delayed Recipients
"
    ::= {cumulativeStat 56}

cumulsmtpConnSSL  OBJECT-TYPE
    SYNTAX      Counter32
    MAX-ACCESS  read-only
    STATUS      current
    DESCRIPTION
"
SSL-Port SMTP Connections
"
    ::= {cumulativeStat 57}

cumulsmtpConnTLS  OBJECT-TYPE
    SYNTAX      Counter32
    MAX-ACCESS  read-only
    STATUS      current
    DESCRIPTION
"
STARTTLS SMTP Connections
"
    ::= {cumulativeStat 58}

cumulcrashAnalyze  OBJECT-TYPE
    SYNTAX      Counter32
    MAX-ACCESS  read-only
    STATUS      current
    DESCRIPTION
"
Crash Analyzer
"
    ::= {cumulativeStat 60}

cumulmsgMaxErrors  OBJECT-TYPE
    SYNTAX      Counter32
    MAX-ACCESS  read-only
    STATUS      current
    DESCRIPTION
"
Max Errors Exceeded
"
    ::= {cumulativeStat 61}

cumulnoprocessing  OBJECT-TYPE
    SYNTAX      Counter32
    MAX-ACCESS  read-only
    STATUS      current
    DESCRIPTION
"
Noprocessing
"
    ::= {cumulativeStat 62}

cumulviridetected  OBJECT-TYPE
    SYNTAX      Counter32
    MAX-ACCESS  read-only
    STATUS      current
    DESCRIPTION
"
Viruses Detected
"
    ::= {cumulativeStat 63}

cumuladmConnDenied  OBJECT-TYPE
    SYNTAX      Counter32
    MAX-ACCESS  read-only
    STATUS      current
    DESCRIPTION
"
Admin Connections Rejected
"
    ::= {cumulativeStat 64}

cumulrcptEmbargoed  OBJECT-TYPE
    SYNTAX      Counter32
    MAX-ACCESS  read-only
    STATUS      current
    DESCRIPTION
"
Embargoed Recipients
"
    ::= {cumulativeStat 65}

cumulrcptReportHam  OBJECT-TYPE
    SYNTAX      Counter32
    MAX-ACCESS  read-only
    STATUS      current
    DESCRIPTION
"
Ham Reports
"
    ::= {cumulativeStat 66}

cumulrcptSpamLover  OBJECT-TYPE
    SYNTAX      Counter32
    MAX-ACCESS  read-only
    STATUS      current
    DESCRIPTION
"
Spam-Lover Recipients
"
    ::= {cumulativeStat 67}

cumulrcptUnchecked  OBJECT-TYPE
    SYNTAX      Counter32
    MAX-ACCESS  read-only
    STATUS      current
    DESCRIPTION
"
Unchecked Recipients
"
    ::= {cumulativeStat 68}

cumulrcptValidated  OBJECT-TYPE
    SYNTAX      Counter32
    MAX-ACCESS  read-only
    STATUS      current
    DESCRIPTION
"
Validated Recipients
"
    ::= {cumulativeStat 69}

cumulsmtpConnLimit  OBJECT-TYPE
    SYNTAX      Counter32
    MAX-ACCESS  read-only
    STATUS      current
    DESCRIPTION
"
Overall Limits
"
    ::= {cumulativeStat 70}

cumuldenyConnection  OBJECT-TYPE
    SYNTAX      Counter32
    MAX-ACCESS  read-only
    STATUS      current
    DESCRIPTION
"
Deny Connection
"
    ::= {cumulativeStat 73}

cumullocalFrequency  OBJECT-TYPE
    SYNTAX      Counter32
    MAX-ACCESS  read-only
    STATUS      current
    DESCRIPTION
"
local frequency
"
    ::= {cumulativeStat 74}

cumulmsgNoSRSBounce  OBJECT-TYPE
    SYNTAX      Counter32
    MAX-ACCESS  read-only
    STATUS      current
    DESCRIPTION
"
Unsigned SRS Bounces
"
    ::= {cumulativeStat 75}

cumulrcptReportSpam  OBJECT-TYPE
    SYNTAX      Counter32
    MAX-ACCESS  read-only
    STATUS      current
    DESCRIPTION
"
Spam Reports
"
    ::= {cumulativeStat 76}

cumulrcptSpamBucket  OBJECT-TYPE
    SYNTAX      Counter32
    MAX-ACCESS  read-only
    STATUS      current
    DESCRIPTION
"
Spam Bucketed Recipients
"
    ::= {cumulativeStat 77}

cumulsmtpConnDenied  OBJECT-TYPE
    SYNTAX      Counter32
    MAX-ACCESS  read-only
    STATUS      current
    DESCRIPTION
"
Denied SMTP Connections (enforced Extreme)
"
    ::= {cumulativeStat 78}

cumulstatConnDenied  OBJECT-TYPE
    SYNTAX      Counter32
    MAX-ACCESS  read-only
    STATUS      current
    DESCRIPTION
"
Stat Connections Rejected
"
    ::= {cumulativeStat 79}

cumuldelayConnection  OBJECT-TYPE
    SYNTAX      Counter32
    MAX-ACCESS  read-only
    STATUS      current
    DESCRIPTION
"
By Delay on PB
"
    ::= {cumulativeStat 80}

cumuldenyConnectionA  OBJECT-TYPE
    SYNTAX      Counter32
    MAX-ACCESS  read-only
    STATUS      current
    DESCRIPTION
"
Denied SMTP Connections (strict)
"
    ::= {cumulativeStat 81}

cumulrcptDelayedLate  OBJECT-TYPE
    SYNTAX      Counter32
    MAX-ACCESS  read-only
    STATUS      current
    DESCRIPTION
"
Delayed (Late) Recipients
"
    ::= {cumulativeStat 82}

cumulrcptNonexistent  OBJECT-TYPE
    SYNTAX      Counter32
    MAX-ACCESS  read-only
    STATUS      current
    DESCRIPTION
"
Nonexistent Recipients
"
    ::= {cumulativeStat 83}

cumulrcptUnprocessed  OBJECT-TYPE
    SYNTAX      Counter32
    MAX-ACCESS  read-only
    STATUS      current
    DESCRIPTION
"
Noprocessed Recipients
"
    ::= {cumulativeStat 84}

cumulrcptWhitelisted  OBJECT-TYPE
    SYNTAX      Counter32
    MAX-ACCESS  read-only
    STATUS      current
    DESCRIPTION
"
Whitelisted Recipients
"
    ::= {cumulativeStat 85}

cumulsmtpConnLimitIP  OBJECT-TYPE
    SYNTAX      Counter32
    MAX-ACCESS  read-only
    STATUS      current
    DESCRIPTION
"
By IP Limits
"
    ::= {cumulativeStat 86}

cumulsmtpSameSubject  OBJECT-TYPE
    SYNTAX      Counter32
    MAX-ACCESS  read-only
    STATUS      current
    DESCRIPTION
"
By Same Subjects Limits
"
    ::= {cumulativeStat 87}

cumulmsgMSGIDtrErrors  OBJECT-TYPE
    SYNTAX      Counter32
    MAX-ACCESS  read-only
    STATUS      current
    DESCRIPTION
"
MSGID signing Errors
"
    ::= {cumulativeStat 89}

cumulmsgMaxVRFYErrors  OBJECT-TYPE
    SYNTAX      Counter32
    MAX-ACCESS  read-only
    STATUS      current
    DESCRIPTION
"
Max VRFY Errors
"
    ::= {cumulativeStat 90}

cumulsmtpConnDomainIP  OBJECT-TYPE
    SYNTAX      Counter32
    MAX-ACCESS  read-only
    STATUS      current
    DESCRIPTION
"
By Domain IP Limits
"
    ::= {cumulativeStat 92}

cumulinternaladdresses  OBJECT-TYPE
    SYNTAX      Counter32
    MAX-ACCESS  read-only
    STATUS      current
    DESCRIPTION
"
Invalid Internal Mail
"
    ::= {cumulativeStat 93}

cumulrcptAcceptedLocal  OBJECT-TYPE
    SYNTAX      Counter32
    MAX-ACCESS  read-only
    STATUS      current
    DESCRIPTION
"
Local Recipients Accepted
"
    ::= {cumulativeStat 94}

cumulrcptRelayRejected  OBJECT-TYPE
    SYNTAX      Counter32
    MAX-ACCESS  read-only
    STATUS      current
    DESCRIPTION
"
Relay Attempts Rejected
"
    ::= {cumulativeStat 98}

cumulsmtpConnLimitFreq  OBJECT-TYPE
    SYNTAX      Counter32
    MAX-ACCESS  read-only
    STATUS      current
    DESCRIPTION
"
By IP Frequency Limits
"
    ::= {cumulativeStat 99}

cumulsmtpConnNotLogged  OBJECT-TYPE
    SYNTAX      Counter32
    MAX-ACCESS  read-only
    STATUS      current
    DESCRIPTION
"
Not Logged SMTP Connections
"
    ::= {cumulativeStat 100}

cumulrcptDelayedExpired  OBJECT-TYPE
    SYNTAX      Counter32
    MAX-ACCESS  read-only
    STATUS      current
    DESCRIPTION
"
Delayed (Expired) Recipients
"
    ::= {cumulativeStat 102}

cumulrcptNotWhitelisted  OBJECT-TYPE
    SYNTAX      Counter32
    MAX-ACCESS  read-only
    STATUS      current
    DESCRIPTION
"
Not Whitelisted Recipients
"
    ::= {cumulativeStat 103}

cumulsenderInvalidLocals  OBJECT-TYPE
    SYNTAX      Counter32
    MAX-ACCESS  read-only
    STATUS      current
    DESCRIPTION
"
Invalid Sender
"
    ::= {cumulativeStat 105}

cumulsmtpConnIdleTimeout  OBJECT-TYPE
    SYNTAX      Counter32
    MAX-ACCESS  read-only
    STATUS      current
    DESCRIPTION
"
SMTP Connections Timeout
"
    ::= {cumulativeStat 106}

cumulmsgBackscatterErrors  OBJECT-TYPE
    SYNTAX      Counter32
    MAX-ACCESS  read-only
    STATUS      current
    DESCRIPTION
"
BackScatter Errors
"
    ::= {cumulativeStat 107}

cumulrcptReportRedlistAdd  OBJECT-TYPE
    SYNTAX      Counter32
    MAX-ACCESS  read-only
    STATUS      current
    DESCRIPTION
"
Redlist Additions
"
    ::= {cumulativeStat 108}

cumulrcptReportWhitelistAdd  OBJECT-TYPE
    SYNTAX      Counter32
    MAX-ACCESS  read-only
    STATUS      current
    DESCRIPTION
"
Whitelist Additions
"
    ::= {cumulativeStat 111}

cumulsmtpConcurrentSessions  OBJECT-TYPE
    SYNTAX      Counter32
    MAX-ACCESS  read-only
    STATUS      current
    DESCRIPTION
"

"
    ::= {cumulativeStat 112}

cumulsmtpConnSSLIdleTimeout  OBJECT-TYPE
    SYNTAX      Counter32
    MAX-ACCESS  read-only
    STATUS      current
    DESCRIPTION
"
SMTP SSL-Port-Connections Timeout
"
    ::= {cumulativeStat 113}

cumulsmtpConnTLSIdleTimeout  OBJECT-TYPE
    SYNTAX      Counter32
    MAX-ACCESS  read-only
    STATUS      current
    DESCRIPTION
"
SMTP STARTTLS-Connections Timeout
"
    ::= {cumulativeStat 114}

cumulrcptReportRedlistRemove  OBJECT-TYPE
    SYNTAX      Counter32
    MAX-ACCESS  read-only
    STATUS      current
    DESCRIPTION
"
Redlist Deletions
"
    ::= {cumulativeStat 115}

cumulrcptReportWhitelistRemove  OBJECT-TYPE
    SYNTAX      Counter32
    MAX-ACCESS  read-only
    STATUS      current
    DESCRIPTION
"
Whitelist Deletions
"
    ::= {cumulativeStat 116}

cumulsmtpMaxConcurrentSessions  OBJECT-TYPE
    SYNTAX      Counter32
    MAX-ACCESS  read-only
    STATUS      current
    DESCRIPTION
"
Concurrent SMTP Sessions
"
    ::= {cumulativeStat 117}

currentTotmsgTotal  OBJECT-TYPE
    SYNTAX      Counter32
    MAX-ACCESS  read-only
    STATUS      current
    DESCRIPTION
"
Messages Processed
"
    ::= {currentTotalStat 19}

currentTotrcptTotal  OBJECT-TYPE
    SYNTAX      Counter32
    MAX-ACCESS  read-only
    STATUS      current
    DESCRIPTION
"
Envelope Recipients Processed
"
    ::= {currentTotalStat 32}

currentTotrcptReport  OBJECT-TYPE
    SYNTAX      Counter32
    MAX-ACCESS  read-only
    STATUS      current
    DESCRIPTION
"
Email Reports
"
    ::= {currentTotalStat 49}

currentTotsmtpConnSSL  OBJECT-TYPE
    SYNTAX      Counter32
    MAX-ACCESS  read-only
    STATUS      current
    DESCRIPTION
"
SSL-Port SMTP Connections
"
    ::= {currentTotalStat 57}

currentTotsmtpConnTLS  OBJECT-TYPE
    SYNTAX      Counter32
    MAX-ACCESS  read-only
    STATUS      current
    DESCRIPTION
"
STARTTLS SMTP Connections
"
    ::= {currentTotalStat 58}

currentTotadmConnTotal  OBJECT-TYPE
    SYNTAX      Counter32
    MAX-ACCESS  read-only
    STATUS      current
    DESCRIPTION
"
Admin Connections Received
"
    ::= {currentTotalStat 59}

currentTotsmtpConnLimit  OBJECT-TYPE
    SYNTAX      Counter32
    MAX-ACCESS  read-only
    STATUS      current
    DESCRIPTION
"
Overall Limits
"
    ::= {currentTotalStat 70}

currentTotsmtpConnTotal  OBJECT-TYPE
    SYNTAX      Counter32
    MAX-ACCESS  read-only
    STATUS      current
    DESCRIPTION
"
SMTP Connections Received
"
    ::= {currentTotalStat 71}

currentTotstatConnTotal  OBJECT-TYPE
    SYNTAX      Counter32
    MAX-ACCESS  read-only
    STATUS      current
    DESCRIPTION
"
Stat Connections Received
"
    ::= {currentTotalStat 72}

currentTotrcptUnprocessed  OBJECT-TYPE
    SYNTAX      Counter32
    MAX-ACCESS  read-only
    STATUS      current
    DESCRIPTION
"
Noprocessed Recipients
"
    ::= {currentTotalStat 84}

currentTotmsgAcceptedTotal  OBJECT-TYPE
    SYNTAX      Counter32
    MAX-ACCESS  read-only
    STATUS      current
    DESCRIPTION
"
Messages Passed
"
    ::= {currentTotalStat 88}

currentTotmsgRejectedTotal  OBJECT-TYPE
    SYNTAX      Counter32
    MAX-ACCESS  read-only
    STATUS      current
    DESCRIPTION
"
Messages Rejected
"
    ::= {currentTotalStat 91}

currentTotrcptAcceptedLocal  OBJECT-TYPE
    SYNTAX      Counter32
    MAX-ACCESS  read-only
    STATUS      current
    DESCRIPTION
"
Local Recipients Accepted
"
    ::= {currentTotalStat 94}

currentTotrcptAcceptedTotal  OBJECT-TYPE
    SYNTAX      Counter32
    MAX-ACCESS  read-only
    STATUS      current
    DESCRIPTION
"
Envelope Recipients Accepted
"
    ::= {currentTotalStat 95}

currentTotrcptRejectedLocal  OBJECT-TYPE
    SYNTAX      Counter32
    MAX-ACCESS  read-only
    STATUS      current
    DESCRIPTION
"
Local Recipients Rejected
"
    ::= {currentTotalStat 96}

currentTotrcptRejectedTotal  OBJECT-TYPE
    SYNTAX      Counter32
    MAX-ACCESS  read-only
    STATUS      current
    DESCRIPTION
"
Envelope Recipients Rejected
"
    ::= {currentTotalStat 97}

currentTotrcptAcceptedRemote  OBJECT-TYPE
    SYNTAX      Counter32
    MAX-ACCESS  read-only
    STATUS      current
    DESCRIPTION
"
Remote Recipients Accepted
"
    ::= {currentTotalStat 101}

currentTotrcptRejectedRemote  OBJECT-TYPE
    SYNTAX      Counter32
    MAX-ACCESS  read-only
    STATUS      current
    DESCRIPTION
"
Remote Recipients Rejected
"
    ::= {currentTotalStat 104}

currentTotsmtpConnIdleTimeout  OBJECT-TYPE
    SYNTAX      Counter32
    MAX-ACCESS  read-only
    STATUS      current
    DESCRIPTION
"
SMTP Connections Timeout
"
    ::= {currentTotalStat 106}

currentTotsmtpConnAcceptedTotal  OBJECT-TYPE
    SYNTAX      Counter32
    MAX-ACCESS  read-only
    STATUS      current
    DESCRIPTION
"
SMTP Connections Accepted
"
    ::= {currentTotalStat 109}

currentTotsmtpConnRejectedTotal  OBJECT-TYPE
    SYNTAX      Counter32
    MAX-ACCESS  read-only
    STATUS      current
    DESCRIPTION
"
SMTP Connections Rejected
"
    ::= {currentTotalStat 110}

currentTotsmtpConnSSLIdleTimeout  OBJECT-TYPE
    SYNTAX      Counter32
    MAX-ACCESS  read-only
    STATUS      current
    DESCRIPTION
"
SMTP SSL-Port-Connections Timeout
"
    ::= {currentTotalStat 113}

currentTotsmtpConnTLSIdleTimeout  OBJECT-TYPE
    SYNTAX      Counter32
    MAX-ACCESS  read-only
    STATUS      current
    DESCRIPTION
"
SMTP STARTTLS-Connections Timeout
"
    ::= {currentTotalStat 114}

cumulTotmsgTotal  OBJECT-TYPE
    SYNTAX      Counter32
    MAX-ACCESS  read-only
    STATUS      current
    DESCRIPTION
"
Messages Processed
"
    ::= {cumulativeTotalStat 19}

cumulTotrcptTotal  OBJECT-TYPE
    SYNTAX      Counter32
    MAX-ACCESS  read-only
    STATUS      current
    DESCRIPTION
"
Envelope Recipients Processed
"
    ::= {cumulativeTotalStat 32}

cumulTotrcptReport  OBJECT-TYPE
    SYNTAX      Counter32
    MAX-ACCESS  read-only
    STATUS      current
    DESCRIPTION
"
Email Reports
"
    ::= {cumulativeTotalStat 49}

cumulTotsmtpConnSSL  OBJECT-TYPE
    SYNTAX      Counter32
    MAX-ACCESS  read-only
    STATUS      current
    DESCRIPTION
"
SSL-Port SMTP Connections
"
    ::= {cumulativeTotalStat 57}

cumulTotsmtpConnTLS  OBJECT-TYPE
    SYNTAX      Counter32
    MAX-ACCESS  read-only
    STATUS      current
    DESCRIPTION
"
STARTTLS SMTP Connections
"
    ::= {cumulativeTotalStat 58}

cumulTotadmConnTotal  OBJECT-TYPE
    SYNTAX      Counter32
    MAX-ACCESS  read-only
    STATUS      current
    DESCRIPTION
"
Admin Connections Received
"
    ::= {cumulativeTotalStat 59}

cumulTotsmtpConnLimit  OBJECT-TYPE
    SYNTAX      Counter32
    MAX-ACCESS  read-only
    STATUS      current
    DESCRIPTION
"
Overall Limits
"
    ::= {cumulativeTotalStat 70}

cumulTotsmtpConnTotal  OBJECT-TYPE
    SYNTAX      Counter32
    MAX-ACCESS  read-only
    STATUS      current
    DESCRIPTION
"
SMTP Connections Received
"
    ::= {cumulativeTotalStat 71}

cumulTotstatConnTotal  OBJECT-TYPE
    SYNTAX      Counter32
    MAX-ACCESS  read-only
    STATUS      current
    DESCRIPTION
"
Stat Connections Received
"
    ::= {cumulativeTotalStat 72}

cumulTotrcptUnprocessed  OBJECT-TYPE
    SYNTAX      Counter32
    MAX-ACCESS  read-only
    STATUS      current
    DESCRIPTION
"
Noprocessed Recipients
"
    ::= {cumulativeTotalStat 84}

cumulTotmsgAcceptedTotal  OBJECT-TYPE
    SYNTAX      Counter32
    MAX-ACCESS  read-only
    STATUS      current
    DESCRIPTION
"
Messages Passed
"
    ::= {cumulativeTotalStat 88}

cumulTotmsgRejectedTotal  OBJECT-TYPE
    SYNTAX      Counter32
    MAX-ACCESS  read-only
    STATUS      current
    DESCRIPTION
"
Messages Rejected
"
    ::= {cumulativeTotalStat 91}

cumulTotrcptAcceptedLocal  OBJECT-TYPE
    SYNTAX      Counter32
    MAX-ACCESS  read-only
    STATUS      current
    DESCRIPTION
"
Local Recipients Accepted
"
    ::= {cumulativeTotalStat 94}

cumulTotrcptAcceptedTotal  OBJECT-TYPE
    SYNTAX      Counter32
    MAX-ACCESS  read-only
    STATUS      current
    DESCRIPTION
"
Envelope Recipients Accepted
"
    ::= {cumulativeTotalStat 95}

cumulTotrcptRejectedLocal  OBJECT-TYPE
    SYNTAX      Counter32
    MAX-ACCESS  read-only
    STATUS      current
    DESCRIPTION
"
Local Recipients Rejected
"
    ::= {cumulativeTotalStat 96}

cumulTotrcptRejectedTotal  OBJECT-TYPE
    SYNTAX      Counter32
    MAX-ACCESS  read-only
    STATUS      current
    DESCRIPTION
"
Envelope Recipients Rejected
"
    ::= {cumulativeTotalStat 97}

cumulTotrcptAcceptedRemote  OBJECT-TYPE
    SYNTAX      Counter32
    MAX-ACCESS  read-only
    STATUS      current
    DESCRIPTION
"
Remote Recipients Accepted
"
    ::= {cumulativeTotalStat 101}

cumulTotrcptRejectedRemote  OBJECT-TYPE
    SYNTAX      Counter32
    MAX-ACCESS  read-only
    STATUS      current
    DESCRIPTION
"
Remote Recipients Rejected
"
    ::= {cumulativeTotalStat 104}

cumulTotsmtpConnIdleTimeout  OBJECT-TYPE
    SYNTAX      Counter32
    MAX-ACCESS  read-only
    STATUS      current
    DESCRIPTION
"
SMTP Connections Timeout
"
    ::= {cumulativeTotalStat 106}

cumulTotsmtpConnAcceptedTotal  OBJECT-TYPE
    SYNTAX      Counter32
    MAX-ACCESS  read-only
    STATUS      current
    DESCRIPTION
"
SMTP Connections Accepted
"
    ::= {cumulativeTotalStat 109}

cumulTotsmtpConnRejectedTotal  OBJECT-TYPE
    SYNTAX      Counter32
    MAX-ACCESS  read-only
    STATUS      current
    DESCRIPTION
"
SMTP Connections Rejected
"
    ::= {cumulativeTotalStat 110}

cumulTotsmtpConnSSLIdleTimeout  OBJECT-TYPE
    SYNTAX      Counter32
    MAX-ACCESS  read-only
    STATUS      current
    DESCRIPTION
"
SMTP SSL-Port-Connections Timeout
"
    ::= {cumulativeTotalStat 113}

cumulTotsmtpConnTLSIdleTimeout  OBJECT-TYPE
    SYNTAX      Counter32
    MAX-ACCESS  read-only
    STATUS      current
    DESCRIPTION
"
SMTP STARTTLS-Connections Timeout
"
    ::= {cumulativeTotalStat 114}

currentScoredHMM  OBJECT-TYPE
    SYNTAX      Counter32
    MAX-ACCESS  read-only
    STATUS      current
    DESCRIPTION
"
currently scored HMM
"
    ::= {currentScoreStat 0}

currentScoredSIZE  OBJECT-TYPE
    SYNTAX      Counter32
    MAX-ACCESS  read-only
    STATUS      current
    DESCRIPTION
"
currently scored SIZE
"
    ::= {currentScoreStat 1}

currentScoredbombRe  OBJECT-TYPE
    SYNTAX      Counter32
    MAX-ACCESS  read-only
    STATUS      current
    DESCRIPTION
"
currently scored bombRe
"
    ::= {currentScoreStat 2}

currentScoredHMM-HAM  OBJECT-TYPE
    SYNTAX      Counter32
    MAX-ACCESS  read-only
    STATUS      current
    DESCRIPTION
"
currently scored HMM-HAM
"
    ::= {currentScoreStat 3}

currentScoredSPFfail  OBJECT-TYPE
    SYNTAX      Counter32
    MAX-ACCESS  read-only
    STATUS      current
    DESCRIPTION
"
currently scored SPFfail
"
    ::= {currentScoreStat 4}

currentScoredSPFnone  OBJECT-TYPE
    SYNTAX      Counter32
    MAX-ACCESS  read-only
    STATUS      current
    DESCRIPTION
"
currently scored SPFnone
"
    ::= {currentScoreStat 5}

currentScoredSPFpass  OBJECT-TYPE
    SYNTAX      Counter32
    MAX-ACCESS  read-only
    STATUS      current
    DESCRIPTION
"
currently scored SPFpass
"
    ::= {currentScoreStat 6}

currentScoredTimeOut  OBJECT-TYPE
    SYNTAX      Counter32
    MAX-ACCESS  read-only
    STATUS      current
    DESCRIPTION
"
currently scored TimeOut
"
    ::= {currentScoreStat 7}

currentScoredASSP_AFC  OBJECT-TYPE
    SYNTAX      Counter32
    MAX-ACCESS  read-only
    STATUS      current
    DESCRIPTION
"
currently scored ASSP_AFC
"
    ::= {currentScoreStat 8}

currentScoredASSP_DCC  OBJECT-TYPE
    SYNTAX      Counter32
    MAX-ACCESS  read-only
    STATUS      current
    DESCRIPTION
"
currently scored ASSP_DCC
"
    ::= {currentScoreStat 9}

currentScoredASSP_OCR  OBJECT-TYPE
    SYNTAX      Counter32
    MAX-ACCESS  read-only
    STATUS      current
    DESCRIPTION
"
currently scored ASSP_OCR
"
    ::= {currentScoreStat 10}

currentScoredBayesian  OBJECT-TYPE
    SYNTAX      Counter32
    MAX-ACCESS  read-only
    STATUS      current
    DESCRIPTION
"
currently scored Bayesian
"
    ::= {currentScoreStat 11}

currentScoredBlackOrg  OBJECT-TYPE
    SYNTAX      Counter32
    MAX-ACCESS  read-only
    STATUS      current
    DESCRIPTION
"
currently scored BlackOrg
"
    ::= {currentScoreStat 12}

currentScoredBombData  OBJECT-TYPE
    SYNTAX      Counter32
    MAX-ACCESS  read-only
    STATUS      current
    DESCRIPTION
"
currently scored BombData
"
    ::= {currentScoreStat 13}

currentScoredDKIMpass  OBJECT-TYPE
    SYNTAX      Counter32
    MAX-ACCESS  read-only
    STATUS      current
    DESCRIPTION
"
currently scored DKIMpass
"
    ::= {currentScoreStat 14}

currentScoredIPinHELO  OBJECT-TYPE
    SYNTAX      Counter32
    MAX-ACCESS  read-only
    STATUS      current
    DESCRIPTION
"
currently scored IPinHELO
"
    ::= {currentScoreStat 15}

currentScoredSPFerror  OBJECT-TYPE
    SYNTAX      Counter32
    MAX-ACCESS  read-only
    STATUS      current
    DESCRIPTION
"
currently scored SPFerror
"
    ::= {currentScoreStat 16}

currentScoredgriplist  OBJECT-TYPE
    SYNTAX      Counter32
    MAX-ACCESS  read-only
    STATUS      current
    DESCRIPTION
"
currently scored griplist
"
    ::= {currentScoreStat 17}

currentScoredBombBlack  OBJECT-TYPE
    SYNTAX      Counter32
    MAX-ACCESS  read-only
    STATUS      current
    DESCRIPTION
"
currently scored BombBlack
"
    ::= {currentScoreStat 18}

currentScoredMaxErrors  OBJECT-TYPE
    SYNTAX      Counter32
    MAX-ACCESS  read-only
    STATUS      current
    DESCRIPTION
"
currently scored MaxErrors
"
    ::= {currentScoreStat 19}

currentScoredMessageOK  OBJECT-TYPE
    SYNTAX      Counter32
    MAX-ACCESS  read-only
    STATUS      current
    DESCRIPTION
"
currently scored MessageOK
"
    ::= {currentScoreStat 20}

currentScoredMissingMX  OBJECT-TYPE
    SYNTAX      Counter32
    MAX-ACCESS  read-only
    STATUS      current
    DESCRIPTION
"
currently scored MissingMX
"
    ::= {currentScoreStat 21}

currentScoredValidHELO  OBJECT-TYPE
    SYNTAX      Counter32
    MAX-ACCESS  read-only
    STATUS      current
    DESCRIPTION
"
currently scored ValidHELO
"
    ::= {currentScoreStat 22}

currentScoredASSP_Razor  OBJECT-TYPE
    SYNTAX      Counter32
    MAX-ACCESS  read-only
    STATUS      current
    DESCRIPTION
"
currently scored ASSP_Razor
"
    ::= {currentScoreStat 23}

currentScoredAUTHErrors  OBJECT-TYPE
    SYNTAX      Counter32
    MAX-ACCESS  read-only
    STATUS      current
    DESCRIPTION
"
currently scored AUTHErrors
"
    ::= {currentScoreStat 24}

currentScoredBadHistory  OBJECT-TYPE
    SYNTAX      Counter32
    MAX-ACCESS  read-only
    STATUS      current
    DESCRIPTION
"
currently scored BadHistory
"
    ::= {currentScoreStat 25}

currentScoredBombScript  OBJECT-TYPE
    SYNTAX      Counter32
    MAX-ACCESS  read-only
    STATUS      current
    DESCRIPTION
"
currently scored BombScript
"
    ::= {currentScoreStat 26}

currentScoredDKIMfailed  OBJECT-TYPE
    SYNTAX      Counter32
    MAX-ACCESS  read-only
    STATUS      current
    DESCRIPTION
"
currently scored DKIMfailed
"
    ::= {currentScoreStat 27}

currentScoredForgedHELO  OBJECT-TYPE
    SYNTAX      Counter32
    MAX-ACCESS  read-only
    STATUS      current
    DESCRIPTION
"
currently scored ForgedHELO
"
    ::= {currentScoreStat 28}

currentScoredInWhiteBox  OBJECT-TYPE
    SYNTAX      Counter32
    MAX-ACCESS  read-only
    STATUS      current
    DESCRIPTION
"
currently scored InWhiteBox
"
    ::= {currentScoreStat 29}

currentScoredLimitingIP  OBJECT-TYPE
    SYNTAX      Counter32
    MAX-ACCESS  read-only
    STATUS      current
    DESCRIPTION
"
currently scored LimitingIP
"
    ::= {currentScoreStat 30}

currentScoredMissingMXA  OBJECT-TYPE
    SYNTAX      Counter32
    MAX-ACCESS  read-only
    STATUS      current
    DESCRIPTION
"
currently scored MissingMXA
"
    ::= {currentScoreStat 31}

currentScoredNoSpoofing  OBJECT-TYPE
    SYNTAX      Counter32
    MAX-ACCESS  read-only
    STATUS      current
    DESCRIPTION
"
currently scored NoSpoofing
"
    ::= {currentScoreStat 32}

currentScoredPTRinvalid  OBJECT-TYPE
    SYNTAX      Counter32
    MAX-ACCESS  read-only
    STATUS      current
    DESCRIPTION
"
currently scored PTRinvalid
"
    ::= {currentScoreStat 33}

currentScoredPTRmissing  OBJECT-TYPE
    SYNTAX      Counter32
    MAX-ACCESS  read-only
    STATUS      current
    DESCRIPTION
"
currently scored PTRmissing
"
    ::= {currentScoreStat 34}

currentScoredSPFneutral  OBJECT-TYPE
    SYNTAX      Counter32
    MAX-ACCESS  read-only
    STATUS      current
    DESCRIPTION
"
currently scored SPFneutral
"
    ::= {currentScoreStat 35}

currentScoredCountryCode  OBJECT-TYPE
    SYNTAX      Counter32
    MAX-ACCESS  read-only
    STATUS      current
    DESCRIPTION
"
currently scored CountryCode
"
    ::= {currentScoreStat 36}

currentScoredDNSBLfailed  OBJECT-TYPE
    SYNTAX      Counter32
    MAX-ACCESS  read-only
    STATUS      current
    DESCRIPTION
"
currently scored DNSBLfailed
"
    ::= {currentScoreStat 37}

currentScoredEarlyTalker  OBJECT-TYPE
    SYNTAX      Counter32
    MAX-ACCESS  read-only
    STATUS      current
    DESCRIPTION
"
currently scored EarlyTalker
"
    ::= {currentScoreStat 38}

currentScoredHomeCountry  OBJECT-TYPE
    SYNTAX      Counter32
    MAX-ACCESS  read-only
    STATUS      current
    DESCRIPTION
"
currently scored HomeCountry
"
    ::= {currentScoreStat 39}

currentScoredIPfrequency  OBJECT-TYPE
    SYNTAX      Counter32
    MAX-ACCESS  read-only
    STATUS      current
    DESCRIPTION
"
currently scored IPfrequency
"
    ::= {currentScoreStat 40}

currentScoredInvalidHELO  OBJECT-TYPE
    SYNTAX      Counter32
    MAX-ACCESS  read-only
    STATUS      current
    DESCRIPTION
"
currently scored InvalidHELO
"
    ::= {currentScoreStat 41}

currentScoredSPFsoftfail  OBJECT-TYPE
    SYNTAX      Counter32
    MAX-ACCESS  read-only
    STATUS      current
    DESCRIPTION
"
currently scored SPFsoftfail
"
    ::= {currentScoreStat 42}

currentScoredURIBLfailed  OBJECT-TYPE
    SYNTAX      Counter32
    MAX-ACCESS  read-only
    STATUS      current
    DESCRIPTION
"
currently scored URIBLfailed
"
    ::= {currentScoreStat 43}

currentScoredpenaltytrap  OBJECT-TYPE
    SYNTAX      Counter32
    MAX-ACCESS  read-only
    STATUS      current
    DESCRIPTION
"
currently scored penaltytrap
"
    ::= {currentScoreStat 44}

currentScoredBayesian-HAM  OBJECT-TYPE
    SYNTAX      Counter32
    MAX-ACCESS  read-only
    STATUS      current
    DESCRIPTION
"
currently scored Bayesian-HAM
"
    ::= {currentScoreStat 45}

currentScoredBombCharSets  OBJECT-TYPE
    SYNTAX      Counter32
    MAX-ACCESS  read-only
    STATUS      current
    DESCRIPTION
"
currently scored BombCharSets
"
    ::= {currentScoreStat 46}

currentScoredBombHeaderRe  OBJECT-TYPE
    SYNTAX      Counter32
    MAX-ACCESS  read-only
    STATUS      current
    DESCRIPTION
"
currently scored BombHeaderRe
"
    ::= {currentScoreStat 47}

currentScoredBombSenderIP  OBJECT-TYPE
    SYNTAX      Counter32
    MAX-ACCESS  read-only
    STATUS      current
    DESCRIPTION
"
currently scored BombSenderIP
"
    ::= {currentScoreStat 48}

currentScoredDMARC-failed  OBJECT-TYPE
    SYNTAX      Counter32
    MAX-ACCESS  read-only
    STATUS      current
    DESCRIPTION
"
currently scored DMARC-failed
"
    ::= {currentScoreStat 49}

currentScoredDNSBLneutral  OBJECT-TYPE
    SYNTAX      Counter32
    MAX-ACCESS  read-only
    STATUS      current
    DESCRIPTION
"
currently scored DNSBLneutral
"
    ::= {currentScoreStat 50}

currentScoredFrom-missing  OBJECT-TYPE
    SYNTAX      Counter32
    MAX-ACCESS  read-only
    STATUS      current
    DESCRIPTION
"
currently scored From-missing
"
    ::= {currentScoreStat 51}

currentScoredRelayAttempt  OBJECT-TYPE
    SYNTAX      Counter32
    MAX-ACCESS  read-only
    STATUS      current
    DESCRIPTION
"
currently scored RelayAttempt
"
    ::= {currentScoreStat 52}

currentScoredURIBLneutral  OBJECT-TYPE
    SYNTAX      Counter32
    MAX-ACCESS  read-only
    STATUS      current
    DESCRIPTION
"
currently scored URIBLneutral
"
    ::= {currentScoreStat 53}

currentScoredvirus-ClamAV  OBJECT-TYPE
    SYNTAX      Counter32
    MAX-ACCESS  read-only
    STATUS      current
    DESCRIPTION
"
currently scored virus-ClamAV
"
    ::= {currentScoreStat 54}

currentScoredBadAttachment  OBJECT-TYPE
    SYNTAX      Counter32
    MAX-ACCESS  read-only
    STATUS      current
    DESCRIPTION
"
currently scored BadAttachment
"
    ::= {currentScoreStat 55}

currentScoredBombSubjectRe  OBJECT-TYPE
    SYNTAX      Counter32
    MAX-ACCESS  read-only
    STATUS      current
    DESCRIPTION
"
currently scored BombSubjectRe
"
    ::= {currentScoreStat 56}

currentScoredKnownGoodHelo  OBJECT-TYPE
    SYNTAX      Counter32
    MAX-ACCESS  read-only
    STATUS      current
    DESCRIPTION
"
currently scored KnownGoodHelo
"
    ::= {currentScoreStat 57}

currentScoredMsg-IDinvalid  OBJECT-TYPE
    SYNTAX      Counter32
    MAX-ACCESS  read-only
    STATUS      current
    DESCRIPTION
"
currently scored Msg-IDinvalid
"
    ::= {currentScoreStat 58}

currentScoredMsg-IDmissing  OBJECT-TYPE
    SYNTAX      Counter32
    MAX-ACCESS  read-only
    STATUS      current
    DESCRIPTION
"
currently scored Msg-IDmissing
"
    ::= {currentScoreStat 59}

currentScoredNeedRecipient  OBJECT-TYPE
    SYNTAX      Counter32
    MAX-ACCESS  read-only
    STATUS      current
    DESCRIPTION
"
currently scored NeedRecipient
"
    ::= {currentScoreStat 60}

currentScoredBlockedCountry  OBJECT-TYPE
    SYNTAX      Counter32
    MAX-ACCESS  read-only
    STATUS      current
    DESCRIPTION
"
currently scored BlockedCountry
"
    ::= {currentScoreStat 61}

currentScoredBombSenderHelo  OBJECT-TYPE
    SYNTAX      Counter32
    MAX-ACCESS  read-only
    STATUS      current
    DESCRIPTION
"
currently scored BombSenderHelo
"
    ::= {currentScoreStat 62}

currentScoredExtremeHistory  OBJECT-TYPE
    SYNTAX      Counter32
    MAX-ACCESS  read-only
    STATUS      current
    DESCRIPTION
"
currently scored ExtremeHistory
"
    ::= {currentScoreStat 63}

currentScoredInvalidAddress  OBJECT-TYPE
    SYNTAX      Counter32
    MAX-ACCESS  read-only
    STATUS      current
    DESCRIPTION
"
currently scored InvalidAddress
"
    ::= {currentScoreStat 64}

currentScoredMsg-IDnotvalid  OBJECT-TYPE
    SYNTAX      Counter32
    MAX-ACCESS  read-only
    STATUS      current
    DESCRIPTION
"
currently scored Msg-IDnotvalid
"
    ::= {currentScoreStat 65}

currentScoredNoCountryNoOrg  OBJECT-TYPE
    SYNTAX      Counter32
    MAX-ACCESS  read-only
    STATUS      current
    DESCRIPTION
"
currently scored NoCountryNoOrg
"
    ::= {currentScoreStat 66}

currentScoredSPFfail-strict  OBJECT-TYPE
    SYNTAX      Counter32
    MAX-ACCESS  read-only
    STATUS      current
    DESCRIPTION
"
currently scored SPFfail-strict
"
    ::= {currentScoreStat 67}

currentScoredSPFnone-strict  OBJECT-TYPE
    SYNTAX      Counter32
    MAX-ACCESS  read-only
    STATUS      current
    DESCRIPTION
"
currently scored SPFnone-strict
"
    ::= {currentScoreStat 68}

currentScoredSRS_Not_Signed  OBJECT-TYPE
    SYNTAX      Counter32
    MAX-ACCESS  read-only
    STATUS      current
    DESCRIPTION
"
currently scored SRS_Not_Signed
"
    ::= {currentScoreStat 69}

currentScoredvirus-FileScan  OBJECT-TYPE
    SYNTAX      Counter32
    MAX-ACCESS  read-only
    STATUS      current
    DESCRIPTION
"
currently scored virus-FileScan
"
    ::= {currentScoreStat 70}

currentScoredBlacklistedHelo  OBJECT-TYPE
    SYNTAX      Counter32
    MAX-ACCESS  read-only
    STATUS      current
    DESCRIPTION
"
currently scored BlacklistedHelo
"
    ::= {currentScoreStat 71}

currentScoredWhiteSenderBase  OBJECT-TYPE
    SYNTAX      Counter32
    MAX-ACCESS  read-only
    STATUS      current
    DESCRIPTION
"
currently scored WhiteSenderBase
"
    ::= {currentScoreStat 72}

currentScoredinternaladdress  OBJECT-TYPE
    SYNTAX      Counter32
    MAX-ACCESS  read-only
    STATUS      current
    DESCRIPTION
"
currently scored internaladdress
"
    ::= {currentScoreStat 73}

currentScoredIPinHELOmismatch  OBJECT-TYPE
    SYNTAX      Counter32
    MAX-ACCESS  read-only
    STATUS      current
    DESCRIPTION
"
currently scored IPinHELOmismatch
"
    ::= {currentScoreStat 74}

currentScoredLimitingIPDomain  OBJECT-TYPE
    SYNTAX      Counter32
    MAX-ACCESS  read-only
    STATUS      current
    DESCRIPTION
"
currently scored LimitingIPDomain
"
    ::= {currentScoreStat 75}

currentScoredMaxDuplicateRcpt  OBJECT-TYPE
    SYNTAX      Counter32
    MAX-ACCESS  read-only
    STATUS      current
    DESCRIPTION
"
currently scored MaxDuplicateRcpt
"
    ::= {currentScoreStat 76}

currentScoredMsg-IDsuspicious  OBJECT-TYPE
    SYNTAX      Counter32
    MAX-ACCESS  read-only
    STATUS      current
    DESCRIPTION
"
currently scored Msg-IDsuspicious
"
    ::= {currentScoreStat 77}

currentScoredbombSuspiciousRe  OBJECT-TYPE
    SYNTAX      Counter32
    MAX-ACCESS  read-only
    STATUS      current
    DESCRIPTION
"
currently scored bombSuspiciousRe
"
    ::= {currentScoreStat 78}

currentScoredBATV-check-failed  OBJECT-TYPE
    SYNTAX      Counter32
    MAX-ACCESS  read-only
    STATUS      current
    DESCRIPTION
"
currently scored BATV-check-failed
"
    ::= {currentScoreStat 79}

currentScoredBlacklistedDomain  OBJECT-TYPE
    SYNTAX      Counter32
    MAX-ACCESS  read-only
    STATUS      current
    DESCRIPTION
"
currently scored BlacklistedDomain
"
    ::= {currentScoreStat 80}

currentScoredSPFneutral-strict  OBJECT-TYPE
    SYNTAX      Counter32
    MAX-ACCESS  read-only
    STATUS      current
    DESCRIPTION
"
currently scored SPFneutral-strict
"
    ::= {currentScoreStat 81}

currentScoredBackscatter-failed  OBJECT-TYPE
    SYNTAX      Counter32
    MAX-ACCESS  read-only
    STATUS      current
    DESCRIPTION
"
currently scored Backscatter-failed
"
    ::= {currentScoreStat 82}

currentScoredBombSenderMailFrom  OBJECT-TYPE
    SYNTAX      Counter32
    MAX-ACCESS  read-only
    STATUS      current
    DESCRIPTION
"
currently scored BombSenderMailFrom
"
    ::= {currentScoreStat 83}

currentScoredInvalidLocalSender  OBJECT-TYPE
    SYNTAX      Counter32
    MAX-ACCESS  read-only
    STATUS      current
    DESCRIPTION
"
currently scored InvalidLocalSender
"
    ::= {currentScoreStat 84}

currentScoredSPFsoftfail-strict  OBJECT-TYPE
    SYNTAX      Counter32
    MAX-ACCESS  read-only
    STATUS      current
    DESCRIPTION
"
currently scored SPFsoftfail-strict
"
    ::= {currentScoreStat 85}

currentScoredSpamCollectAddress  OBJECT-TYPE
    SYNTAX      Counter32
    MAX-ACCESS  read-only
    STATUS      current
    DESCRIPTION
"
currently scored SpamCollectAddress
"
    ::= {currentScoreStat 86}

currentScoredLimitingSameSubject  OBJECT-TYPE
    SYNTAX      Counter32
    MAX-ACCESS  read-only
    STATUS      current
    DESCRIPTION
"
currently scored LimitingSameSubject
"
    ::= {currentScoreStat 87}

currentScoredSSL-TLS-connection-OK  OBJECT-TYPE
    SYNTAX      Counter32
    MAX-ACCESS  read-only
    STATUS      current
    DESCRIPTION
"
currently scored SSL-TLS-connection-OK
"
    ::= {currentScoreStat 88}

currentScoredMSGID-signature-failed  OBJECT-TYPE
    SYNTAX      Counter32
    MAX-ACCESS  read-only
    STATUS      current
    DESCRIPTION
"
currently scored MSGID-signature-failed
"
    ::= {currentScoreStat 89}

currentScoredSuspiciousVirus-ClamAV  OBJECT-TYPE
    SYNTAX      Counter32
    MAX-ACCESS  read-only
    STATUS      current
    DESCRIPTION
"
currently scored SuspiciousVirus-ClamAV
"
    ::= {currentScoreStat 90}

currentScoredSuspiciousVirus-FileScan  OBJECT-TYPE
    SYNTAX      Counter32
    MAX-ACCESS  read-only
    STATUS      current
    DESCRIPTION
"
currently scored SuspiciousVirus-FileScan
"
    ::= {currentScoreStat 91}

cumulScoredHMM  OBJECT-TYPE
    SYNTAX      Counter32
    MAX-ACCESS  read-only
    STATUS      current
    DESCRIPTION
"
cumulative scored HMM
"
    ::= {cumulativeScoreStat 0}

cumulScoredSIZE  OBJECT-TYPE
    SYNTAX      Counter32
    MAX-ACCESS  read-only
    STATUS      current
    DESCRIPTION
"
cumulative scored SIZE
"
    ::= {cumulativeScoreStat 1}

cumulScoredbombRe  OBJECT-TYPE
    SYNTAX      Counter32
    MAX-ACCESS  read-only
    STATUS      current
    DESCRIPTION
"
cumulative scored bombRe
"
    ::= {cumulativeScoreStat 2}

cumulScoredHMM-HAM  OBJECT-TYPE
    SYNTAX      Counter32
    MAX-ACCESS  read-only
    STATUS      current
    DESCRIPTION
"
cumulative scored HMM-HAM
"
    ::= {cumulativeScoreStat 3}

cumulScoredSPFfail  OBJECT-TYPE
    SYNTAX      Counter32
    MAX-ACCESS  read-only
    STATUS      current
    DESCRIPTION
"
cumulative scored SPFfail
"
    ::= {cumulativeScoreStat 4}

cumulScoredSPFnone  OBJECT-TYPE
    SYNTAX      Counter32
    MAX-ACCESS  read-only
    STATUS      current
    DESCRIPTION
"
cumulative scored SPFnone
"
    ::= {cumulativeScoreStat 5}

cumulScoredSPFpass  OBJECT-TYPE
    SYNTAX      Counter32
    MAX-ACCESS  read-only
    STATUS      current
    DESCRIPTION
"
cumulative scored SPFpass
"
    ::= {cumulativeScoreStat 6}

cumulScoredTimeOut  OBJECT-TYPE
    SYNTAX      Counter32
    MAX-ACCESS  read-only
    STATUS      current
    DESCRIPTION
"
cumulative scored TimeOut
"
    ::= {cumulativeScoreStat 7}

cumulScoredASSP_AFC  OBJECT-TYPE
    SYNTAX      Counter32
    MAX-ACCESS  read-only
    STATUS      current
    DESCRIPTION
"
cumulative scored ASSP_AFC
"
    ::= {cumulativeScoreStat 8}

cumulScoredASSP_DCC  OBJECT-TYPE
    SYNTAX      Counter32
    MAX-ACCESS  read-only
    STATUS      current
    DESCRIPTION
"
cumulative scored ASSP_DCC
"
    ::= {cumulativeScoreStat 9}

cumulScoredASSP_OCR  OBJECT-TYPE
    SYNTAX      Counter32
    MAX-ACCESS  read-only
    STATUS      current
    DESCRIPTION
"
cumulative scored ASSP_OCR
"
    ::= {cumulativeScoreStat 10}

cumulScoredBayesian  OBJECT-TYPE
    SYNTAX      Counter32
    MAX-ACCESS  read-only
    STATUS      current
    DESCRIPTION
"
cumulative scored Bayesian
"
    ::= {cumulativeScoreStat 11}

cumulScoredBlackOrg  OBJECT-TYPE
    SYNTAX      Counter32
    MAX-ACCESS  read-only
    STATUS      current
    DESCRIPTION
"
cumulative scored BlackOrg
"
    ::= {cumulativeScoreStat 12}

cumulScoredBombData  OBJECT-TYPE
    SYNTAX      Counter32
    MAX-ACCESS  read-only
    STATUS      current
    DESCRIPTION
"
cumulative scored BombData
"
    ::= {cumulativeScoreStat 13}

cumulScoredDKIMpass  OBJECT-TYPE
    SYNTAX      Counter32
    MAX-ACCESS  read-only
    STATUS      current
    DESCRIPTION
"
cumulative scored DKIMpass
"
    ::= {cumulativeScoreStat 14}

cumulScoredIPinHELO  OBJECT-TYPE
    SYNTAX      Counter32
    MAX-ACCESS  read-only
    STATUS      current
    DESCRIPTION
"
cumulative scored IPinHELO
"
    ::= {cumulativeScoreStat 15}

cumulScoredSPFerror  OBJECT-TYPE
    SYNTAX      Counter32
    MAX-ACCESS  read-only
    STATUS      current
    DESCRIPTION
"
cumulative scored SPFerror
"
    ::= {cumulativeScoreStat 16}

cumulScoredgriplist  OBJECT-TYPE
    SYNTAX      Counter32
    MAX-ACCESS  read-only
    STATUS      current
    DESCRIPTION
"
cumulative scored griplist
"
    ::= {cumulativeScoreStat 17}

cumulScoredBombBlack  OBJECT-TYPE
    SYNTAX      Counter32
    MAX-ACCESS  read-only
    STATUS      current
    DESCRIPTION
"
cumulative scored BombBlack
"
    ::= {cumulativeScoreStat 18}

cumulScoredMaxErrors  OBJECT-TYPE
    SYNTAX      Counter32
    MAX-ACCESS  read-only
    STATUS      current
    DESCRIPTION
"
cumulative scored MaxErrors
"
    ::= {cumulativeScoreStat 19}

cumulScoredMessageOK  OBJECT-TYPE
    SYNTAX      Counter32
    MAX-ACCESS  read-only
    STATUS      current
    DESCRIPTION
"
cumulative scored MessageOK
"
    ::= {cumulativeScoreStat 20}

cumulScoredMissingMX  OBJECT-TYPE
    SYNTAX      Counter32
    MAX-ACCESS  read-only
    STATUS      current
    DESCRIPTION
"
cumulative scored MissingMX
"
    ::= {cumulativeScoreStat 21}

cumulScoredValidHELO  OBJECT-TYPE
    SYNTAX      Counter32
    MAX-ACCESS  read-only
    STATUS      current
    DESCRIPTION
"
cumulative scored ValidHELO
"
    ::= {cumulativeScoreStat 22}

cumulScoredASSP_Razor  OBJECT-TYPE
    SYNTAX      Counter32
    MAX-ACCESS  read-only
    STATUS      current
    DESCRIPTION
"
cumulative scored ASSP_Razor
"
    ::= {cumulativeScoreStat 23}

cumulScoredAUTHErrors  OBJECT-TYPE
    SYNTAX      Counter32
    MAX-ACCESS  read-only
    STATUS      current
    DESCRIPTION
"
cumulative scored AUTHErrors
"
    ::= {cumulativeScoreStat 24}

cumulScoredBadHistory  OBJECT-TYPE
    SYNTAX      Counter32
    MAX-ACCESS  read-only
    STATUS      current
    DESCRIPTION
"
cumulative scored BadHistory
"
    ::= {cumulativeScoreStat 25}

cumulScoredBombScript  OBJECT-TYPE
    SYNTAX      Counter32
    MAX-ACCESS  read-only
    STATUS      current
    DESCRIPTION
"
cumulative scored BombScript
"
    ::= {cumulativeScoreStat 26}

cumulScoredDKIMfailed  OBJECT-TYPE
    SYNTAX      Counter32
    MAX-ACCESS  read-only
    STATUS      current
    DESCRIPTION
"
cumulative scored DKIMfailed
"
    ::= {cumulativeScoreStat 27}

cumulScoredForgedHELO  OBJECT-TYPE
    SYNTAX      Counter32
    MAX-ACCESS  read-only
    STATUS      current
    DESCRIPTION
"
cumulative scored ForgedHELO
"
    ::= {cumulativeScoreStat 28}

cumulScoredInWhiteBox  OBJECT-TYPE
    SYNTAX      Counter32
    MAX-ACCESS  read-only
    STATUS      current
    DESCRIPTION
"
cumulative scored InWhiteBox
"
    ::= {cumulativeScoreStat 29}

cumulScoredLimitingIP  OBJECT-TYPE
    SYNTAX      Counter32
    MAX-ACCESS  read-only
    STATUS      current
    DESCRIPTION
"
cumulative scored LimitingIP
"
    ::= {cumulativeScoreStat 30}

cumulScoredMissingMXA  OBJECT-TYPE
    SYNTAX      Counter32
    MAX-ACCESS  read-only
    STATUS      current
    DESCRIPTION
"
cumulative scored MissingMXA
"
    ::= {cumulativeScoreStat 31}

cumulScoredNoSpoofing  OBJECT-TYPE
    SYNTAX      Counter32
    MAX-ACCESS  read-only
    STATUS      current
    DESCRIPTION
"
cumulative scored NoSpoofing
"
    ::= {cumulativeScoreStat 32}

cumulScoredPTRinvalid  OBJECT-TYPE
    SYNTAX      Counter32
    MAX-ACCESS  read-only
    STATUS      current
    DESCRIPTION
"
cumulative scored PTRinvalid
"
    ::= {cumulativeScoreStat 33}

cumulScoredPTRmissing  OBJECT-TYPE
    SYNTAX      Counter32
    MAX-ACCESS  read-only
    STATUS      current
    DESCRIPTION
"
cumulative scored PTRmissing
"
    ::= {cumulativeScoreStat 34}

cumulScoredSPFneutral  OBJECT-TYPE
    SYNTAX      Counter32
    MAX-ACCESS  read-only
    STATUS      current
    DESCRIPTION
"
cumulative scored SPFneutral
"
    ::= {cumulativeScoreStat 35}

cumulScoredCountryCode  OBJECT-TYPE
    SYNTAX      Counter32
    MAX-ACCESS  read-only
    STATUS      current
    DESCRIPTION
"
cumulative scored CountryCode
"
    ::= {cumulativeScoreStat 36}

cumulScoredDNSBLfailed  OBJECT-TYPE
    SYNTAX      Counter32
    MAX-ACCESS  read-only
    STATUS      current
    DESCRIPTION
"
cumulative scored DNSBLfailed
"
    ::= {cumulativeScoreStat 37}

cumulScoredEarlyTalker  OBJECT-TYPE
    SYNTAX      Counter32
    MAX-ACCESS  read-only
    STATUS      current
    DESCRIPTION
"
cumulative scored EarlyTalker
"
    ::= {cumulativeScoreStat 38}

cumulScoredHomeCountry  OBJECT-TYPE
    SYNTAX      Counter32
    MAX-ACCESS  read-only
    STATUS      current
    DESCRIPTION
"
cumulative scored HomeCountry
"
    ::= {cumulativeScoreStat 39}

cumulScoredIPfrequency  OBJECT-TYPE
    SYNTAX      Counter32
    MAX-ACCESS  read-only
    STATUS      current
    DESCRIPTION
"
cumulative scored IPfrequency
"
    ::= {cumulativeScoreStat 40}

cumulScoredInvalidHELO  OBJECT-TYPE
    SYNTAX      Counter32
    MAX-ACCESS  read-only
    STATUS      current
    DESCRIPTION
"
cumulative scored InvalidHELO
"
    ::= {cumulativeScoreStat 41}

cumulScoredSPFsoftfail  OBJECT-TYPE
    SYNTAX      Counter32
    MAX-ACCESS  read-only
    STATUS      current
    DESCRIPTION
"
cumulative scored SPFsoftfail
"
    ::= {cumulativeScoreStat 42}

cumulScoredURIBLfailed  OBJECT-TYPE
    SYNTAX      Counter32
    MAX-ACCESS  read-only
    STATUS      current
    DESCRIPTION
"
cumulative scored URIBLfailed
"
    ::= {cumulativeScoreStat 43}

cumulScoredpenaltytrap  OBJECT-TYPE
    SYNTAX      Counter32
    MAX-ACCESS  read-only
    STATUS      current
    DESCRIPTION
"
cumulative scored penaltytrap
"
    ::= {cumulativeScoreStat 44}

cumulScoredBayesian-HAM  OBJECT-TYPE
    SYNTAX      Counter32
    MAX-ACCESS  read-only
    STATUS      current
    DESCRIPTION
"
cumulative scored Bayesian-HAM
"
    ::= {cumulativeScoreStat 45}

cumulScoredBombCharSets  OBJECT-TYPE
    SYNTAX      Counter32
    MAX-ACCESS  read-only
    STATUS      current
    DESCRIPTION
"
cumulative scored BombCharSets
"
    ::= {cumulativeScoreStat 46}

cumulScoredBombHeaderRe  OBJECT-TYPE
    SYNTAX      Counter32
    MAX-ACCESS  read-only
    STATUS      current
    DESCRIPTION
"
cumulative scored BombHeaderRe
"
    ::= {cumulativeScoreStat 47}

cumulScoredBombSenderIP  OBJECT-TYPE
    SYNTAX      Counter32
    MAX-ACCESS  read-only
    STATUS      current
    DESCRIPTION
"
cumulative scored BombSenderIP
"
    ::= {cumulativeScoreStat 48}

cumulScoredDMARC-failed  OBJECT-TYPE
    SYNTAX      Counter32
    MAX-ACCESS  read-only
    STATUS      current
    DESCRIPTION
"
cumulative scored DMARC-failed
"
    ::= {cumulativeScoreStat 49}

cumulScoredDNSBLneutral  OBJECT-TYPE
    SYNTAX      Counter32
    MAX-ACCESS  read-only
    STATUS      current
    DESCRIPTION
"
cumulative scored DNSBLneutral
"
    ::= {cumulativeScoreStat 50}

cumulScoredFrom-missing  OBJECT-TYPE
    SYNTAX      Counter32
    MAX-ACCESS  read-only
    STATUS      current
    DESCRIPTION
"
cumulative scored From-missing
"
    ::= {cumulativeScoreStat 51}

cumulScoredRelayAttempt  OBJECT-TYPE
    SYNTAX      Counter32
    MAX-ACCESS  read-only
    STATUS      current
    DESCRIPTION
"
cumulative scored RelayAttempt
"
    ::= {cumulativeScoreStat 52}

cumulScoredURIBLneutral  OBJECT-TYPE
    SYNTAX      Counter32
    MAX-ACCESS  read-only
    STATUS      current
    DESCRIPTION
"
cumulative scored URIBLneutral
"
    ::= {cumulativeScoreStat 53}

cumulScoredvirus-ClamAV  OBJECT-TYPE
    SYNTAX      Counter32
    MAX-ACCESS  read-only
    STATUS      current
    DESCRIPTION
"
cumulative scored virus-ClamAV
"
    ::= {cumulativeScoreStat 54}

cumulScoredBadAttachment  OBJECT-TYPE
    SYNTAX      Counter32
    MAX-ACCESS  read-only
    STATUS      current
    DESCRIPTION
"
cumulative scored BadAttachment
"
    ::= {cumulativeScoreStat 55}

cumulScoredBombSubjectRe  OBJECT-TYPE
    SYNTAX      Counter32
    MAX-ACCESS  read-only
    STATUS      current
    DESCRIPTION
"
cumulative scored BombSubjectRe
"
    ::= {cumulativeScoreStat 56}

cumulScoredKnownGoodHelo  OBJECT-TYPE
    SYNTAX      Counter32
    MAX-ACCESS  read-only
    STATUS      current
    DESCRIPTION
"
cumulative scored KnownGoodHelo
"
    ::= {cumulativeScoreStat 57}

cumulScoredMsg-IDinvalid  OBJECT-TYPE
    SYNTAX      Counter32
    MAX-ACCESS  read-only
    STATUS      current
    DESCRIPTION
"
cumulative scored Msg-IDinvalid
"
    ::= {cumulativeScoreStat 58}

cumulScoredMsg-IDmissing  OBJECT-TYPE
    SYNTAX      Counter32
    MAX-ACCESS  read-only
    STATUS      current
    DESCRIPTION
"
cumulative scored Msg-IDmissing
"
    ::= {cumulativeScoreStat 59}

cumulScoredNeedRecipient  OBJECT-TYPE
    SYNTAX      Counter32
    MAX-ACCESS  read-only
    STATUS      current
    DESCRIPTION
"
cumulative scored NeedRecipient
"
    ::= {cumulativeScoreStat 60}

cumulScoredBlockedCountry  OBJECT-TYPE
    SYNTAX      Counter32
    MAX-ACCESS  read-only
    STATUS      current
    DESCRIPTION
"
cumulative scored BlockedCountry
"
    ::= {cumulativeScoreStat 61}

cumulScoredBombSenderHelo  OBJECT-TYPE
    SYNTAX      Counter32
    MAX-ACCESS  read-only
    STATUS      current
    DESCRIPTION
"
cumulative scored BombSenderHelo
"
    ::= {cumulativeScoreStat 62}

cumulScoredExtremeHistory  OBJECT-TYPE
    SYNTAX      Counter32
    MAX-ACCESS  read-only
    STATUS      current
    DESCRIPTION
"
cumulative scored ExtremeHistory
"
    ::= {cumulativeScoreStat 63}

cumulScoredInvalidAddress  OBJECT-TYPE
    SYNTAX      Counter32
    MAX-ACCESS  read-only
    STATUS      current
    DESCRIPTION
"
cumulative scored InvalidAddress
"
    ::= {cumulativeScoreStat 64}

cumulScoredMsg-IDnotvalid  OBJECT-TYPE
    SYNTAX      Counter32
    MAX-ACCESS  read-only
    STATUS      current
    DESCRIPTION
"
cumulative scored Msg-IDnotvalid
"
    ::= {cumulativeScoreStat 65}

cumulScoredNoCountryNoOrg  OBJECT-TYPE
    SYNTAX      Counter32
    MAX-ACCESS  read-only
    STATUS      current
    DESCRIPTION
"
cumulative scored NoCountryNoOrg
"
    ::= {cumulativeScoreStat 66}

cumulScoredSPFfail-strict  OBJECT-TYPE
    SYNTAX      Counter32
    MAX-ACCESS  read-only
    STATUS      current
    DESCRIPTION
"
cumulative scored SPFfail-strict
"
    ::= {cumulativeScoreStat 67}

cumulScoredSPFnone-strict  OBJECT-TYPE
    SYNTAX      Counter32
    MAX-ACCESS  read-only
    STATUS      current
    DESCRIPTION
"
cumulative scored SPFnone-strict
"
    ::= {cumulativeScoreStat 68}

cumulScoredSRS_Not_Signed  OBJECT-TYPE
    SYNTAX      Counter32
    MAX-ACCESS  read-only
    STATUS      current
    DESCRIPTION
"
cumulative scored SRS_Not_Signed
"
    ::= {cumulativeScoreStat 69}

cumulScoredvirus-FileScan  OBJECT-TYPE
    SYNTAX      Counter32
    MAX-ACCESS  read-only
    STATUS      current
    DESCRIPTION
"
cumulative scored virus-FileScan
"
    ::= {cumulativeScoreStat 70}

cumulScoredBlacklistedHelo  OBJECT-TYPE
    SYNTAX      Counter32
    MAX-ACCESS  read-only
    STATUS      current
    DESCRIPTION
"
cumulative scored BlacklistedHelo
"
    ::= {cumulativeScoreStat 71}

cumulScoredWhiteSenderBase  OBJECT-TYPE
    SYNTAX      Counter32
    MAX-ACCESS  read-only
    STATUS      current
    DESCRIPTION
"
cumulative scored WhiteSenderBase
"
    ::= {cumulativeScoreStat 72}

cumulScoredinternaladdress  OBJECT-TYPE
    SYNTAX      Counter32
    MAX-ACCESS  read-only
    STATUS      current
    DESCRIPTION
"
cumulative scored internaladdress
"
    ::= {cumulativeScoreStat 73}

cumulScoredIPinHELOmismatch  OBJECT-TYPE
    SYNTAX      Counter32
    MAX-ACCESS  read-only
    STATUS      current
    DESCRIPTION
"
cumulative scored IPinHELOmismatch
"
    ::= {cumulativeScoreStat 74}

cumulScoredLimitingIPDomain  OBJECT-TYPE
    SYNTAX      Counter32
    MAX-ACCESS  read-only
    STATUS      current
    DESCRIPTION
"
cumulative scored LimitingIPDomain
"
    ::= {cumulativeScoreStat 75}

cumulScoredMaxDuplicateRcpt  OBJECT-TYPE
    SYNTAX      Counter32
    MAX-ACCESS  read-only
    STATUS      current
    DESCRIPTION
"
cumulative scored MaxDuplicateRcpt
"
    ::= {cumulativeScoreStat 76}

cumulScoredMsg-IDsuspicious  OBJECT-TYPE
    SYNTAX      Counter32
    MAX-ACCESS  read-only
    STATUS      current
    DESCRIPTION
"
cumulative scored Msg-IDsuspicious
"
    ::= {cumulativeScoreStat 77}

cumulScoredbombSuspiciousRe  OBJECT-TYPE
    SYNTAX      Counter32
    MAX-ACCESS  read-only
    STATUS      current
    DESCRIPTION
"
cumulative scored bombSuspiciousRe
"
    ::= {cumulativeScoreStat 78}

cumulScoredBATV-check-failed  OBJECT-TYPE
    SYNTAX      Counter32
    MAX-ACCESS  read-only
    STATUS      current
    DESCRIPTION
"
cumulative scored BATV-check-failed
"
    ::= {cumulativeScoreStat 79}

cumulScoredBlacklistedDomain  OBJECT-TYPE
    SYNTAX      Counter32
    MAX-ACCESS  read-only
    STATUS      current
    DESCRIPTION
"
cumulative scored BlacklistedDomain
"
    ::= {cumulativeScoreStat 80}

cumulScoredSPFneutral-strict  OBJECT-TYPE
    SYNTAX      Counter32
    MAX-ACCESS  read-only
    STATUS      current
    DESCRIPTION
"
cumulative scored SPFneutral-strict
"
    ::= {cumulativeScoreStat 81}

cumulScoredBackscatter-failed  OBJECT-TYPE
    SYNTAX      Counter32
    MAX-ACCESS  read-only
    STATUS      current
    DESCRIPTION
"
cumulative scored Backscatter-failed
"
    ::= {cumulativeScoreStat 82}

cumulScoredBombSenderMailFrom  OBJECT-TYPE
    SYNTAX      Counter32
    MAX-ACCESS  read-only
    STATUS      current
    DESCRIPTION
"
cumulative scored BombSenderMailFrom
"
    ::= {cumulativeScoreStat 83}

cumulScoredInvalidLocalSender  OBJECT-TYPE
    SYNTAX      Counter32
    MAX-ACCESS  read-only
    STATUS      current
    DESCRIPTION
"
cumulative scored InvalidLocalSender
"
    ::= {cumulativeScoreStat 84}

cumulScoredSPFsoftfail-strict  OBJECT-TYPE
    SYNTAX      Counter32
    MAX-ACCESS  read-only
    STATUS      current
    DESCRIPTION
"
cumulative scored SPFsoftfail-strict
"
    ::= {cumulativeScoreStat 85}

cumulScoredSpamCollectAddress  OBJECT-TYPE
    SYNTAX      Counter32
    MAX-ACCESS  read-only
    STATUS      current
    DESCRIPTION
"
cumulative scored SpamCollectAddress
"
    ::= {cumulativeScoreStat 86}

cumulScoredLimitingSameSubject  OBJECT-TYPE
    SYNTAX      Counter32
    MAX-ACCESS  read-only
    STATUS      current
    DESCRIPTION
"
cumulative scored LimitingSameSubject
"
    ::= {cumulativeScoreStat 87}

cumulScoredSSL-TLS-connection-OK  OBJECT-TYPE
    SYNTAX      Counter32
    MAX-ACCESS  read-only
    STATUS      current
    DESCRIPTION
"
cumulative scored SSL-TLS-connection-OK
"
    ::= {cumulativeScoreStat 88}

cumulScoredMSGID-signature-failed  OBJECT-TYPE
    SYNTAX      Counter32
    MAX-ACCESS  read-only
    STATUS      current
    DESCRIPTION
"
cumulative scored MSGID-signature-failed
"
    ::= {cumulativeScoreStat 89}

cumulScoredSuspiciousVirus-ClamAV  OBJECT-TYPE
    SYNTAX      Counter32
    MAX-ACCESS  read-only
    STATUS      current
    DESCRIPTION
"
cumulative scored SuspiciousVirus-ClamAV
"
    ::= {cumulativeScoreStat 90}

cumulScoredSuspiciousVirus-FileScan  OBJECT-TYPE
    SYNTAX      Counter32
    MAX-ACCESS  read-only
    STATUS      current
    DESCRIPTION
"
cumulative scored SuspiciousVirus-FileScan
"
    ::= {cumulativeScoreStat 91}

asspAPIcmd  OBJECT-TYPE
    SYNTAX      OCTET STRING
    MAX-ACCESS  read-write
    STATUS      current
    DESCRIPTION
"
the command to be executed inside assp
"
    ::= {asspAPI 0}

asspAPIresult   OBJECT-TYPE
    SYNTAX      OCTET STRING
    MAX-ACCESS  read-write
    STATUS      current
    DESCRIPTION
"
result of the command that was executed in asspAPI (.5.0)
"
    ::= {asspAPI 1}



END
